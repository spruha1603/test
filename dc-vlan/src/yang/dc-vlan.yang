module dc-vlan {
  namespace "http://com/comcast/services/dcvlan";  
  prefix dcvlan;

  import tailf-ncs {
    prefix ncs;
  }
  import tailf-common {
    prefix tailf;
  }
  

  organization "Comcast";
	
  contact  "Comcast Platform Services";
	
  description  "Comcast data center port turn-up service YANG model";
	
  revision 2016-11-08 {
    description "First release of the vlan service";
    reference "Comcast Yang";
  }
    typedef duplex-type {
    type enumeration {
      enum full;
      enum half;
    }
  }

  typedef vlan-id-type {
    type uint16 {
      range "1..4094";  
    }
  }

  typedef role {
    type enumeration {
      enum "ur";
      enum "l3-spine";
      enum "l3-leaf";
      enum "l2-topofrack";
      //enum "l2-spine";
      //enum “agg-spine”;
    }
  }
  
  augment /ncs:services {
    list dc-vlan {
      tailf:info "Data center VLAN service";
      key device;

      uses ncs:service-data;
      ncs:servicepoint "dc-vlan";

      leaf device {
        type leafref {
          path "/ncs:devices/ncs:device/ncs:name";
        }
      }

      list vlan {
        key "vlan-id";
        leaf vlan-id {
          tailf:info "VLAN identifier that is the key of service";
          type vlan-id-type;
        }
        leaf vlan-name {
          description "Name used to identify this VLAN";
          type string;
          mandatory true;
        }
      }
    }
  }
}
