module tailf-ned-cisco-ios {
  // Generated by yanger -t ncs
  tailf:ncs-device-type "cli-ned";

  namespace "urn:ios";
  prefix ios;

  import tailf-common {
    prefix tailf;
  }
  import ietf-inet-types {
    prefix inet;
  }
  import ietf-yang-types {
    prefix yang;
  }
  import tailf-ncs {
    prefix ncs;
  }

  revision 2017-03-17 {
    description
      "5.0.14
       See CHANGES.
      ";
  }

  typedef isakmp-pfs-type {
    type enumeration {
      enum "group1" {
        tailf:info
          "D-H Group1 (768-bit modp)";
      }
      enum "group14" {
        tailf:info
          "D-H Group14 (2048-bit modp)";
      }
      enum "group15" {
        tailf:info
          "D-H Group15 (3072-bit modp)";
      }
      enum "group16" {
        tailf:info
          "D-H Group16 (4096-bit modp)";
      }
      enum "group19" {
        tailf:info
          "D-H Group19 (256-bit ecp)";
      }
      enum "group2" {
        tailf:info
          "D-H Group2 (1024-bit modp)";
      }
      enum "group20" {
        tailf:info
          "D-H Group20 (384-bit ecp)";
      }
      enum "group21" {
        tailf:info
          "D-H Group21 (521-bit ecp)";
      }
      enum "group24" {
        tailf:info
          "D-H Group24 (2048-bit modp, 256 bit subgroup)";
      }
      enum "group5" {
        tailf:info
          "D-H Group5 (1536-bit modp)";
      }
    }
  }

  typedef object-group-service-tcp-udp-type {
    type union {
      type uint16 {
        tailf:info
          "<0-65535>;;Port number";
      }
      type enumeration {
        enum "discard" {
          tailf:info
            "Discard (9)";
        }
        enum "domain" {
          tailf:info
            "Domain Name Service (53)";
        }
        enum "echo" {
          tailf:info
            "Echo (7)";
        }
        enum "pim-auto-rp" {
          tailf:info
            "PIM Auto-RP (496)";
        }
        enum "sunrpc" {
          tailf:info
            "Sun Remote Procedure Call (111)";
        }
        enum "syslog" {
          tailf:info
            "Syslog (514)";
        }
        enum "tacacs" {
          tailf:info
            "TAC Access Control System (49)";
        }
        enum "talk" {
          tailf:info
            "Talk (517)";
        }
      }
    }
  }

  typedef object-group-service-udp-type {
    type union {
      type uint16 {
        tailf:info
          "<0-65535>;;Port number";
      }
      type enumeration {
        enum "biff" {
          tailf:info
            "Biff (mail notification, comsat, 512)";
        }
        enum "bootpc" {
          tailf:info
            "Bootstrap Protocol (BOOTP) client (68)";
        }
        enum "discard" {
          tailf:info
            "Discard (9)";
        }
        enum "dnsix" {
          tailf:info
            "DNSIX security protocol auditing (195)";
        }
        enum "domain" {
          tailf:info
            "Domain Name Service (DNS, 53)";
        }
        enum "echo" {
          tailf:info
            "Echo (7)";
        }
        enum "isakmp" {
          tailf:info
            "Internet Security Association and Key Management Protocol (500)";
        }
        enum "mobile-ip" {
          tailf:info
            "Mobile IP registration (434)";
        }
        enum "nameserver" {
          tailf:info
            "IEN116 name service (obsolete, 42)";
        }
        enum "netbios-dgm" {
          tailf:info
            "NetBios datagram service (138)";
        }
        enum "netbios-ns" {
          tailf:info
            "NetBios name service (137)";
        }
        enum "netbios-ss" {
          tailf:info
            "NetBios session service (139)";
        }
        enum "non500-isakmp" {
          tailf:info
            "Internet Security Association and Key Management Protocol (4500)";
        }
        enum "ntp" {
          tailf:info
            "Network Time Protocol (123)";
        }
        enum "pim-auto-rp" {
          tailf:info
            "PIM Auto-RP (496)";
        }
        enum "rip" {
          tailf:info
            "Routing Information Protocol (router, in.routed, 520)";
        }
        enum "ripv6" {
          tailf:info
            "Routing Information Protocol V6 (router, in.routed, 521)";
        }
        enum "snmp" {
          tailf:info
            "Simple Network Management Protocol (161)";
        }
        enum "snmptrap" {
          tailf:info
            "SNMP Traps (162)";
        }
        enum "sunrpc" {
          tailf:info
            "Sun Remote Procedure Call (111)";
        }
        enum "syslog" {
          tailf:info
            "System Logger (514)";
        }
        enum "tacacs" {
          tailf:info
            "TAC Access Control System (49)";
        }
        enum "talk" {
          tailf:info
            "Talk (517)";
        }
        enum "tftp" {
          tailf:info
            "Trivial File Transfer Protocol (69)";
        }
        enum "time" {
          tailf:info
            "Time (37)";
        }
        enum "who" {
          tailf:info
            "Who service (rwho, 513)";
        }
        enum "xdmcp" {
          tailf:info
            "X Display Manager Control Protocol (177)";
        }
      }
    }
  }

  typedef object-group-service-tcp-type {
    type union {
      type uint16 {
        tailf:info
          "<0-65535>;;Port number";
      }
      type enumeration {
        enum "bgp" {
          tailf:info
            "Border Gateway Protocol (179)";
        }
        enum "chargen" {
          tailf:info
            "Character generator (19)";
        }
        enum "cmd" {
          tailf:info
            "Remote commands (rcmd, 514)";
        }
        enum "connectedapps-plain" {
          tailf:info
            "ConnectedApps Cleartext (15001)";
        }
        enum "connectedapps-tls" {
          tailf:info
            "ConnectedApps TLS (15002)";
        }
        enum "daytime" {
          tailf:info
            "Daytime (13)";
        }
        enum "discard" {
          tailf:info
            "Discard (9)";
        }
        enum "domain" {
          tailf:info
            "Domain Name Service (53)";
        }
        enum "echo" {
          tailf:info
            "Echo (7)";
        }
        enum "exec" {
          tailf:info
            "Exec (rsh, 512)";
        }
        enum "finger" {
          tailf:info
            "Finger (79)";
        }
        enum "ftp" {
          tailf:info
            "File Transfer Protocol (21)";
        }
        enum "ftp-data" {
          tailf:info
            "FTP data connections (20)";
        }
        enum "gopher" {
          tailf:info
            "Gopher (70)";
        }
        enum "hostname" {
          tailf:info
            "NIC hostname server (101)";
        }
        enum "ident" {
          tailf:info
            "Ident Protocol (113)";
        }
        enum "irc" {
          tailf:info
            "Internet Relay Chat (194)";
        }
        enum "klogin" {
          tailf:info
            "Kerberos login (543)";
        }
        enum "kshell" {
          tailf:info
            "Kerberos shell (544)";
        }
        enum "login" {
          tailf:info
            "Login (rlogin, 513)";
        }
        enum "lpd" {
          tailf:info
            "Printer service (515)";
        }
        enum "msrpc" {
          tailf:info
            "MS Remote Procedure Call (135)";
        }
        enum "nntp" {
          tailf:info
            "Network News Transport Protocol (119)";
        }
        enum "pim-auto-rp" {
          tailf:info
            "PIM Auto-RP (496)";
        }
        enum "pop2" {
          tailf:info
            "Post Office Protocol v2 (109)";
        }
        enum "pop3" {
          tailf:info
            "Post Office Protocol v3 (110)";
        }
        enum "smtp" {
          tailf:info
            "Simple Mail Transport Protocol (25)";
        }
        enum "sunrpc" {
          tailf:info
            "Sun Remote Procedure Call (111)";
        }
        enum "syslog" {
          tailf:info
            "Syslog (514)";
        }
        enum "tacacs" {
          tailf:info
            "TAC Access Control System (49)";
        }
        enum "talk" {
          tailf:info
            "Talk (517)";
        }
        enum "telnet" {
          tailf:info
            "Telnet (23)";
        }
        enum "time" {
          tailf:info
            "Time (37)";
        }
        enum "uucp" {
          tailf:info
            "Unix-to-Unix Copy Program (540)";
        }
        enum "whois" {
          tailf:info
            "Nicname (43)";
        }
        enum "www" {
          tailf:info
            "World Wide Web (HTTP, 80)";
        }
      }
    }
  }

  typedef object-group-service-icmp-type {
    type union {
      type uint16 {
        tailf:info
          "<0-65535>;;Port number";
      }
      type enumeration {
        enum "alternate-address" {
          tailf:info
            "Alternate address";
        }
        enum "conversion-error" {
          tailf:info
            "Datagram conversion";
        }
        enum "echo" {
          tailf:info
            "Echo (ping)";
        }
        enum "echo-reply" {
          tailf:info
            "Echo reply";
        }
        enum "information-reply" {
          tailf:info
            "Information replies";
        }
        enum "information-request" {
          tailf:info
            "Information requests";
        }
        enum "mask-reply" {
          tailf:info
            "Mask replies";
        }
        enum "mask-request" {
          tailf:info
            "Mask requests";
        }
        enum "mobile-redirect" {
          tailf:info
            "Mobile host redirect";
        }
        enum "parameter-problem" {
          tailf:info
            "All parameter problems";
        }
        enum "redirect" {
          tailf:info
            "All redirects";
        }
        enum "router-advertisement" {
          tailf:info
            "Router discovery advertise.";
        }
        enum "router-solicitation" {
          tailf:info
            "Router discovery solicitations";
        }
        enum "source-quench" {
          tailf:info
            "Source quenches";
        }
        enum "time-exceeded" {
          tailf:info
            "All time exceededs";
        }
        enum "timestamp-reply" {
          tailf:info
            "Timestamp replies";
        }
        enum "timestamp-request" {
          tailf:info
            "Timestamp requests";
        }
        enum "traceroute" {
          tailf:info
            "Traceroute";
        }
        enum "unreachable" {
          tailf:info
            "All unreachables";
        }
      }
    }
  }

  typedef cable-downstream-interleaver-depth-option {
    type enumeration {
      enum "I128-J1" {
        tailf:info
          "RFGW_MB_FEC-I-128-J-1";
      }
      enum "I128-J2" {
        tailf:info
          "RFGW_MB_FEC-I-128-J-2";
      }
      enum "I128-J3" {
        tailf:info
          "RFGW_MB_FEC-I-128-J-3";
      }
      enum "I128-J4" {
        tailf:info
          "RFGW_MB_FEC-I-128-J-4";
      }
      enum "I128-J5" {
        tailf:info
          "RFGW_MB_FEC-I-128-J-5";
      }
      enum "I128-J6" {
        tailf:info
          "RFGW_MB_FEC-I-128-J-6";
      }
      enum "I128-J7" {
        tailf:info
          "RFGW_MB_FEC-I-128-J-7";
      }
      enum "I128-J8" {
        tailf:info
          "RFGW_MB_FEC-I-128-J-8";
      }
      enum "I16-J8" {
        tailf:info
          "RFGW_MB_FEC-I-16-J-8 ";
      }
      enum "I32-J4" {
        tailf:info
          "RFGW_MB_FEC-I-32-J-4 ";
      }
      enum "I64-J2" {
        tailf:info
          "RFGW_MB_FEC-I-64-J-2 ";
      }
      enum "I8-J16" {
        tailf:info
          "RFGW_MB_FEC-I-8-J-16 ";
      }
    }
  }

  typedef l2protocol-type {
    type enumeration {
      enum "cdp" {
        tailf:info
          "Cisco Discovery Protocol";
      }
      enum "dtp" {
        tailf:info
          "Dynamic Trunking Protocol";
      }
      enum "lacp" {
        tailf:info
          "LACP Protocol";
      }
      enum "lldp" {
        tailf:info
          "Link Layer Discovery Protocol";
      }
      enum "pagp" {
        tailf:info
          "Port Aggregation Protocol";
      }
      enum "stp" {
        tailf:info
          "Spanning Tree Protocol";
      }
      enum "udld" {
        tailf:info
          "UDLD Protocol";
      }
      enum "vtp" {
        tailf:info
          "Vlan Trunking Protocol";
      }
      enum "dot1x" {
        tailf:info
          "Dot1x Protocol";
      }
    }
  }

  typedef eigrp-as-no-type {
    type union {
      type uint16 {
        tailf:info
          "<1-65535>;;Autonomous system number";
        range "1..65535";
      }
      type string {
        tailf:info
          "WORD;;EIGRP Virtual-Instance Name";
      }
    }
  }

  typedef bgp-as-no-type {
    type union {
      type uint32 {
        tailf:info
          "<1-4294967295>;;Autonomous system number";
        range "1..4294967295";
      }
      type string {
        tailf:info
          "<1.0-XX.YY>;;Autonomous system number";
        pattern '[0-9]+.*';
      }
    }
  }

  typedef ipsec-window-size-type {
    type enumeration {
      enum "1024" {
        tailf:info
          "Window size of 1024";
      }
      enum "128" {
        tailf:info
          "Window size of 128";
      }
      enum "256" {
        tailf:info
          "Window size of 256";
      }
      enum "512" {
        tailf:info
          "Window size of 512";
      }
      enum "64" {
        tailf:info
          "Window size of 64 (default)";
      }
    }
  }

  typedef aaa-group-type {
    type union {
      type string {
        tailf:info
          "WORD;;Server-group name";
      }
      type enumeration {
        enum "ldap" {
          tailf:info
            "Use list of all LDAP hosts.";
        }
        enum "radius" {
          tailf:info
            "Use list of all Radius hosts.";
        }
        enum "tacacs+" {
          tailf:info
            "Use list of all Tacacs+ hosts.";
        }
      }
    }
  }

  typedef aaa-accounting-name-type {
    type union {
      type enumeration {
        enum "default" {
          tailf:info
            "The default accounting list.";
        }
      }
      type string {
        tailf:info
          "WORD;;Named Accounting list (max 31 characters).";
        length "1..31";
      }
    }
  }

  typedef aaa-authentication-name-type {
    type union {
      type enumeration {
        enum "default" {
          tailf:info
            "The default authentication list.";
        }
      }
      type string {
        tailf:info
          "WORD;;Named authentication list (max 31 characters).";
        length "1..31";
      }
    }
  }

  typedef aaa-authorization-name-type {
    type union {
      type enumeration {
        enum "default" {
          tailf:info
            "The default authorization list.";
        }
      }
      type string {
        tailf:info
          "WORD;;Named authorization list (max 31 characters).";
        length "1..31";
      }
    }
  }

  typedef police-burst-type {
    type uint32 {
      tailf:info
        "<1000-512000000>;;Burst bytes";
      range "1000..512000000";
    }
  }

  typedef police-bps-type {
    type uint64 {
      tailf:info
        "<8000-64000000000>;;Bits per second";
      range "8000..64000000000";
    }
  }

  typedef police-pps-bps-type {
    type enumeration {
      enum "pps" {
        tailf:info
          "pps  Treat 'rate' value in packets-per-second";
      }
      enum "bps" {
        tailf:info
          "pps  Treat 'rate' value in bytes-per-second";
      }
    }
  }

  typedef police-packets-bytes-type {
    type enumeration {
      enum "packets" {
        tailf:info
          "Treat 'burst' value as packets";
      }
      enum "bytes" {
        tailf:info
          "Treat 'burst' value as bytes";
      }
    }
  }

  typedef operator-type {
    type enumeration {
      enum "eq" {
        tailf:info
          "Equal to";
      }
      enum "ge" {
        tailf:info
          "Greater than or equal to";
      }
      enum "gt" {
        tailf:info
          "Greater than";
      }
      enum "le" {
        tailf:info
          "Less than or equal to";
      }
      enum "lt" {
        tailf:info
          "Less than";
      }
      enum "ne" {
        tailf:info
          "Not equal to";
      }
    }
  }

  typedef logging-level-type {
    type union {
      type uint16 {
        tailf:info
          "<0-7>;;Logging severity level";
        range "0..7";
      }
      type enumeration {
        enum "alerts" {
          tailf:info
            "Immediate action needed (severity=1)";
          value 1;
        }
        enum "critical" {
          tailf:info
            "Critical conditions (severity=2)";
          value 2;
        }
        enum "debugging" {
          tailf:info
            "Debugging messages (severity=7)";
          value 7;
        }
        enum "emergencies" {
          tailf:info
            "System is unusable (severity=0)";
          value 0;
        }
        enum "errors" {
          tailf:info
            "Error conditions (severity=3)";
          value 3;
        }
        enum "informational" {
          tailf:info
            "Informational messages (severity=6)";
          value 6;
        }
        enum "notifications" {
          tailf:info
            "Normal but significant conditions (severity=5)";
          value 5;
        }
        enum "warnings" {
          tailf:info
            "Warning conditions (severity=4)";
          value 4;
        }
      }
    }
  }

  typedef authentication-level-type {
    type enumeration {
      enum "level-1" {
        tailf:info
          "ISIS authentication for level-1";
      }
      enum "level-2" {
        tailf:info
          "ISIS authentication for level-2";
      }
    }
  }

  typedef isis-level-type {
    type enumeration {
      enum "level-1" {
        tailf:info
          "Level-1 only";
      }
      enum "level-1-2" {
        tailf:info
          "Level-1-2";
      }
      enum "level-2" {
        tailf:info
          "Level-2 only";
      }
    }
  }

  typedef limit-dc-non-dc-type {
    type union {
      type uint32 {
        tailf:info
          "<1-255>;;The maximum number of retransmissions";
        range "1..255";
      }
      type enumeration {
        enum "disable" {
          tailf:info
            "Disable the feature";
        }
      }
    }
  }

  typedef ospf-metric-type {
    type uint32 {
      tailf:info
        "<1-2>;;OSPF Link State type";
      range "1..2";
    }
  }

  typedef ospf-area-type {
    type union {
      type uint32 {
        tailf:info
          "<0-4294967295>;;OSPF area ID as a decimal value";
        range "0..4294967295";
      }
      type inet:ipv4-address {
        tailf:info
          "A.B.C.D;;OSPF area ID in IP address format";
      }
    }
  }

  typedef redist-ospf-external-type {
    type enumeration {
      enum "1" {
        tailf:info
          "Redistribute external type 1 routes";
      }
      enum "2" {
        tailf:info
          "Redistribute external type 2 routes";
      }
    }
  }

  typedef prec_value-type {
    type union {
      type uint8 {
        tailf:info
          "<0-7>;;new precedence";
        range "0..7";
      }
      type enumeration {
        enum "cos" {
          tailf:info
            "Set packet precedence from cos";
          value 1001;
        }
        enum "dscp" {
          tailf:info
            "Set packet precedence from dscp";
          value 1002;
        }
        enum "exp" {
          tailf:info
            "Set packet precedence from exp";
          value 1003;
        }
        enum "precedence" {
          tailf:info
            "Set packet precedence from precedence";
          value 1004;
        }
      }
    }
  }

  typedef exp_value-type {
    type union {
      type uint8 {
        tailf:info
          "<0-7>;;new exp";
        range "0..7";
      }
      type enumeration {
        enum "cos" {
          tailf:info
            "Set packet exp from cos";
          value 1001;
        }
        enum "dscp" {
          tailf:info
            "Set packet exp from dscp";
          value 1002;
        }
        enum "exp" {
          tailf:info
            "Set packet exp from exp";
          value 1003;
        }
        enum "precedence" {
          tailf:info
            "Set packet exp from precedence";
          value 1004;
        }
      }
    }
  }

  typedef qos_value-type {
    type union {
      type uint8 {
        tailf:info
          "<0-99>;;new qos-group";
        range "0..99";
      }
      type enumeration {
        enum "cos" {
          tailf:info
            "Set packet qos from cos";
          value 1001;
        }
        enum "dscp" {
          tailf:info
            "Set packet qos from dscp";
          value 1002;
        }
        enum "exp" {
          tailf:info
            "Set packet qos from exp";
          value 1003;
        }
        enum "precedence" {
          tailf:info
            "Set packet qos from precedence";
          value 1004;
        }
      }
    }
  }

  typedef cos_value-type {
    type union {
      type uint8 {
        tailf:info
          "<0-7>;;new cos value";
        range "0..7";
      }
      type enumeration {
        enum "cos" {
          tailf:info
            "Set packet cos from cos";
          value 1001;
        }
        enum "dscp" {
          tailf:info
            "Set packet cos from dscp";
          value 1002;
        }
        enum "exp" {
          tailf:info
            "Set packet cos from exp";
          value 1003;
        }
        enum "precedence" {
          tailf:info
            "Set packet cos from precedence";
          value 1004;
        }
      }
    }
  }

  typedef precedence-type {
    type union {
      type uint8 {
        tailf:info
          "<0-7>;;Precedence value";
        range "0..7";
      }
      type enumeration {
        enum "critical" {
          tailf:info
            "Set packets with critical precedence (5)";
        }
        enum "flash" {
          tailf:info
            "Set packets with flash precedence (3)";
        }
        enum "flash-override" {
          tailf:info
            "Set packets with flash override precedence (4)";
        }
        enum "immediate" {
          tailf:info
            "Set packets with immediate precedence (2)";
        }
        enum "internet" {
          tailf:code-name "prec_internet";
          tailf:info
            "Set packets with internetwork control precedence (6)";
        }
        enum "network" {
          tailf:info
            "Set packets with network control precedence (7)";
        }
        enum "priority" {
          tailf:code-name "prec_priority";
          tailf:info
            "Set packets with priority precedence (1)";
        }
        enum "routine" {
          tailf:info
            "Set packets with routine precedence (0)";
        }
      }
    }
  }

  typedef dscp-type {
    type union {
      type uint8 {
        tailf:info
          "<0-63>;;Differentiated services codepoint value";
        range "0..63";
      }
      type enumeration {
        enum "af11" {
          tailf:info
            "Match packets with AF11 dscp (001010)";
          value 10011;
        }
        enum "af12" {
          tailf:info
            "Match packets with AF12 dscp (001100)";
          value 10012;
        }
        enum "af13" {
          tailf:info
            "Match packets with AF13 dscp (001110)";
          value 10013;
        }
        enum "af21" {
          tailf:info
            "Match packets with AF21 dscp (010010)";
          value 10021;
        }
        enum "af22" {
          tailf:info
            "Match packets with AF22 dscp (010100)";
          value 10022;
        }
        enum "af23" {
          tailf:info
            "Match packets with AF23 dscp (010110)";
          value 10023;
        }
        enum "af31" {
          tailf:info
            "Match packets with AF31 dscp (011010)";
          value 10031;
        }
        enum "af32" {
          tailf:info
            "Match packets with AF32 dscp (011100)";
          value 10032;
        }
        enum "af33" {
          tailf:info
            "Match packets with AF33 dscp (011110)";
          value 10033;
        }
        enum "af41" {
          tailf:info
            "Match packets with AF41 dscp (100010)";
          value 10041;
        }
        enum "af42" {
          tailf:info
            "Match packets with AF42 dscp (100100)";
          value 10042;
        }
        enum "af43" {
          tailf:info
            "Match packets with AF43 dscp (100110)";
          value 10043;
        }
        enum "cs1" {
          tailf:info
            "Match packets with CS1(precedence 1) dscp (001000)";
          value 10001;
        }
        enum "cs2" {
          tailf:info
            "Match packets with CS2(precedence 2) dscp (010000)";
          value 10002;
        }
        enum "cs3" {
          tailf:info
            "Match packets with CS3(precedence 3) dscp (011000)";
          value 10003;
        }
        enum "cs4" {
          tailf:info
            "Match packets with CS4(precedence 4) dscp (100000)";
          value 10004;
        }
        enum "cs5" {
          tailf:info
            "Match packets with CS5(precedence 5) dscp (101000)";
          value 10005;
        }
        enum "cs6" {
          tailf:info
            "Match packets with CS6(precedence 6) dscp (110000)";
          value 10006;
        }
        enum "cs7" {
          tailf:info
            "Match packets with CS7(precedence 7) dscp (111000)";
          value 10007;
        }
        enum "default" {
          tailf:info
            "Match packets with default dscp (000000)";
          tailf:code-name "dscp_default";
          value 1000;
        }
        enum "dscp" {
          tailf:info
            "Set packet dscp from dscp";
          value 1001;
        }
        enum "ef" {
          tailf:info
            "Match packets with EF dscp (101110)";
          value 1002;
        }
        enum "precedence" {
          tailf:info
            "Set packet dscp from precedence";
          value 1003;
        }
      }
    }
  }

  typedef spanning-tree-cost-type {
    type union {
      type uint32 {
        tailf:info
          "<1-200000000>;;Port path cost";
        range "1..200000000";
      }
      type enumeration {
        enum "auto" {
          tailf:code-name "spanning-tree-cost-type-auto";
          tailf:info
            "Determine cost based on media speed of this interface";
        }
      }
    }
  }

  typedef mst-cost-type {
    type union {
      type uint32 {
        tailf:info
          "<1-200000000>;;Port path cost";
        range "1..200000000";
      }
      type enumeration {
        enum "auto" {
          tailf:code-name "mst_cost_type_auto";
          tailf:info
            "Determine cost based on media speed of this interface";
        }
      }
    }
  }

  typedef ldp-discovery-address-type {
    type union {
      type enumeration {
        enum "interface" {
          tailf:info
            "Use interface address for LDP transport address";
          tailf:code-name "ldp_interface";
        }
      }
      type inet:ipv4-address {
        tailf:info
          "A.B.C.D;;IP address to use for LDP transport address";
      }
    }
  }

  typedef exp-ip-acl-type {
    type union {
      type uint16 {
        tailf:info
          "<1-199>;;IP access list";
        range "1..199";
      }
      type uint16 {
        tailf:info
          "<1300-2699>;;IP expanded access list";
        range "1300..2699";
      }
      type string {
        tailf:info
          "WORD;;Access-list name";
      }
    }
  }

  typedef ext-ip-acl-type {
    type union {
      type uint16 {
        tailf:info
          "<100-199>;;IP access list number";
        range "100..199";
      }
      type uint16 {
        tailf:info
          "<2000-2699>;;IP access list number (expanded range)";
        range "2000..2699";
      }
      type string {
        tailf:info
          "WORD;;Access-list name";
      }
    }
  }

  typedef ip-acl-type {
    type union {
      type uint16 {
        tailf:info
          "<1-199>;;Standard or Extended IP access list number";
        range "1..199";
      }
      type string {
        tailf:info
          "WORD;;IP Named Access list";
      }
    }
  }

  typedef std-ip-acl-type {
    type union {
      type uint16 {
        tailf:info
          "<1-99>;;Standard IP access list";
        range "1..99";
      }
      type uint16 {
        tailf:info
          "<1300-1999>;;Standard IP access list (expanded range)";
        range "1300..1999";
      }
      type string {
        tailf:info
          "WORD;;Named access list";
      }
    }
  }

  typedef ext-acl-type {
    type union {
      type uint16 {
        tailf:info
          "<100-199>;;Access list number";
        range "100..199";
      }
      type uint16 {
        tailf:info
          "<2000-2699>;;Access list number (expanded range)";
        range "2000..2699";
      }
      type string {
        tailf:info
          "WORD;;IP Named Extended Access list";
      }
    }
  }

  typedef std-acl-type {
    type union {
      type uint16 {
        tailf:info
          "<1-99>;;Standard access list";
        range "1..99";
      }
      type uint16 {
        tailf:info
          "<1300-1999>;;Standard access list (expanded range)";
        range "1300..1999";
      }
      type string {
        tailf:info
          "WORD;;Named access list";
      }
    }
  }

  typedef month-type {
    type enumeration {
      enum "Jan";
      enum "Feb";
      enum "Mar";
      enum "Apr";
      enum "May";
      enum "Jun";
      enum "Jul";
      enum "Aug";
      enum "Sep";
      enum "Oct";
      enum "Nov";
      enum "Dec";
    }
  }

  typedef weekday-type {
    type enumeration {
      enum "Mon";
      enum "Tue";
      enum "Wed";
      enum "Thu";
      enum "Fri";
      enum "Sat";
      enum "Sun";
    }
  }

  typedef hhmm-type {
    type string {
      pattern '([0-1]?[0-9]|2[0-4]):([0-5][0-9])(:[0-5][0-9])?';
    }
  }

  typedef asn-ip-type {
    type string {
      tailf:info
        "ASN:nn or IP-address:nn";
      pattern '(([0-9]+)|((([0-9]|[1-9][0-9]|1[0-9][0-9]|2[0-4][0-9]|25[0-5])\.){3}([0-9]|[1-9][0-9]|1[0-9][0-9]|2[0-4][0-9]|25[0-5]))):[0-9]+';
    }
  }

  typedef vpn-id-type {
    type string {
      tailf:info
        "OUI:VPN-Index;;, format (hex) <3 bytes OUI:4 bytes VPN_Index>";
      pattern '[0-9a-fA-F][0-9a-fA-F]?[0-9a-fA-F]?:[0-9a-fA-F][0-9a-fA-F]?[0-9a-fA-F]?[0-9a-fA-F]?';
    }
  }

  typedef rd-type {
    type string {
      tailf:info
        "ASN:nn or IP-address:nn;;VPN Route Distinguisher";
      pattern '(\d*(.\d*)*)?:(\d*(.\d*)*)?';
    }
  }

  typedef ipv6-prefix {
    type tailf:ipv6-address-and-prefix-length;
  }

  typedef ipv4-prefix {
    type tailf:ipv4-address-and-prefix-length;
  }

  typedef percentage-type {
    type uint8 {
      tailf:info
        "<1-100>;;Percentage";
      range "1..100";
    }
  }

  grouping ncs_template_description-grouping {
    leaf description {
      type string;
    }
  }

  grouping ncs_template_password-grouping {
    leaf type {
      type string;
    }
    leaf secret {
      type string;
    }
  }

  grouping ncs_template_crypto-key-grouping {
    leaf encryption {
      type string;
    }
    leaf secret {
      type string;
    }
  }

  grouping ncs_template_interface-name-grouping {
    choice interface-choice {
      leaf Null {
        type string;
      }
      leaf Loopback {
        type string;
      }
      leaf VirtualPortGroup {
        type string;
      }
      leaf Embedded-Service-Engine {
        type string;
      }
      leaf Service-Engine {
        type string;
      }
      leaf Tunnel {
        type string;
      }
      leaf Port-channel {
        type string;
      }
      container Port-channel-subinterface {
        leaf Port-channel {
          type string;
        }
      }
      leaf Multilink {
        type string;
      }
      leaf MFR {
        type string;
      }
      container MFR-subinterface {
        leaf MFR {
          type string;
        }
      }
      leaf BRI {
        type string;
      }
      leaf Ethernet {
        type string;
      }
      leaf FastEthernet {
        type string;
      }
      leaf GigabitEthernet {
        type string;
      }
      leaf TenGigabitEthernet {
        type string;
      }
      leaf FortyGigabitEthernet {
        type string;
      }
      leaf HundredGigE {
        type string;
      }
      leaf Wlan-GigabitEthernet {
        type string;
      }
      leaf wlan-ap {
        type string;
      }
      leaf ATM {
        type string;
      }
      leaf CEM {
        type string;
      }
      leaf BDI {
        type string;
      }
      leaf BVI {
        type string;
      }
      leaf Cable {
        type string;
      }
      leaf Video {
        type string;
      }
      leaf Integrated-Cable {
        type string;
      }
      leaf Modular-Cable {
        type string;
      }
      leaf Wideband-Cable {
        type string;
      }
      leaf Dialer {
        type string;
      }
      leaf Bundle {
        type string;
      }
      leaf Cellular {
        type string;
      }
      leaf Qam-red {
        type string;
      }
      leaf Asi {
        type string;
      }
      leaf Vlan {
        type string;
      }
      leaf Async {
        type string;
      }
      leaf Group-Async {
        type string;
      }
      leaf POS {
        type string;
      }
      leaf Serial {
        type string;
      }
      container Serial-subinterface {
        leaf Serial {
          type string;
        }
      }
      leaf Virtual-Template {
        type string;
      }
      leaf pseudowire {
        type string;
      }
      leaf LISP {
        type string;
      }
      container LISP-subinterface {
        leaf LISP {
          type string;
        }
      }
      leaf ToP {
        type string;
      }
      leaf Dot11Radio {
        type string;
      }
      leaf vasileft {
        type string;
      }
      leaf vasiright {
        type string;
      }
      leaf AppNav-Compress {
        type string;
      }
      leaf AppNav-UnCompress {
        type string;
      }
      leaf ucse {
        type string;
      }
    }
  }

  grouping ncs_template_service-policy-grouping {
    leaf input {
      type string;
    }
    leaf output {
      type string;
    }
  }

  grouping ncs_template_police-action-transmit-grouping {
    leaf transmit {
      type empty;
    }
  }

  grouping ncs_template_police-action-drop-grouping {
    leaf drop {
      type empty;
    }
  }

  grouping ncs_template_police-conform-action-grouping {
    container conform-action {
      choice conform-action-choice {
        leaf set-clp-transmit {
          type empty;
        }
        leaf set-cos-transmit {
          type string;
        }
        leaf set-discard-class-transmit {
          type string;
        }
        leaf set-dscp-transmit {
          type string;
        }
        leaf set-frde-transmit {
          type empty;
        }
        leaf set-mpls-exp-imposition-transmit {
          type string;
        }
        leaf set-mpls-exp-topmost-transmit {
          type string;
        }
        leaf set-prec-transmit {
          type string;
        }
        leaf set-qos-transmit {
          type string;
        }
        leaf transmit {
          type empty;
        }
        leaf drop {
          type empty;
        }
      }
    }
    leaf table {
      type string;
    }
  }

  grouping ncs_template_police-exceed-action-grouping {
    container exceed-action {
      choice exceed-action-choice {
        leaf dscp {
          type string;
        }
        leaf set-clp-transmit {
          type empty;
        }
        leaf set-cos-transmit {
          type string;
        }
        leaf set-discard-class-transmit {
          type string;
        }
        leaf set-dscp-transmit {
          type string;
        }
        leaf set-frde-transmit {
          type empty;
        }
        leaf set-mpls-exp-imposition-transmit {
          type string;
        }
        leaf set-mpls-exp-topmost-transmit {
          type string;
        }
        leaf set-prec-transmit {
          type string;
        }
        leaf set-qos-transmit {
          type string;
        }
        leaf transmit {
          type empty;
        }
        leaf drop {
          type empty;
        }
      }
    }
  }

  grouping ncs_template_police-violate-action-grouping {
    container violate-action {
      choice violate-action-choice {
        leaf set-clp-transmit {
          type empty;
        }
        leaf set-cos-transmit {
          type string;
        }
        leaf set-discard-class-transmit {
          type string;
        }
        leaf set-dscp-transmit {
          type string;
        }
        leaf set-frde-transmit {
          type empty;
        }
        leaf set-mpls-exp-imposition-transmit {
          type string;
        }
        leaf set-mpls-exp-topmost-transmit {
          type string;
        }
        leaf set-prec-transmit {
          type string;
        }
        leaf set-qos-transmit {
          type string;
        }
        leaf transmit {
          type empty;
        }
        leaf drop {
          type empty;
        }
      }
    }
  }

  grouping ncs_template_police-multiple-conform-action-grouping {
    container conform-set-clp-transmit {
      container conform-action {
        leaf set-clp-transmit {
          type empty;
        }
      }
    }
    container conform-set-cos-transmit {
      container conform-action {
        leaf set-cos-transmit {
          type string;
        }
      }
    }
    container conform-set-cos-transmit-table {
      container conform-action {
        leaf set-cos-transmit {
          type string;
        }
        leaf table {
          type string;
        }
      }
    }
    container conform-set-discard-class-transmit {
      container conform-action {
        leaf set-discard-class-transmit {
          type string;
        }
      }
    }
    container conform-set-dscp-transmit {
      container conform-action {
        leaf set-dscp-transmit {
          type string;
        }
      }
    }
    container conform-set-dscp-transmit-table {
      container conform-action {
        leaf set-dscp-transmit {
          type string;
        }
        leaf table {
          type string;
        }
      }
    }
    container conform-set-frde-transmit {
      container conform-action {
        leaf set-frde-transmit {
          type empty;
        }
      }
    }
    container conform-set-mpls-exp-imposition-transmit {
      container conform-action {
        leaf set-mpls-exp-imposition-transmit {
          type string;
        }
      }
    }
    container conform-set-mpls-exp-imposition-transmit-table {
      container conform-action {
        leaf set-mpls-exp-imposition-transmit {
          type string;
        }
        leaf table {
          type string;
        }
      }
    }
    container conform-set-mpls-exp-topmost-transmit {
      container conform-action {
        leaf set-mpls-exp-topmost-transmit {
          type string;
        }
      }
    }
    container conform-set-mpls-exp-topmost-transmit-table {
      container conform-action {
        leaf set-mpls-exp-topmost-transmit {
          type string;
        }
        leaf table {
          type string;
        }
      }
    }
    container conform-set-prec-transmit {
      container conform-action {
        leaf set-prec-transmit {
          type string;
        }
      }
    }
    container conform-set-prec-transmit-table {
      container conform-action {
        leaf set-prec-transmit {
          type string;
        }
        leaf table {
          type string;
        }
      }
    }
    container conform-set-qos-transmit {
      container conform-action {
        leaf set-qos-transmit {
          type string;
        }
      }
    }
    container conform-set-qos-transmit-table {
      container conform-action {
        leaf set-qos-transmit {
          type string;
        }
        leaf table {
          type string;
        }
      }
    }
    container conform-transmit {
      container conform-action {
        uses ncs_template_police-action-transmit-grouping;
      }
    }
    container conform-drop {
      container conform-action {
        uses ncs_template_police-action-drop-grouping;
      }
    }
  }

  grouping ncs_template_police-multiple-exceed-action-grouping {
    container exceed-dscp {
      container exceed-action {
        leaf dscp {
          type string;
        }
      }
    }
    container exceed-set-clp-transmit {
      container exceed-action {
        leaf set-clp-transmit {
          type empty;
        }
      }
    }
    container exceed-set-cos-transmit {
      container exceed-action {
        leaf set-cos-transmit {
          type string;
        }
      }
    }
    container exceed-set-cos-transmit-table {
      container exceed-action {
        leaf set-cos-transmit {
          type string;
        }
        leaf table {
          type string;
        }
      }
    }
    container exceed-set-discard-class-transmit {
      container exceed-action {
        leaf set-discard-class-transmit {
          type string;
        }
      }
    }
    container exceed-set-dscp-transmit {
      container exceed-action {
        leaf set-dscp-transmit {
          type string;
        }
      }
    }
    container exceed-set-frde-transmit {
      container exceed-action {
        leaf set-frde-transmit {
          type empty;
        }
      }
    }
    container exceed-set-mpls-exp-imposition-transmit {
      container exceed-action {
        leaf set-mpls-exp-imposition-transmit {
          type string;
        }
      }
    }
    container exceed-set-mpls-exp-topmost-transmit {
      container exceed-action {
        leaf set-mpls-exp-topmost-transmit {
          type string;
        }
      }
    }
    container exceed-set-prec-transmit {
      container exceed-action {
        leaf set-prec-transmit {
          type string;
        }
      }
    }
    container exceed-set-qos-transmit {
      container exceed-action {
        leaf set-qos-transmit {
          type string;
        }
      }
    }
    container exceed-set-qos-transmit-table {
      container exceed-action {
        leaf set-qos-transmit {
          type string;
        }
        leaf table {
          type string;
        }
      }
    }
    container exceed-transmit {
      container exceed-action {
        uses ncs_template_police-action-transmit-grouping;
      }
    }
    container exceed-drop {
      container exceed-action {
        uses ncs_template_police-action-drop-grouping;
      }
    }
  }

  grouping ncs_template_police-multiple-violate-action-grouping {
    container violate-set-clp-transmit {
      container violate-action {
        leaf set-clp-transmit {
          type empty;
        }
      }
    }
    container violate-set-cos-transmit {
      container violate-action {
        leaf set-cos-transmit {
          type string;
        }
      }
    }
    container violate-set-discard-class-transmit {
      container violate-action {
        leaf set-discard-class-transmit {
          type string;
        }
      }
    }
    container violate-set-dscp-transmit {
      container violate-action {
        leaf set-dscp-transmit {
          type string;
        }
      }
    }
    container violate-set-frde-transmit {
      container violate-action {
        leaf set-frde-transmit {
          type empty;
        }
      }
    }
    container violate-set-mpls-exp-imposition-transmit {
      container violate-action {
        leaf set-mpls-exp-imposition-transmit {
          type string;
        }
      }
    }
    container violate-set-mpls-exp-topmost-transmit {
      container violate-action {
        leaf set-mpls-exp-topmost-transmit {
          type string;
        }
      }
    }
    container violate-set-prec-transmit {
      container violate-action {
        leaf set-prec-transmit {
          type string;
        }
      }
    }
    container violate-set-qos-transmit {
      container violate-action {
        leaf set-qos-transmit {
          type string;
        }
      }
    }
    container violate-transmit {
      container violate-action {
        uses ncs_template_police-action-transmit-grouping;
      }
    }
    container violate-drop {
      container violate-action {
        uses ncs_template_police-action-drop-grouping;
      }
    }
  }

  grouping ncs_template_police-action-grouping {
    container actions {
      uses ncs_template_police-multiple-conform-action-grouping;
      uses ncs_template_police-multiple-exceed-action-grouping;
      uses ncs_template_police-multiple-violate-action-grouping;
    }
  }

  grouping ncs_template_policy-map-class-grouping {
    leaf pass-through {
      type empty;
    }
    container policy {
      leaf action {
        type string;
      }
      leaf log {
        // NCS drop when statement
        type empty;
      }
      leaf parameter-map {
        // NCS drop when statement
        type string;
      }
    }
    container inspect-police {
      // NCS drop when statement
      container police {
        leaf rate {
          type string;
        }
        leaf burst {
          type string;
        }
      }
    }
    container bandwidth {
      leaf bits {
        type string;
      }
      leaf percent {
        type string;
      }
      container remaining {
        container percent {
          leaf percent {
            // NCS drop tailf-common:cli-diff-dependency statement
            type string;
          }
          uses ncs_template_bandwidth-remaining-account-grouping;
        }
        container ratio {
          leaf ratio {
            type string;
          }
          uses ncs_template_bandwidth-remaining-account-grouping;
        }
      }
    }
    container compression {
      presence "Activate Compression";
      container header {
        presence "configure header compression";
        leaf ip {
          type string;
        }
      }
    }
    leaf dbl {
      type empty;
    }
    container estimate {
      container bandwidth {
        presence "true";
        container delay-one-in {
          leaf doi {
            type string;
          }
          leaf milliseconds {
            type string;
          }
        }
        leaf drop-one-in {
          type string;
        }
      }
    }
    container fair-queue {
      presence "true";
      leaf dynamic-queues {
        type string;
      }
      leaf queue-limit {
        type string;
      }
    }
    container flow {
      leaf monitor {
        type string;
      }
    }
    leaf netflow-sampler {
      type string;
    }
    container police-aggregate {
      container police {
        leaf aggregate {
          // NCS drop tailf-common:cli-diff-dependency statement
          // NCS drop tailf-common:cli-diff-dependency statement
          type string;
        }
      }
    }
    choice police-choice {
      case police-cirmode-case {
        container police-policy-map {
          container police {
            // NCS drop when statement
            leaf cir {
              // NCS drop tailf-common:cli-diff-dependency statement
              type string;
            }
            leaf bc {
              type string;
            }
            leaf be {
              // NCS drop when statement
              type string;
            }
            leaf pir {
              type string;
            }
            container pir-be {
              // NCS drop when statement
              leaf be {
                type string;
              }
            }
            uses ncs_template_police-action-grouping;
            container conform-color {
              leaf class-map-name {
                type string;
              }
              leaf exceed-color {
                type string;
              }
            }
          }
        }
      }
      case police-cir-percent-case {
        container police-cir-percent {
          container police {
            container cir {
              container percent {
                leaf percentage {
                  type string;
                }
                leaf bc {
                  type string;
                }
                container bc-ms {
                  // NCS drop when statement
                  leaf ms {
                    type empty;
                  }
                }
                leaf be {
                  // NCS drop when statement
                  type string;
                }
                container be-ms {
                  // NCS drop when statement
                  leaf ms {
                    type empty;
                  }
                }
                container pir {
                  leaf percent {
                    type string;
                  }
                }
                container pir-be {
                  // NCS drop when statement
                  leaf be {
                    type string;
                  }
                }
                container pir-be-ms {
                  // NCS drop when statement
                  leaf ms {
                    type empty;
                  }
                }
                uses ncs_template_police-action-grouping;
              }
            }
          }
        }
      }
      case police-rate-unit-case {
        container police-rate-unit {
          container police {
            container rate {
              leaf units {
                type string;
              }
              leaf xps {
                type string;
              }
              leaf burst {
                type string;
              }
              leaf burst-type {
                // NCS drop when statement
                type string;
              }
              leaf peak-rate {
                type string;
              }
              leaf peak-rate-type {
                // NCS drop when statement
                type string;
              }
              leaf peak-burst {
                type string;
              }
              leaf peak-burst-type {
                // NCS drop when statement
                type string;
              }
              uses ncs_template_police-action-grouping;
            }
          }
        }
      }
      case police-rate-percent-case {
        container police-rate-percent {
          container police {
            container rate {
              container percent {
                leaf percentage {
                  type string;
                }
                leaf burst {
                  type string;
                }
                leaf ms {
                  // NCS drop when statement
                  type empty;
                }
                container peak-rate {
                  leaf percent {
                    type string;
                  }
                }
                leaf peak-burst {
                  type string;
                }
                container peak-burst-ms {
                  // NCS drop when statement
                  leaf ms {
                    type empty;
                  }
                }
                uses ncs_template_police-action-grouping;
              }
            }
          }
        }
      }
      case police-rate-pdp-case {
        container police-rate-pdp {
          container police {
            container rate {
              container pdp {
                leaf burst {
                  type string;
                }
                leaf peak-rate {
                  type string;
                }
                leaf peak-burst {
                  // NCS drop when statement
                  type string;
                }
                uses ncs_template_police-action-grouping;
              }
            }
          }
        }
      }
      case police-flow-case {
        container police-flow {
          container police {
            container flow {
              leaf mask {
                type string;
              }
              leaf bps {
                type string;
              }
              leaf burst-normal {
                // NCS drop when statement
                type string;
              }
              uses ncs_template_police-action-grouping;
            }
          }
        }
      }
      case police-bpsflat-case {
        container police-catalyst {
          container police {
            // NCS drop when statement
            leaf bps-value {
              type string;
            }
            leaf bps {
              // NCS drop when statement
              type empty;
            }
            leaf byte-value {
              type string;
            }
            leaf byte {
              // NCS drop when statement
              type empty;
            }
            container actions {
              uses ncs_template_police-multiple-conform-action-grouping;
              uses ncs_template_police-multiple-exceed-action-grouping;
              uses ncs_template_police-multiple-violate-action-grouping;
            }
          }
        }
      }
      case police-switch-case {
        container police-switch {
          container police {
            // NCS drop when statement
            leaf cir {
              // NCS drop tailf-common:cli-diff-dependency statement
              type string;
            }
            leaf bc {
              type string;
            }
            leaf exceed-action {
              type string;
            }
          }
        }
      }
      case police-numflat-case {
        container police-numflat {
          container police {
            // NCS drop when statement
            leaf cir {
              // NCS drop tailf-common:cli-diff-dependency statement
              type string;
            }
            leaf bc {
              type string;
            }
            leaf be {
              type string;
            }
            container actions {
              uses ncs_template_police-multiple-conform-action-grouping;
              uses ncs_template_police-multiple-exceed-action-grouping;
              uses ncs_template_police-multiple-violate-action-grouping;
            }
          }
        }
      }
      case police-cirflat-case {
        container police-cirflat {
          container police {
            // NCS drop when statement
            leaf cir {
              // NCS drop tailf-common:cli-diff-dependency statement
              type string;
            }
            leaf bc {
              type string;
            }
            leaf pir {
              type string;
            }
            leaf be {
              type string;
            }
            container actions {
              uses ncs_template_police-conform-action-grouping;
              uses ncs_template_police-exceed-action-grouping;
              uses ncs_template_police-violate-action-grouping;
            }
          }
        }
      }
    }
    container priority {
      presence "true";
      leaf level {
        type string;
      }
      choice priority-type {
        leaf kilo-bits {
          type string;
        }
        leaf percent {
          type string;
        }
      }
      leaf burst {
        type string;
      }
    }
    container shape {
      leaf adaptive {
        type string;
      }
      container average {
        choice average-choice {
          case a {
            leaf bit-rate {
              type string;
            }
            leaf bits-per-interval-sustained {
              type string;
            }
            leaf bits-per-interval-excess {
              type string;
            }
          }
          case b {
            leaf percent {
              type string;
            }
            leaf burst-size-sustained {
              type string;
            }
            leaf ms {
              type empty;
            }
            container bse {
              leaf burst-size-excess {
                type string;
              }
              leaf ms {
                type empty;
              }
            }
          }
          case c {
            leaf target-bit-rate {
              type string;
            }
            leaf account {
              type empty;
            }
            leaf user-defined {
              type string;
            }
            leaf atm {
              type empty;
            }
          }
        }
      }
      leaf fecn-adapt {
        type empty;
      }
      container fr-voice-adapt {
        presence "true";
        leaf deactivation {
          type string;
        }
      }
      leaf max-buffers {
        type string;
      }
    }
    container queue-limit {
      // NCS drop tailf-common:cli-diff-dependency statement
      choice queue-limit-choice {
        case queue-limit-percent {
          leaf percent {
            type string;
          }
        }
        case queue-limit-dscp {
          list dscp {
            // NCS patched for predictable order
            ordered-by user;
            key "dscp";
            leaf dscp {
              type string;
            }
            leaf percent {
              type string;
            }
          }
        }
        case queue-limit-value {
          leaf queue-limit-value {
            type string;
          }
          leaf queue-limit-type {
            type string;
          }
        }
      }
    }
    container random-detect {
      container base {
        leaf type {
          // NCS drop tailf-common:cli-diff-dependency statement
          type string;
        }
        leaf aggregate {
          type empty;
        }
        leaf minimum-thresh {
          type string;
        }
        leaf maximum-thresh {
          type string;
        }
        leaf mark-probability {
          type empty;
        }
        leaf denominator {
          type string;
        }
      }
      leaf exponential-weighting-constant {
        type string;
      }
      leaf ecn {
        type empty;
      }
      list cos {
        // NCS patched for predictable order
        ordered-by user;
        // NCS drop when statement
        // NCS drop tailf-common:cli-diff-dependency statement
        key "cos";
        leaf cos {
          type string;
        }
        uses ncs_template_random-detect-grouping;
      }
      list precedence {
        // NCS patched for predictable order
        ordered-by user;
        // NCS drop when statement
        // NCS drop tailf-common:cli-diff-dependency statement
        key "prec";
        leaf prec {
          type string;
        }
        uses ncs_template_random-detect-grouping;
      }
      container precedence-values {
        list precedence {
          // NCS patched for predictable order
          ordered-by user;
          // NCS drop when statement
          // NCS drop tailf-common:cli-diff-dependency statement
          key "values";
          leaf values {
            type string;
          }
          uses ncs_template_random-detect-values-grouping;
        }
      }
      list discard-class {
        // NCS patched for predictable order
        ordered-by user;
        // NCS drop when statement
        // NCS drop tailf-common:cli-diff-dependency statement
        key "dclass";
        leaf dclass {
          type string;
        }
        uses ncs_template_random-detect-grouping;
      }
      list dscp {
        // NCS patched for predictable order
        ordered-by user;
        // NCS drop when statement
        // NCS drop tailf-common:cli-diff-dependency statement
        key "dscpvalue";
        leaf dscpvalue {
          type string;
        }
        uses ncs_template_random-detect-grouping;
      }
    }
    container set {
      leaf atm-clp {
        type empty;
      }
      container cos {
        choice cos-type {
          case a {
            leaf val {
              type string;
            }
          }
          case b {
            leaf pack {
              type string;
            }
            leaf table {
              type string;
            }
          }
        }
      }
      leaf discard-class {
        type string;
      }
      container dscp {
        leaf tunnel {
          type string;
        }
        leaf value {
          type string;
        }
      }
      leaf fr-de {
        type empty;
      }
      container ip {
        choice ip-choice {
          leaf dscp {
            type string;
          }
          container precedence {
            presence "Set IP precedence";
            leaf precedence-val {
              type string;
            }
          }
        }
      }
      container mpls {
        container experimental {
          container imposition {
            leaf exp-value {
              type string;
            }
          }
          container topmost {
            leaf exp-value {
              type string;
            }
          }
        }
      }
      container qos-group {
        leaf qos-group-value {
          type string;
        }
      }
      container precedence {
        choice precedence-choice {
          case precedence-value {
            leaf precedence-value {
              type string;
            }
          }
          case precedence-from-field {
            leaf from-field {
              type string;
            }
            leaf table {
              type string;
            }
          }
        }
      }
    }
    leaf service-policy {
      type string;
    }
    leaf trust {
      type string;
    }
    container distribute {
      list service-node-group {
        // NCS patched for predictable order
        ordered-by user;
        // NCS drop max-elements statement
        key "name";
        leaf name {
          type string;
        }
      }
    }
    leaf monitor-load {
      type string;
    }
  }

  grouping ncs_template_distribute-list-content-grouping {
    leaf access-list-name {
      type string;
    }
    leaf prefix-list {
      // NCS drop tailf-common:cli-diff-dependency statement
      type string;
    }
    leaf prefix {
      // NCS drop tailf-common:cli-diff-dependency statement
      type string;
    }
    leaf gateway {
      // NCS drop tailf-common:cli-diff-dependency statement
      type string;
    }
    leaf route-map {
      type string;
    }
  }

  grouping ncs_template_redistribute-ospf-match-grouping {
    leaf match {
      type empty;
    }
    leaf internal {
      // NCS drop when statement
      type empty;
    }
    container external-1 {
      // NCS drop when statement
      leaf external {
        type string;
      }
    }
    container external-2 {
      // NCS drop when statement
      leaf external {
        type string;
      }
    }
    container nssa-external-1 {
      // NCS drop when statement
      leaf nssa-external {
        type string;
      }
    }
    container nssa-external-2 {
      // NCS drop when statement
      leaf nssa-external {
        type string;
      }
    }
  }

  grouping ncs_template_router-distribute-list-grouping {
    list distribute-list {
      // NCS patched for predictable order
      ordered-by user;
      key "direction";
      leaf direction {
        // NCS drop tailf-common:cli-diff-dependency statement
        type string;
      }
      uses ncs_template_distribute-list-content-grouping;
    }
    container distribute-list-interface {
      list distribute-list {
        // NCS patched for predictable order
        ordered-by user;
        key "direction interface";
        leaf direction {
          type string;
        }
        leaf interface {
          // NCS drop tailf-common:cli-diff-dependency statement
          type string;
        }
        uses ncs_template_distribute-list-content-grouping;
      }
    }
  }

  grouping ncs_template_router-offset-list-grouping {
    list offset-list {
      // NCS patched for predictable order
      ordered-by user;
      key "direction";
      leaf id {
        type string;
      }
      leaf direction {
        type string;
      }
      leaf offset {
        type string;
      }
    }
    container offset-list-interface {
      list offset-list {
        // NCS patched for predictable order
        ordered-by user;
        key "direction interface";
        leaf id {
          type string;
        }
        leaf direction {
          type string;
        }
        leaf offset {
          type string;
        }
        leaf interface {
          // NCS drop tailf-common:cli-diff-dependency statement
          type string;
        }
      }
    }
  }

  grouping ncs_template_passive-interface-grouping {
    container passive-interface {
      choice passive-interface-choice {
        leaf default {
          type empty;
        }
        list interface {
          // NCS patched for predictable order
          ordered-by user;
          key "name";
          leaf name {
            // NCS drop tailf-common:cli-diff-dependency statement
            type string;
          }
        }
      }
    }
    container disable {
      // NCS drop when statement
      // NCS drop tailf-common:cli-diff-dependency statement
      list passive-interface {
        // NCS patched for predictable order
        ordered-by user;
        key "interface";
        leaf interface {
          // NCS drop tailf-common:cli-diff-dependency statement
          type string;
        }
      }
    }
  }

  grouping ncs_template_ip-community-list-grouping {
    list entry {
      // NCS patched for predictable order
      ordered-by user;
      key "expr";
      leaf expr {
        type string;
      }
    }
  }

  grouping ncs_template_ip-extcommunity-list-grouping {
    list entry {
      // NCS patched for predictable order
      ordered-by user;
      key "expr";
      leaf expr {
        type string;
      }
    }
  }

  grouping ncs_template_ip-route-options-grouping {
    leaf dhcp {
      type empty;
    }
    leaf metric {
      type string;
    }
    leaf global {
      type empty;
    }
    leaf name {
      type string;
    }
    leaf permanent {
      type empty;
    }
    leaf multicast {
      type empty;
    }
    leaf tag {
      type string;
    }
    leaf track {
      type string;
    }
  }

  grouping ncs_template_ip-route-grouping {
    list ip-route-interface-forwarding-list {
      // NCS patched for predictable order
      ordered-by user;
      key "prefix mask interface forwarding-address";
      leaf prefix {
        type string;
      }
      leaf mask {
        type string;
      }
      leaf interface {
        type string;
      }
      leaf forwarding-address {
        type string;
      }
      uses ncs_template_ip-route-options-grouping;
    }
    list ip-route-forwarding-list {
      // NCS patched for predictable order
      ordered-by user;
      key "prefix mask forwarding-address";
      leaf prefix {
        type string;
      }
      leaf mask {
        type string;
      }
      leaf forwarding-address {
        type string;
      }
      uses ncs_template_ip-route-options-grouping;
    }
    list ip-route-interface-list {
      // NCS patched for predictable order
      ordered-by user;
      key "prefix mask interface";
      leaf prefix {
        type string;
      }
      leaf mask {
        type string;
      }
      leaf interface {
        type string;
      }
      uses ncs_template_ip-route-options-grouping;
    }
  }

  grouping ncs_template_ipv6-route-options-grouping {
    leaf distance {
      type string;
    }
    choice type-choice {
      leaf multicast {
        type empty;
      }
      leaf unicast {
        type empty;
      }
    }
    leaf tag {
      type string;
    }
  }

  grouping ncs_template_ipv6-route-grouping {
    list ipv6-route-interface-destination-list {
      // NCS patched for predictable order
      ordered-by user;
      key "prefix interface destination";
      leaf prefix {
        type string;
      }
      leaf interface {
        // NCS drop tailf-common:cli-diff-dependency statement
        type string;
      }
      leaf destination {
        type string;
      }
      uses ncs_template_ipv6-route-options-grouping;
    }
    list ipv6-route-destination-list {
      // NCS patched for predictable order
      ordered-by user;
      key "prefix destination";
      leaf prefix {
        type string;
      }
      leaf destination {
        type string;
      }
      uses ncs_template_ipv6-route-options-grouping;
    }
    list ipv6-route-interface-list {
      // NCS patched for predictable order
      ordered-by user;
      key "prefix interface";
      leaf prefix {
        type string;
      }
      leaf interface {
        // NCS drop tailf-common:cli-diff-dependency statement
        type string;
      }
      uses ncs_template_ipv6-route-options-grouping;
    }
  }

  grouping ncs_template_random-detect-grouping {
    leaf min-threshold {
      type string;
    }
    leaf min-threshold-unit {
      type string;
    }
    leaf max-threshold {
      type string;
    }
    leaf max-threshold-unit {
      type string;
    }
    leaf denominator {
      type string;
    }
  }

  grouping ncs_template_random-detect-values-grouping {
    leaf minimum-thresh {
      type string;
    }
    leaf maximum-thresh {
      type string;
    }
    leaf mark-prob {
      type string;
    }
  }

  grouping ncs_template_class-map-match-grouping {
    container access-group {
      leaf-list index {
        // NCS patched for predictable order
        ordered-by user;
        type string;
      }
      leaf-list name {
        // NCS patched for predictable order
        ordered-by user;
        type string;
      }
    }
    leaf any {
      type empty;
    }
    leaf-list class-map {
      // NCS patched for predictable order
      ordered-by user;
      type string;
    }
    leaf-list cos {
      // NCS patched for predictable order
      ordered-by user;
      // NCS drop max-elements statement
      type string;
    }
    container cos-inner {
      container cos {
        leaf-list inner {
          // NCS patched for predictable order
          ordered-by user;
          // NCS drop max-elements statement
          type string;
        }
      }
    }
    container destination-address {
      leaf-list mac {
        // NCS patched for predictable order
        ordered-by user;
        type string;
      }
    }
    leaf-list discard-class {
      // NCS patched for predictable order
      ordered-by user;
      type string;
    }
    leaf-list dscp {
      // NCS patched for predictable order
      ordered-by user;
      type string;
    }
    leaf fr-de {
      type empty;
    }
    leaf-list fr-dlci {
      // NCS patched for predictable order
      ordered-by user;
      type string;
    }
    leaf-list input-interface {
      // NCS patched for predictable order
      ordered-by user;
      type string;
    }
    container ip {
      leaf-list dscp {
        // NCS patched for predictable order
        ordered-by user;
        type string;
      }
      leaf-list precedence {
        // NCS patched for predictable order
        ordered-by user;
        type string;
      }
      list rtp {
        // NCS patched for predictable order
        ordered-by user;
        key "port1 port2";
        leaf port1 {
          type string;
        }
        leaf port2 {
          type string;
        }
      }
    }
    container mpls {
      container experimental {
        leaf-list topmost {
          // NCS patched for predictable order
          ordered-by user;
          type string;
        }
      }
    }
    leaf-list precedence {
      // NCS patched for predictable order
      ordered-by user;
      type string;
    }
    container protocol {
      container attribute {
        list category {
          // NCS patched for predictable order
          ordered-by user;
          key "category-type";
          leaf category-type {
            type string;
          }
        }
        list traffic-class {
          // NCS patched for predictable order
          ordered-by user;
          key "traffic-class-type";
          leaf traffic-class-type {
            type string;
          }
        }
        list business-relevance {
          // NCS patched for predictable order
          ordered-by user;
          key "business-relevance-type";
          leaf business-relevance-type {
            type string;
          }
        }
      }
      list protocol-list {
        // NCS patched for predictable order
        ordered-by user;
        key "name";
        leaf name {
          type string;
        }
        list values {
          // NCS patched for predictable order
          ordered-by user;
          key "value";
          leaf value {
            type string;
          }
        }
      }
    }
    container packet {
      list length {
        // NCS patched for predictable order
        ordered-by user;
        key "line";
        leaf line {
          type string;
        }
      }
    }
    leaf-list qos-group {
      // NCS patched for predictable order
      ordered-by user;
      type string;
    }
    container source-address {
      leaf-list mac {
        // NCS patched for predictable order
        ordered-by user;
        type string;
      }
    }
    leaf-list vlan {
      // NCS patched for predictable order
      ordered-by user;
      type string;
    }
    container service {
      container instance {
        leaf-list ethernet {
          // NCS patched for predictable order
          ordered-by user;
          type string;
        }
      }
    }
  }

  grouping ncs_template_ip-name-server-grouping {
    list name-server-list {
      // NCS patched for predictable order
      ordered-by user;
      // NCS drop max-elements statement
      key "address";
      leaf address {
        type string;
      }
    }
  }

  grouping ncs_template_ip-host-grouping {
    list host-list {
      // NCS patched for predictable order
      ordered-by user;
      key "hostname";
      leaf hostname {
        type string;
      }
      leaf tcp-port-number {
        type string;
      }
      leaf-list ip-address1 {
        // NCS patched for predictable order
        ordered-by user;
        type string;
      }
    }
  }

  grouping ncs_template_ip-dhcp-excluded-address-grouping {
    list low-list {
      // NCS patched for predictable order
      ordered-by user;
      key "low";
      leaf low {
        type string;
      }
    }
    list low-high-list {
      // NCS patched for predictable order
      ordered-by user;
      key "low high";
      leaf low {
        type string;
      }
      leaf high {
        type string;
      }
    }
  }

  grouping ncs_template_ntp-peer-grouping {
    list peer-list {
      // NCS patched for predictable order
      ordered-by user;
      key "name";
      leaf name {
        type string;
      }
      leaf burst {
        type empty;
      }
      leaf iburst {
        type empty;
      }
      leaf key {
        type string;
      }
      leaf maxpoll {
        type string;
      }
      leaf minpoll {
        type string;
      }
      leaf normal-sync {
        type empty;
      }
      leaf prefer {
        type empty;
      }
      container source {
        uses ncs_template_interface-name-grouping;
      }
      leaf version {
        type string;
      }
    }
  }

  grouping ncs_template_sntp-server-grouping {
    list server-list {
      // NCS patched for predictable order
      ordered-by user;
      key "name";
      leaf name {
        type string;
      }
      leaf key {
        type string;
      }
      leaf version {
        type string;
      }
    }
  }

  grouping ncs_template_line-grouping {
    leaf location {
      type string;
    }
    leaf absolute-timeout {
      type string;
    }
    container access-class {
      list access-list {
        // NCS patched for predictable order
        ordered-by user;
        key "direction";
        leaf direction {
          type string;
        }
        leaf access-list {
          type string;
        }
        leaf vrf-also {
          type empty;
        }
      }
    }
    leaf flush-at-activation {
      type string;
      // NCS drop default statement
    }
    container activation-character-choice {
      choice activation-character-choice {
        leaf activation-character {
          type string;
          // NCS drop default statement
        }
        container activation-character-conf {
          leaf activation-character {
            type string;
          }
        }
      }
    }
    leaf escape-character {
      type string;
    }
    container script {
      leaf dialer {
        type string;
      }
    }
    container modem {
      leaf enable {
        type string;
      }
      leaf InOut {
        type empty;
      }
      container autoconfigure {
        leaf discovery {
          type empty;
        }
        leaf type {
          type string;
        }
      }
    }
    container exec-choice {
      choice exec-choice {
        // NCS drop default statement
        leaf exec {
          type string;
          // NCS drop default statement
        }
        container exec-conf {
          container exec {
            container prompt {
              leaf timestamp {
                type empty;
              }
            }
          }
        }
      }
    }
    container exec-timeout {
      leaf minutes {
        type string;
      }
      leaf seconds {
        type string;
      }
    }
    container timeout {
      container login {
        leaf response {
          type string;
        }
      }
    }
    container session-disconnect-warning {
      leaf seconds {
        type string;
      }
      leaf message {
        type string;
      }
    }
    container logging {
      container synchronous {
        presence "true";
        leaf level {
          type string;
        }
      }
    }
    leaf rotary {
      type string;
    }
    container login {
      presence "true";
      leaf local {
        type empty;
      }
    }
    container local-authentication {
      container login {
        leaf tacacs {
          type empty;
        }
        leaf authentication {
          type string;
          // NCS drop default statement
        }
      }
    }
    container autocommand {
      leaf command {
        type string;
      }
    }
    container accounting {
      leaf exec {
        type string;
        // NCS drop default statement
      }
      list commands {
        // NCS patched for predictable order
        ordered-by user;
        key "level";
        leaf level {
          type string;
        }
        leaf name {
          type string;
          // NCS drop default statement
        }
      }
    }
    leaf logout-warning {
      type string;
    }
    container ipv6 {
      list access-class {
        // NCS patched for predictable order
        ordered-by user;
        key "direction";
        leaf direction {
          type string;
        }
        leaf access-list {
          type string;
        }
      }
    }
    container authorization {
      leaf exec {
        type string;
        // NCS drop default statement
      }
      list commands {
        // NCS patched for predictable order
        ordered-by user;
        key "level";
        leaf level {
          type string;
        }
        leaf name {
          type string;
          // NCS drop default statement
        }
      }
    }
    container history {
      leaf size {
        type string;
      }
    }
    leaf full-help {
      type empty;
    }
    container password {
      uses ncs_template_password-grouping;
    }
    container privilege {
      leaf level {
        type string;
      }
    }
    container session-timeout {
      leaf session-timeout-value {
        type string;
      }
      leaf output {
        type empty;
      }
    }
    leaf stopbits {
      type string;
    }
    container telnet {
      leaf transparent {
        type empty;
      }
    }
    container transport {
      leaf-list input {
        // NCS patched for predictable order
        ordered-by user;
        type string;
      }
      leaf-list output {
        // NCS patched for predictable order
        ordered-by user;
        type string;
      }
      leaf preferred {
        type string;
      }
    }
    leaf speed {
      type string;
    }
    leaf rxspeed {
      type string;
    }
    leaf txspeed {
      type string;
    }
    leaf flowcontrol {
      type string;
    }
    leaf length {
      type string;
    }
    leaf width {
      type string;
    }
  }

  grouping ncs_template_queue-size-grouping {
    leaf queue-size-1 {
      type string;
    }
    leaf queue-size-2 {
      type string;
    }
    leaf queue-size-3 {
      type string;
    }
    leaf queue-size-4 {
      type string;
    }
    leaf queue-size-5 {
      type string;
    }
    leaf queue-size-6 {
      type string;
    }
    leaf queue-size-7 {
      type string;
    }
    leaf queue-size-8 {
      type string;
    }
  }

  grouping ncs_template_interface-common-pre-grouping {
    leaf mac-address {
      type string;
    }
    leaf description {
      type string;
    }
    container backup {
      container interface {
        uses ncs_template_interface-name-grouping;
      }
    }
    list glbp {
      // NCS patched for predictable order
      ordered-by user;
      key "group-number";
      leaf group-number {
        type string;
      }
      leaf ip {
        type string;
      }
      container ip-secondary-list {
        list ip {
          // NCS patched for predictable order
          ordered-by user;
          key "address";
          leaf address {
            type string;
          }
          leaf secondary {
            type empty;
          }
        }
      }
      leaf priority {
        type string;
      }
      container preempt {
        presence "true";
        container delay {
          leaf minimum {
            type string;
          }
        }
      }
    }
  }

  grouping ncs_template_interface-ospfv3-grouping {
    container area {
      leaf id {
        type string;
      }
      leaf instance {
        type string;
      }
    }
    leaf priority {
      type string;
    }
    container authentication {
      choice authentication-choice {
        leaf key-chain {
          type string;
        }
        leaf null {
          type empty;
        }
      }
    }
  }

  grouping ncs_template_interface-common-grouping0 {
    container arp {
      leaf timeout {
        type string;
      }
      leaf frame-relay {
        type string;
      }
    }
    container authentication {
      container event {
        container server {
          container dead {
            container action {
              container authorize {
                leaf vlan {
                  type string;
                }
              }
            }
          }
        }
        container no-response {
          container action {
            container authorize {
              leaf vlan {
                type string;
              }
            }
          }
        }
      }
      leaf host-mode {
        type string;
      }
      container order {
        leaf dot1x {
          type string;
        }
      }
      container priority {
        leaf dot1x {
          type string;
        }
      }
      leaf port-control {
        type string;
      }
      leaf periodic {
        type empty;
      }
      container timer {
        leaf reauthenticate {
          type string;
        }
      }
    }
    container access-session {
      leaf closed {
        type empty;
      }
      leaf port-control {
        type string;
        // NCS drop default statement
      }
    }
    container mab {
      presence "true";
      leaf eap {
        type empty;
      }
    }
    leaf medium {
      type string;
    }
    container frame-relay {
      container multilink {
        leaf output-threshold {
          type string;
        }
        container bid {
          leaf bid {
            type string;
          }
        }
      }
      leaf lmi-type {
        type string;
      }
      leaf intf-type {
        type string;
      }
      container interface-dlci {
        leaf dlci {
          type string;
        }
        leaf encapsulation {
          type string;
        }
        leaf class {
          type string;
        }
      }
    }
    container fair-queue {
      presence "true";
      leaf congestive-discard-threshold {
        type string;
      }
      leaf dynamic-queues {
        type string;
      }
      leaf reservable-queues {
        type string;
      }
    }
    container flowcontrol {
      leaf bidirectional {
        type string;
        // NCS drop default statement
      }
      leaf receive {
        type string;
      }
      leaf send {
        type string;
      }
    }
    container traffic-shape {
      container rate {
        leaf bit-rate {
          // NCS drop tailf-common:cli-diff-dependency statement
          type string;
        }
        leaf burst-size {
          type string;
        }
        leaf excess-burst-size {
          type string;
        }
        leaf max-buffers {
          type string;
        }
      }
      list group {
        // NCS patched for predictable order
        ordered-by user;
        key "access-list";
        leaf access-list {
          // NCS drop tailf-common:cli-diff-dependency statement
          type string;
        }
        leaf bit-rate {
          type string;
        }
        leaf burst-size {
          type string;
        }
        leaf excess-burst-size {
          type string;
        }
        leaf max-buffers {
          type string;
        }
      }
    }
    choice keepalive-choice {
      leaf keepalive {
        type string;
        // NCS drop default statement
      }
      container keepalive-period {
        leaf keepalive {
          type string;
          // NCS drop default statement
        }
      }
      container keepalive-period-retries {
        container keepalive {
          leaf period {
            type string;
          }
          leaf retries {
            type string;
          }
        }
      }
    }
    container snmp {
      container ifindex {
        leaf persist {
          type empty;
        }
      }
      container trap {
        leaf link-status {
          type string;
          // NCS drop default statement
        }
        container link-status-capas {
          container link-status {
            container permit {
              leaf duplicates {
                type empty;
              }
            }
          }
        }
        container mac-notification {
          container change {
            leaf added {
              type empty;
            }
            leaf removed {
              type empty;
            }
          }
        }
      }
    }
    container flow-sampler {
      leaf name {
        type string;
      }
      container egress {
        leaf name {
          type string;
        }
        leaf egress {
          type empty;
        }
      }
    }
    container lldp {
      leaf transmit {
        type string;
        // NCS drop default statement
      }
      leaf receive {
        type string;
        // NCS drop default statement
      }
    }
    container bfd {
      container interval {
        leaf msecs {
          type string;
        }
        leaf min_rx {
          type string;
        }
        leaf multiplier {
          type string;
        }
      }
      leaf echo {
        type string;
        // NCS drop default statement
      }
      leaf template {
        type string;
      }
    }
    container bandwidth {
      leaf inherit {
        type empty;
      }
      leaf kilobits {
        type string;
      }
    }
    container cdp {
      leaf enable {
        type string;
        // NCS drop default statement
      }
      container tlv {
        container app {
          presence "true";
          leaf tlvtype {
            type string;
          }
          leaf value {
            type string;
          }
        }
        leaf server-location {
          type empty;
        }
        leaf location {
          type empty;
        }
      }
    }
    container mop {
      leaf xenabled {
        tailf:alt-name "enabled";
        type string;
        // NCS drop default statement
      }
      leaf sysid {
        type string;
        // NCS drop default statement
      }
    }
    container dampening {
      presence "true";
      leaf dampening-time {
        type string;
      }
    }
    list vlan-range {
      // NCS patched for predictable order
      ordered-by user;
      key "id";
      leaf id {
        type string;
      }
      container service-policy {
        uses ncs_template_service-policy-grouping;
      }
    }
    list hold-queue {
      // NCS patched for predictable order
      ordered-by user;
      key "direction";
      leaf direction {
        type string;
      }
      leaf queue-length {
        type string;
      }
    }
    container mpls {
      container accounting {
        container experimental {
          leaf input {
            type empty;
          }
          leaf output {
            type empty;
          }
        }
      }
      container bgp {
        leaf forwarding {
          type empty;
        }
      }
      container label {
        leaf protocol {
          type string;
        }
      }
      container ldp {
        container igp {
          choice sync-choice {
            leaf sync {
              type string;
              // NCS drop default statement
            }
            container sync-delay {
              container sync {
                leaf delay {
                  type string;
                }
              }
            }
          }
        }
        container discovery {
          leaf transport-address {
            type string;
          }
        }
      }
      leaf mtu {
        type string;
        // NCS drop default statement
      }
      container traffic-eng {
        leaf administrative-weight {
          type string;
        }
        leaf backup-path {
          type string;
        }
        leaf attribute-flags {
          type string;
        }
        container flooding {
          container thresholds {
            leaf-list down {
              // NCS patched for predictable order
              ordered-by user;
              type string;
            }
            leaf-list up {
              // NCS patched for predictable order
              ordered-by user;
              type string;
            }
          }
        }
        leaf tunnels {
          type empty;
        }
      }
      leaf ip {
        type empty;
      }
      leaf propagate-cos {
        type empty;
      }
    }
    container isis {
      container bfd {
        presence "true";
        leaf disable {
          type empty;
        }
      }
      leaf tag {
        type string;
      }
      leaf circuit-type {
        type string;
        // NCS drop default statement
      }
      leaf network {
        type string;
      }
      choice metric-choice {
        case default-case {
          leaf metric {
            type string;
          }
        }
        case level-case {
          container metric-level {
            list metric {
              // NCS patched for predictable order
              ordered-by user;
              key "level";
              leaf level {
                type string;
              }
              leaf default {
                type string;
              }
            }
          }
        }
      }
      uses ncs_template_router-isis-interface-grouping;
      container ipv6 {
        // NCS drop tailf-common:cli-diff-dependency statement
        choice metric-choice {
          leaf metric {
            type string;
          }
          container metric-level {
            list metric {
              // NCS patched for predictable order
              ordered-by user;
              key "level";
              leaf level {
                type string;
              }
              leaf value {
                type string;
              }
            }
          }
        }
      }
      leaf three-way-handshake {
        // NCS drop tailf-common:cli-diff-dependency statement
        type string;
        // NCS drop default statement
      }
      choice priority-choice {
        leaf priority {
          type string;
        }
        container priority-level-1-2 {
          list priority {
            // NCS patched for predictable order
            ordered-by user;
            key "level";
            leaf level {
              type string;
            }
            leaf priority {
              type string;
            }
          }
        }
      }
      container hello-multiplier {
        leaf seconds {
          type string;
        }
      }
      container hello-interval {
        choice hello-interval-choice {
          leaf seconds {
            type string;
          }
          leaf minimal {
            type empty;
          }
        }
      }
      choice csnp-interval-choice {
        leaf csnp-interval {
          type string;
        }
        container csnp-interval-level {
          list csnp-interval {
            // NCS patched for predictable order
            ordered-by user;
            key "level";
            leaf level {
              type string;
            }
            leaf seconds {
              type string;
            }
          }
        }
      }
      choice password-choice {
        leaf password {
          type string;
        }
        container password-level-1-2 {
          list password {
            // NCS patched for predictable order
            ordered-by user;
            key "level";
            leaf password {
              type string;
            }
            leaf level {
              type string;
            }
          }
        }
      }
    }
    choice vrf-choice {
      container ip-vrf {
        container ip {
          container vrf {
            leaf forwarding {
              // NCS drop tailf-common:cli-diff-dependency statement
              type string;
            }
          }
        }
      }
      container vrf {
        leaf forwarding {
          // NCS drop tailf-common:cli-diff-dependency statement
          type string;
        }
      }
    }
    container pm-path {
      // NCS drop tailf-common:cli-diff-dependency statement
      leaf name {
        type string;
      }
      leaf interface-id {
        type string;
      }
    }
    container ip {
      list access-group {
        // NCS patched for predictable order
        ordered-by user;
        key "direction";
        leaf direction {
          type string;
        }
        leaf access-list {
          // NCS drop tailf-common:cli-diff-dependency statement
          type string;
        }
      }
      container authentication {
        container mode {
          list eigrp {
            // NCS patched for predictable order
            ordered-by user;
            key "as-no";
            leaf as-no {
              type string;
            }
            leaf md5 {
              type empty;
            }
          }
        }
        container key-chain {
          list eigrp {
            // NCS patched for predictable order
            ordered-by user;
            key "as-no";
            leaf as-no {
              type string;
            }
            leaf key-chain {
              type string;
            }
          }
        }
      }
      container accounting {
        presence "true";
        leaf output-packets {
          type empty;
        }
        container precedence {
          leaf input {
            type empty;
          }
          leaf output {
            type empty;
          }
        }
        leaf access-violations {
          type empty;
        }
      }
      container vrf {
        leaf receive {
          type string;
        }
        leaf sitemap {
          type string;
        }
      }
      container arp {
        container inspection {
          leaf trust {
            type empty;
          }
          container limit {
            choice limit-choice {
              leaf none {
                type empty;
              }
              leaf rate {
                type string;
              }
            }
            container burst {
              leaf interval {
                type string;
              }
            }
          }
        }
      }
      choice address-choice {
        container unnumbered {
          uses ncs_template_interface-name-grouping;
        }
        container no-address {
          leaf address {
            type string;
            // NCS drop default statement
          }
        }
        container address {
          choice address-choice {
            case fixed-case {
              container primary {
                // NCS drop tailf-common:cli-diff-dependency statement
                leaf address {
                  type string;
                }
                leaf mask {
                  type string;
                }
              }
              list secondary {
                // NCS patched for predictable order
                ordered-by user;
                // NCS drop tailf-common:cli-diff-dependency statement
                key "address mask";
                leaf address {
                  type string;
                }
                leaf mask {
                  type string;
                }
                leaf secondary {
                  type empty;
                }
              }
            }
            case dhcp-case {
              container dhcp {
                presence "true";
                container client-id {
                  uses ncs_template_interface-name-grouping;
                }
                leaf hostname {
                  type string;
                }
              }
            }
            case negotiated-case {
              container negotiated {
                presence "true";
                leaf previous {
                  type empty;
                }
              }
            }
          }
        }
      }
      container directed-broadcast {
        presence "true";
        leaf access-list {
          type string;
        }
      }
      container split-horizon-eigrp {
        container split-horizon {
          container eigrp {
            list no-list {
              // NCS patched for predictable order
              ordered-by user;
              key "as-no";
              leaf as-no {
                type string;
              }
            }
          }
        }
      }
      leaf split-horizon {
        type string;
        // NCS drop default statement
      }
      container router {
        container isis {
          presence "true";
          leaf tag {
            type string;
          }
        }
      }
      container flow {
        leaf ingress {
          type empty;
        }
        leaf egress {
          type empty;
        }
        list monitor {
          // NCS patched for predictable order
          ordered-by user;
          key "direction";
          leaf direction {
            type string;
          }
          leaf name {
            type string;
          }
        }
      }
      container helper-address {
        list helper-address-list {
          // NCS patched for predictable order
          ordered-by user;
          key "address";
          leaf address {
            type string;
          }
        }
        list vrf {
          // NCS patched for predictable order
          ordered-by user;
          key "vrf address";
          leaf vrf {
            type string;
          }
          leaf address {
            type string;
          }
        }
      }
      container summary-address {
        list eigrp {
          // NCS patched for predictable order
          ordered-by user;
          key "as-no ip-address wildcard-mask";
          leaf as-no {
            type string;
          }
          leaf ip-address {
            type string;
          }
          leaf wildcard-mask {
            type string;
          }
          leaf distance {
            type string;
          }
        }
      }
      container ospf {
        list process-id {
          // NCS patched for predictable order
          ordered-by user;
          key "id";
          leaf id {
            type string;
          }
          leaf area {
            type string;
          }
          leaf secondaries {
            type empty;
          }
          leaf none {
            type empty;
          }
        }
        container authentication {
          presence "true";
          choice authentication-choice {
            leaf message-digest {
              type empty;
            }
            leaf null {
              type empty;
            }
            leaf key-chain {
              type string;
            }
          }
        }
        container authentication-key {
          uses ncs_template_password-grouping;
        }
        list message-digest-key {
          // NCS patched for predictable order
          ordered-by user;
          key "id";
          leaf id {
            type string;
          }
          container md5 {
            uses ncs_template_password-grouping;
          }
        }
        leaf-list network {
          // NCS patched for predictable order
          ordered-by user;
          // NCS drop max-elements statement
          type string;
        }
        leaf hello-interval {
          type string;
        }
        container dead-interval {
          choice dead-interva-choice {
            leaf seconds {
              type string;
            }
            case minimal {
              leaf minimal {
                type empty;
              }
              leaf hello-multiplier {
                type string;
              }
            }
          }
        }
        container bfd {
          presence "true";
          leaf enable {
            type string;
          }
        }
        leaf mtu-ignore {
          type empty;
        }
        leaf cost {
          type string;
        }
        container ttl-security {
          presence "true";
          leaf hops {
            type string;
          }
        }
        leaf priority {
          type string;
        }
        container lls {
          presence "true";
          leaf disable {
            type empty;
          }
        }
        container database-filter {
          container all {
            leaf out {
              type empty;
            }
          }
        }
      }
      container pim {
        leaf query-interval {
          type string;
          // NCS drop default statement
        }
        leaf nbma-mode {
          type empty;
        }
        leaf mode {
          type string;
        }
        leaf dr-priority {
          type string;
        }
        leaf snooping {
          type empty;
        }
        leaf passive {
          type empty;
        }
      }
      container multicast {
        container boundary {
          leaf access-list {
            type string;
          }
          leaf filter-autorp {
            type empty;
          }
        }
        container limit {
          list access-lists {
            // NCS patched for predictable order
            ordered-by user;
            key "access-list";
            leaf access-list {
              type string;
            }
            leaf allowed-state {
              type string;
            }
          }
          list connected {
            // NCS patched for predictable order
            ordered-by user;
            key "access-list";
            leaf access-list {
              type string;
            }
            leaf allowed-state {
              type string;
            }
          }
          list out {
            // NCS patched for predictable order
            ordered-by user;
            key "access-list";
            leaf access-list {
              type string;
            }
            leaf allowed-state {
              type string;
            }
          }
          list rpf {
            // NCS patched for predictable order
            ordered-by user;
            key "access-list";
            leaf access-list {
              type string;
            }
            leaf allowed-state {
              type string;
            }
          }
        }
      }
      container policy {
        leaf route-map {
          type string;
        }
      }
      leaf unreachables {
        type string;
        // NCS drop default statement
      }
      leaf proxy-arp {
        type string;
        // NCS drop default statement
      }
      container route-cache-conf {
        leaf route-cache {
          type string;
          // NCS drop default statement
        }
      }
      container route-cache {
        leaf cef {
          type string;
          // NCS drop default statement
        }
        leaf flow {
          type string;
          // NCS drop default statement
        }
        leaf policy {
          type string;
          // NCS drop default statement
        }
        leaf same-interface {
          type string;
          // NCS drop default statement
        }
      }
      leaf mroute-cache {
        type string;
        // NCS drop default statement
      }
      container igmp {
        container max-groups {
          leaf number {
            type string;
          }
          leaf action {
            type string;
            // NCS drop default statement
          }
        }
        leaf filter {
          type string;
        }
        list join-group {
          // NCS patched for predictable order
          ordered-by user;
          key "address";
          leaf address {
            type string;
          }
          leaf source {
            type string;
          }
        }
        container static-group {
          list groups {
            // NCS patched for predictable order
            ordered-by user;
            key "name";
            leaf name {
              type string;
            }
          }
          list class-map {
            // NCS patched for predictable order
            ordered-by user;
            key "id";
            leaf id {
              type string;
            }
          }
        }
        leaf version {
          type string;
        }
        leaf access-group {
          type string;
        }
      }
      leaf redirects {
        type string;
        // NCS drop default statement
      }
      container hello-interval {
        list eigrp {
          // NCS patched for predictable order
          ordered-by user;
          key "as-number";
          leaf as-number {
            type string;
          }
          leaf seconds {
            type string;
          }
        }
      }
      container hold-time {
        list eigrp {
          // NCS patched for predictable order
          ordered-by user;
          key "as-number";
          leaf as-number {
            type string;
          }
          leaf seconds {
            type string;
          }
        }
      }
      container nbar {
        leaf protocol-discovery {
          type empty;
        }
      }
      container nhrp {
        leaf authentication {
          type string;
        }
        leaf group {
          type string;
        }
        container map {
          list map-list {
            // NCS patched for predictable order
            ordered-by user;
            key "ip-address";
            leaf ip-address {
              type string;
            }
            leaf nbma-address {
              type string;
            }
          }
          container multicast {
            leaf dynamic {
              type empty;
            }
            list multicast-list {
              // NCS patched for predictable order
              ordered-by user;
              key "nbma-address";
              leaf nbma-address {
                type string;
              }
            }
          }
          list group {
            // NCS patched for predictable order
            ordered-by user;
            key "name";
            leaf name {
              type string;
            }
            container service-policy {
              leaf output {
                type string;
              }
            }
          }
        }
        leaf network-id {
          type string;
        }
        leaf holdtime {
          type string;
        }
        container nhs {
          list nhs-list {
            // NCS patched for predictable order
            ordered-by user;
            key "nhs-address";
            leaf nhs-address {
              type string;
            }
            leaf nbma {
              type string;
            }
            leaf multicast {
              // NCS drop when statement
              type empty;
            }
          }
        }
        container server-only {
          presence "true";
          leaf non-caching {
            type empty;
          }
        }
        container registration {
          leaf no-unique {
            type empty;
          }
          leaf timeout {
            type string;
          }
        }
        container shortcut {
          presence "true";
          leaf virtual-template {
            type string;
          }
        }
        container redirect {
          presence "true";
          leaf timeout {
            type string;
          }
        }
      }
      container tcp {
        leaf adjust-mss {
          type string;
        }
        container header-compression {
          presence "true";
          leaf type {
            type string;
          }
        }
        leaf compression-connections {
          type string;
        }
      }
      container rtp {
        container header-compression {
          leaf type {
            type string;
          }
          leaf periodic-refresh {
            type empty;
          }
        }
        leaf compression-connections {
          type string;
        }
      }
      container header-compression {
        leaf max-header {
          type string;
        }
      }
      container mobile {
        container router-service {
          container roam {
            presence "true";
            leaf priority {
              type string;
            }
          }
          leaf description {
            type string;
          }
          leaf link-type {
            type string;
          }
          container tunnel {
            leaf mode {
              type string;
            }
          }
          container collocated {
            leaf gateway {
              type string;
            }
            leaf ccoa-only {
              type empty;
            }
            container registration {
              leaf retry {
                type string;
                // NCS drop default statement
              }
              container nat {
                container traversal {
                  presence "true";
                  leaf keepalive {
                    type string;
                  }
                  leaf force {
                    type empty;
                  }
                }
              }
            }
            leaf encapsulation {
              type string;
            }
          }
        }
      }
      list inspect {
        // NCS patched for predictable order
        ordered-by user;
        key "direction";
        leaf direction {
          type string;
        }
        leaf name {
          type string;
        }
      }
      container virtual-reassembly {
        presence "true";
        leaf in {
          type empty;
        }
        leaf out {
          type empty;
        }
        container conf {
          leaf drop-fragments {
            type empty;
          }
          leaf max-fragments {
            type string;
          }
          leaf max-reassemblies {
            type string;
          }
          leaf timeout {
            type string;
          }
          leaf percentage {
            type string;
          }
          leaf-list dscp {
            // NCS patched for predictable order
            ordered-by user;
            type string;
          }
          leaf-list precedence {
            // NCS patched for predictable order
            ordered-by user;
            type string;
          }
        }
      }
      container dns {
        leaf view-group {
          type string;
        }
      }
      container dhcp {
        container relay {
          container information {
            container check-reply {
              presence "true";
              leaf none {
                type empty;
              }
            }
            container option {
              leaf subscriber-id {
                type string;
              }
            }
            container option-insert {
              presence "true";
              leaf none {
                type empty;
              }
            }
            leaf policy-action {
              type string;
            }
            leaf trusted {
              type empty;
            }
          }
        }
        container snooping {
          container limit {
            leaf rate {
              type string;
            }
          }
          leaf trust {
            type empty;
          }
          list vlan {
            // NCS patched for predictable order
            ordered-by user;
            key "id";
            leaf id {
              type string;
            }
            container information {
              container option {
                container format-type {
                  container circuit-id {
                    leaf string {
                      type string;
                    }
                  }
                }
              }
            }
          }
          list bridge-domain {
            // NCS patched for predictable order
            ordered-by user;
            key "id";
            leaf id {
              type string;
            }
            container information {
              container option {
                container format-type {
                  container circuit-id {
                    leaf string {
                      type string;
                    }
                  }
                }
              }
            }
          }
        }
      }
      leaf mtu {
        type string;
      }
      container nat {
        leaf allow-static-host {
          type empty;
        }
        leaf enable {
          type empty;
        }
        choice nat-choice {
          leaf inside {
            type empty;
          }
          leaf outside {
            type empty;
          }
        }
      }
      container rsvp {
        container bandwidth {
          presence "true";
          leaf interface-bandwidth {
            type string;
          }
          leaf single-flow-bandwidth {
            type string;
          }
        }
        container signalling {
          container hello {
            presence "true";
            container graceful-restart {
              presence "true";
            }
          }
        }
        container resource-provider {
          choice resource-provider-choice {
            leaf none {
              type empty;
            }
            leaf wfq {
              type string;
            }
          }
        }
      }
      container verify {
        container unicast {
          container reverse-path {
            presence "true";
          }
          container source {
            leaf reachable-via {
              type string;
            }
            leaf allow-self-ping {
              type empty;
            }
            leaf allow-default {
              type empty;
            }
            leaf access-list {
              type string;
            }
          }
        }
        container source {
          presence "true";
          container vlan {
            container dhcp-snooping {
              presence "true";
              leaf port-security {
                type empty;
              }
            }
          }
        }
      }
      container rip {
        container send {
          leaf version {
            type string;
          }
        }
        container receive {
          leaf version {
            type string;
          }
        }
        container authentication {
          leaf mode {
            type string;
          }
          leaf key-chain {
            type string;
          }
        }
      }
      leaf mask-reply {
        type empty;
      }
      container bandwidth-percent {
        list eigrp {
          // NCS patched for predictable order
          ordered-by user;
          key "as-number";
          leaf as-number {
            type string;
          }
          leaf percent {
            type string;
          }
        }
      }
      container next-hop-self {
        container eigrp {
          list no-list {
            // NCS patched for predictable order
            ordered-by user;
            key "as-number";
            leaf as-number {
              type string;
            }
          }
        }
      }
      container lisp {
        container source-locator {
          uses ncs_template_interface-name-grouping;
        }
      }
      container wccp {
        // NCS drop tailf-common:cli-diff-dependency statement
        uses ncs_template_interface-ip-wccp-grouping;
        list vrf {
          // NCS patched for predictable order
          ordered-by user;
          key "name";
          leaf name {
            // NCS drop tailf-common:cli-diff-dependency statement
            type string;
          }
          uses ncs_template_interface-ip-wccp-grouping;
        }
      }
    }
    container ipv6 {
      container address {
        choice address-choice {
          case autoconfig-case {
            container autoconfig {
              presence "true";
              leaf default {
                type empty;
              }
            }
          }
          case dhcp-case {
            container dhcp {
              presence "true";
              leaf rapid-commit {
                type empty;
              }
            }
          }
          case manual-case {
            list prefix-list {
              // NCS patched for predictable order
              ordered-by user;
              key "prefix";
              leaf prefix {
                type string;
              }
              leaf link-local {
                type empty;
              }
              leaf anycast {
                type empty;
              }
              leaf eui-64 {
                type empty;
              }
            }
          }
        }
      }
      leaf enable {
        type empty;
      }
      container unnumbered {
        uses ncs_template_interface-name-grouping;
      }
      list traffic-filter {
        // NCS patched for predictable order
        ordered-by user;
        key "direction";
        leaf direction {
          type string;
        }
        leaf access-list {
          type string;
        }
      }
      container nd {
        container dad {
          leaf attempts {
            type string;
          }
        }
        leaf reachable-time {
          type string;
        }
        container prefix {
          list prefix-list {
            // NCS patched for predictable order
            ordered-by user;
            key "ipv6-prefix";
            leaf ipv6-prefix {
              type string;
            }
            choice advertise-choice {
              case no-advertise {
                leaf no-advertise {
                  type empty;
                }
              }
              case advertise {
                leaf valid-lifetime {
                  type string;
                }
                leaf preferred-lifetime {
                  type string;
                }
                leaf off-link {
                  type empty;
                }
                leaf no-autoconfig {
                  type empty;
                }
                leaf no-rtr-address {
                  type empty;
                }
                leaf no-onlink {
                  type empty;
                }
              }
            }
          }
        }
        leaf managed-config-flag {
          type empty;
        }
        leaf other-config-flag {
          type empty;
        }
        container ra {
          container suppress {
            presence "true";
            leaf all {
              type empty;
            }
          }
          container interval {
            choice interval-choice {
              leaf seconds {
                type string;
              }
              leaf msec {
                type string;
              }
            }
          }
          leaf lifetime {
            type string;
          }
        }
        container raguard {
          presence "true";
        }
        container autoconfig {
          leaf prefix {
            type empty;
          }
          leaf default-route {
            type empty;
          }
        }
      }
      container mld {
        leaf access-group {
          type string;
        }
      }
      leaf redirects {
        type string;
        // NCS drop default statement
      }
      leaf unreachables {
        type string;
        // NCS drop default statement
      }
      container tcp {
        leaf adjust-mss {
          type string;
        }
      }
      container router {
        container isis {
          presence "true";
          leaf tag {
            type string;
          }
        }
      }
      container ospf {
        leaf network {
          type string;
        }
        list process {
          // NCS patched for predictable order
          ordered-by user;
          key "id";
          leaf id {
            type string;
          }
          leaf area {
            type string;
          }
          leaf instance {
            type string;
          }
        }
        container bfd {
          presence "true";
          leaf disable {
            type empty;
          }
        }
        leaf cost {
          type string;
        }
        container database-filter {
          choice database {
            leaf all {
              type string;
            }
            leaf disable {
              type empty;
            }
          }
        }
        leaf dead-interval {
          type string;
        }
        container demand-circuit {
          presence "true";
          leaf disable {
            type empty;
          }
        }
        container flood-reduction {
          presence "true";
          leaf disable {
            type empty;
          }
        }
        leaf hello-interval {
          type string;
        }
        container mtu-ignore {
          presence "true";
          leaf disable {
            type empty;
          }
        }
        leaf priority {
          type string;
        }
        leaf retransmit-interval {
          type string;
        }
        leaf transmit-delay {
          type string;
        }
      }
      leaf-list eigrp {
        // NCS patched for predictable order
        ordered-by user;
        type string;
      }
      leaf mtu {
        type string;
      }
      container crypto {
        container map {
          // NCS drop tailf-common:cli-diff-dependency statement
          leaf map-name {
            type string;
          }
          leaf redundancy {
            type string;
          }
          leaf stateful {
            // NCS drop when statement
            type empty;
          }
        }
      }
      container hold-time {
        list eigrp {
          // NCS patched for predictable order
          ordered-by user;
          key "as-no";
          leaf as-no {
            type string;
          }
          leaf seconds {
            type string;
          }
        }
      }
      container hello-interval {
        list eigrp {
          // NCS patched for predictable order
          ordered-by user;
          key "as-no";
          leaf as-no {
            type string;
          }
          leaf seconds {
            type string;
          }
        }
      }
      container verify {
        container unicast {
          container source {
            leaf reachable-via {
              type string;
            }
          }
          container reverse-path {
            presence "true";
            leaf access-list {
              type string;
            }
          }
        }
      }
      container dhcp {
        container relay {
          list destination {
            // NCS patched for predictable order
            ordered-by user;
            key "ipv6-address";
            leaf ipv6-address {
              type string;
            }
            leaf source-address {
              type string;
            }
            leaf link-address {
              type string;
            }
          }
          container source-interface {
            uses ncs_template_interface-name-grouping;
          }
        }
        container client {
          container information {
            container refresh {
              leaf minimum {
                type string;
              }
            }
          }
        }
      }
      container nhrp {
        container map {
          list map-list {
            // NCS patched for predictable order
            ordered-by user;
            key "ipv6-address";
            leaf ipv6-address {
              type string;
            }
            leaf nbma-address {
              type string;
            }
          }
          container multicast {
            leaf dynamic {
              type empty;
            }
            list multicast-list {
              // NCS patched for predictable order
              ordered-by user;
              key "nbma-address";
              leaf nbma-address {
                type string;
              }
            }
          }
        }
        leaf network-id {
          type string;
        }
        leaf holdtime {
          type string;
        }
        container nhs {
          list nhs-list {
            // NCS patched for predictable order
            ordered-by user;
            key "nhs-address";
            leaf nhs-address {
              type string;
            }
            leaf nbma {
              type string;
            }
            leaf multicast {
              // NCS drop when statement
              type empty;
            }
          }
        }
        container server-only {
          presence "true";
          leaf non-caching {
            type empty;
          }
        }
        container registration {
          leaf no-unique {
            type empty;
          }
          leaf timeout {
            type string;
          }
        }
        container shortcut {
          presence "true";
        }
        container redirect {
          presence "true";
          leaf timeout {
            type string;
          }
        }
      }
      container summary-address {
        // NCS drop tailf-common:cli-diff-dependency statement
        list eigrp {
          // NCS patched for predictable order
          ordered-by user;
          key "as-no ipv6-address";
          leaf as-no {
            type string;
          }
          leaf ipv6-address {
            type string;
          }
          leaf distance {
            type string;
          }
        }
      }
      list rip {
        // NCS patched for predictable order
        ordered-by user;
        key "id";
        leaf id {
          type string;
        }
        leaf enable {
          type empty;
        }
        container default-information {
          leaf default-route {
            type string;
          }
          leaf metric {
            type string;
          }
        }
      }
      container wccp {
        // NCS drop tailf-common:cli-diff-dependency statement
        uses ncs_template_interface-ip-wccp-grouping;
        list vrf {
          // NCS patched for predictable order
          ordered-by user;
          key "name";
          leaf name {
            // NCS drop tailf-common:cli-diff-dependency statement
            type string;
          }
          uses ncs_template_interface-ip-wccp-grouping;
        }
      }
      container policy {
        leaf route-map {
          type string;
        }
      }
    }
    container ospfv3 {
      // NCS drop tailf-common:cli-diff-dependency statement
      uses ncs_template_interface-ospfv3-grouping;
      list ospfv3-list {
        // NCS patched for predictable order
        ordered-by user;
        key "id";
        leaf id {
          type string;
        }
        uses ncs_template_interface-ospfv3-grouping;
        container ipv4 {
          uses ncs_template_interface-ospfv3-grouping;
        }
        container ipv6 {
          uses ncs_template_interface-ospfv3-grouping;
        }
      }
    }
    container nhrp {
      leaf group {
        type string;
      }
      leaf route-watch {
        // NCS drop tailf-common:cli-diff-dependency statement
        type string;
        // NCS drop default statement
      }
    }
    container if-state {
      leaf nhrp {
        type empty;
      }
    }
    leaf delay {
      type string;
    }
    leaf load-interval {
      type string;
    }
    container logging {
      container event {
        leaf link-status {
          type string;
          // NCS drop default statement
        }
        leaf trunk-status {
          type empty;
        }
        leaf bundle-status {
          type empty;
        }
        leaf subif-link-status {
          type empty;
        }
        container spanning-tree {
          leaf status {
            type empty;
          }
        }
        leaf nfas-status {
          type empty;
        }
      }
    }
    leaf max-reserved-bandwidth {
      type string;
    }
    container mls {
      container netflow {
        leaf sampling {
          type empty;
        }
      }
      container qos {
        container cos {
          leaf cos-value {
            type string;
          }
          leaf override {
            type empty;
          }
        }
        leaf channel-consistency {
          type string;
          // NCS drop default statement
        }
        container trust {
          container device {
            leaf cisco-phone {
              type empty;
            }
          }
          choice trust-choice {
            container cos {
              // NCS drop tailf-common:cli-diff-dependency statement
              presence "true";
              container pass-through {
                leaf dscp {
                  type empty;
                }
              }
            }
            container dscp {
              // NCS drop tailf-common:cli-diff-dependency statement
              presence "true";
              container pass-through {
                leaf cos {
                  type empty;
                }
              }
            }
            container ip-precedence {
              // NCS drop tailf-common:cli-diff-dependency statement
              presence "true";
            }
          }
        }
        container monitor {
          leaf-list dscp {
            // NCS patched for predictable order
            ordered-by user;
            // NCS drop max-elements statement
            type string;
          }
        }
        leaf vlan-based {
          // NCS drop tailf-common:cli-diff-dependency statement
          // NCS drop tailf-common:cli-diff-dependency statement
          type empty;
        }
        leaf bridged {
          type empty;
        }
      }
    }
    container auto {
      container qos {
        container voip {
          leaf cisco-phone {
            type empty;
          }
          leaf trust {
            type empty;
          }
        }
      }
    }
    leaf mtu {
      type string;
    }
    container ntp {
      container broadcast {
        presence "true";
        container client {
          presence "true";
        }
        list destination {
          // NCS patched for predictable order
          ordered-by user;
          key "address";
          leaf version {
            type string;
          }
          leaf key {
            type string;
          }
          leaf address {
            type string;
          }
        }
        container version-key {
          leaf version {
            type string;
          }
          leaf key {
            type string;
          }
        }
      }
      leaf disable {
        type empty;
      }
      container multicast {
        presence "true";
        list address-list {
          // NCS patched for predictable order
          ordered-by user;
          key "group-address";
          leaf group-address {
            type string;
          }
          leaf version {
            type string;
          }
          leaf key {
            type string;
          }
          leaf ttl {
            type string;
          }
        }
        leaf version {
          type string;
        }
        leaf key {
          type string;
        }
        leaf ttl {
          type string;
        }
        container client-list {
          leaf-list client {
            // NCS patched for predictable order
            ordered-by user;
            type string;
          }
        }
        leaf client {
          type empty;
        }
      }
    }
    container power {
      container inline {
        leaf consumption {
          type string;
        }
        leaf mode {
          type string;
          // NCS drop default statement
        }
        leaf max {
          // NCS drop when statement
          type string;
        }
      }
      container client {
        leaf local {
          type empty;
        }
      }
    }
    list rate-limit {
      // NCS patched for predictable order
      ordered-by user;
      key "dir bps bc be conform-action exceed-action";
      leaf dir {
        type string;
      }
      leaf dscp {
        type string;
      }
      leaf bps {
        type string;
      }
      leaf bc {
        type string;
      }
      leaf be {
        type string;
      }
      leaf conform-action {
        type string;
      }
      leaf exceed-action {
        type string;
      }
    }
    container service-policy {
      leaf history {
        type empty;
      }
      uses ncs_template_service-policy-grouping;
      container type {
        container control {
          leaf subscriber {
            type string;
          }
        }
        container performance-monitor {
          uses ncs_template_service-policy-grouping;
        }
      }
    }
    container service-insertion {
      leaf waas {
        type empty;
      }
    }
    container service-module {
      container t1 {
        leaf-list timeslots {
          // NCS patched for predictable order
          ordered-by user;
          type string;
        }
        leaf speed {
          type string;
        }
      }
    }
    leaf group {
      // NCS drop tailf-common:cli-diff-dependency statement
      type string;
    }
    leaf shutdown {
      type empty;
    }
    container standby {
      leaf version {
        type string;
      }
      leaf bfd {
        type string;
        // NCS drop default statement
      }
      container delay {
        leaf minimum {
          type string;
        }
        leaf reload {
          type string;
        }
      }
      leaf mac-refresh {
        type string;
      }
      container use-bia {
        presence "true";
        container scope {
          leaf interface {
            type empty;
          }
        }
      }
      list standby-list {
        // NCS patched for predictable order
        ordered-by user;
        // NCS drop tailf-common:cli-diff-dependency statement
        key "group-number";
        leaf group-number {
          type string;
        }
        container authentication {
          choice auth {
            leaf word {
              type string;
            }
            container md5 {
              leaf key-chain {
                type string;
              }
              container key-string {
                uses ncs_template_password-grouping;
                leaf timeout {
                  type string;
                }
              }
            }
            leaf text {
              type string;
            }
          }
        }
        leaf follow {
          type string;
        }
        container ip {
          presence "true";
          leaf address {
            // NCS drop tailf-common:cli-diff-dependency statement
            type string;
          }
          leaf secondary {
            type empty;
          }
        }
        leaf ipv6 {
          type string;
        }
        leaf mac-address {
          type string;
        }
        leaf name {
          type string;
        }
        container redirect {
          container advertisement {
            container authentication {
              container md5 {
                leaf key-chain {
                  type string;
                }
                container key-string {
                  uses ncs_template_password-grouping;
                  leaf timeout {
                    type string;
                  }
                }
              }
            }
          }
          container timers {
            leaf advertisement {
              type string;
            }
            leaf holddown {
              type string;
            }
          }
          leaf unknown {
            type empty;
          }
        }
        container timers {
          container hello-interval {
            choice hello-interval-choice {
              leaf seconds {
                type string;
              }
              leaf msec {
                type string;
              }
            }
          }
          container hold-time {
            choice hold-time-choice {
              leaf seconds {
                type string;
              }
              leaf msec {
                type string;
              }
            }
          }
        }
        leaf priority {
          type string;
        }
        container preempt {
          presence "true";
          container delay {
            leaf minimum {
              type string;
            }
            leaf reload {
              type string;
            }
            leaf sync {
              type string;
            }
          }
        }
        list track {
          // NCS patched for predictable order
          ordered-by user;
          key "name";
          leaf name {
            type string;
          }
          choice options {
            case interface {
              leaf priority-decrement {
                type string;
              }
            }
            case group-number {
              leaf decrement {
                type string;
              }
              leaf shutdown {
                type empty;
              }
            }
          }
        }
      }
    }
    container storm-control {
      container action {
        leaf shutdown {
          type empty;
        }
        leaf trap {
          type empty;
        }
        leaf level {
          type string;
        }
      }
      container broadcast {
        leaf level {
          type string;
        }
        uses ncs_template_storm-control-level-bps-pps-grouping;
        container include {
          leaf multicast {
            type empty;
          }
        }
      }
      container multicast {
        leaf level {
          type string;
        }
        uses ncs_template_storm-control-level-bps-pps-grouping;
      }
      container unicast {
        leaf level {
          type string;
        }
        uses ncs_template_storm-control-level-bps-pps-grouping;
      }
    }
    container wrr-queue {
      container bandwidth {
        choice bandwidth-choice {
          case a {
            leaf weight-1 {
              type string;
            }
            leaf weight-2 {
              type string;
            }
            leaf weight-3 {
              type string;
            }
            leaf weight-4 {
              type string;
            }
            leaf weight-5 {
              type string;
            }
            leaf weight-6 {
              type string;
            }
            leaf weight-7 {
              type string;
            }
          }
          case b {
            container percent {
              leaf percent-1 {
                type string;
              }
              leaf percent-2 {
                type string;
              }
              leaf percent-3 {
                type string;
              }
              leaf percent-4 {
                type string;
              }
              leaf percent-5 {
                type string;
              }
              leaf percent-6 {
                type string;
              }
              leaf percent-7 {
                type string;
              }
            }
          }
        }
      }
      list dscp-map {
        // NCS patched for predictable order
        ordered-by user;
        key "queue threshold";
        leaf queue {
          type string;
        }
        leaf threshold {
          type string;
        }
        list values {
          // NCS patched for predictable order
          ordered-by user;
          key "value";
          leaf value {
            type string;
          }
        }
      }
      list cos-map {
        // NCS patched for predictable order
        ordered-by user;
        key "queue-id threshold-id";
        leaf queue-id {
          type string;
        }
        leaf threshold-id {
          type string;
        }
        leaf-list cos-values {
          // NCS patched for predictable order
          ordered-by user;
          // NCS drop max-elements statement
          type string;
        }
      }
      container queue-limit {
        leaf weight-a {
          type string;
        }
        leaf weight-b {
          type string;
        }
        leaf weight-c {
          type string;
        }
        leaf weight-d {
          type string;
        }
        leaf weight-e {
          type string;
        }
        leaf weight-f {
          type string;
        }
        leaf weight-g {
          type string;
        }
      }
      container random-detect {
        list max-threshold {
          // NCS patched for predictable order
          ordered-by user;
          key "id";
          leaf id {
            type string;
          }
          uses ncs_template_queue-size-grouping;
        }
        list min-threshold {
          // NCS patched for predictable order
          ordered-by user;
          key "id";
          leaf id {
            type string;
          }
          uses ncs_template_queue-size-grouping;
        }
      }
      list threshold {
        // NCS patched for predictable order
        ordered-by user;
        key "id";
        leaf id {
          type string;
        }
        uses ncs_template_queue-size-grouping;
      }
      list min-reserve {
        // NCS patched for predictable order
        ordered-by user;
        key "id";
        leaf id {
          type string;
        }
        leaf level {
          type string;
        }
      }
    }
    container no-list {
      container wrr-queue {
        list random-detect {
          // NCS patched for predictable order
          ordered-by user;
          key "id";
          leaf id {
            type string;
          }
        }
      }
    }
    container priority-queue {
      leaf queue-limit {
        type string;
      }
      list dscp-map {
        // NCS patched for predictable order
        ordered-by user;
        key "id";
        leaf id {
          type string;
        }
        list values {
          // NCS patched for predictable order
          ordered-by user;
          key "value";
          leaf value {
            type string;
          }
        }
      }
      container cos-map {
        leaf id {
          type string;
        }
        leaf-list cos-values {
          // NCS patched for predictable order
          ordered-by user;
          // NCS drop max-elements statement
          type string;
        }
      }
      leaf out {
        type empty;
      }
    }
    container rep {
      container block {
        container port {
          choice port-choice {
            leaf neighbor-offset {
              type string;
            }
            leaf id {
              type string;
            }
            leaf preferred {
              type empty;
            }
          }
          leaf vlan {
            type string;
          }
        }
      }
      container preempt {
        leaf delay {
          type string;
        }
      }
      container segment {
        leaf id {
          type string;
        }
        leaf edge {
          type empty;
        }
        leaf no-neighbor {
          type empty;
        }
        leaf primary {
          // NCS drop when statement
          type empty;
        }
        leaf preferred {
          type empty;
        }
      }
      container stcn {
        leaf segment {
          type string;
        }
        leaf stp {
          type empty;
        }
      }
    }
    container rcv-queue {
      list cos-map {
        // NCS patched for predictable order
        ordered-by user;
        key "queue-id threshold-id";
        leaf queue-id {
          type string;
        }
        leaf threshold-id {
          type string;
        }
        leaf-list cos-values {
          // NCS patched for predictable order
          ordered-by user;
          // NCS drop max-elements statement
          type string;
        }
      }
    }
    container udld {
      container port {
        presence "true";
        choice port-choice {
          leaf aggressive {
            type empty;
          }
          leaf disable {
            type empty;
          }
        }
      }
    }
    container peer {
      leaf neighbor-route {
        type string;
        // NCS drop default statement
      }
      container default {
        container ip {
          container address {
            choice address-choice {
              leaf dhcp {
                type empty;
              }
              container dhcp-pool {
                presence "true";
                leaf pools {
                  type string;
                }
              }
              container pool {
                presence "true";
                leaf pools {
                  type string;
                }
              }
            }
          }
        }
      }
    }
    container clns {
      leaf mtu {
        type string;
      }
      container router {
        container isis {
          presence "true";
          leaf tag {
            type string;
          }
        }
      }
      leaf route-cache {
        type string;
        // NCS drop default statement
      }
    }
    container dsu {
      leaf bandwidth {
        type string;
      }
      leaf mode {
        type string;
      }
    }
    leaf framing {
      type string;
    }
    leaf cablelength {
      type string;
    }
    container isdn {
      leaf switch-type {
        type string;
      }
      leaf protocol-emulate {
        type string;
      }
      container incoming-voice {
        choice incoming-voice-choice {
          leaf voice {
            type empty;
          }
          container data {
            presence "true";
            leaf kbps {
              type string;
            }
          }
          container modem {
            presence "true";
            leaf kbps {
              type string;
            }
          }
        }
      }
      container supp-service {
        container name {
          container calling {
            presence "true";
          }
        }
      }
      container termination {
        leaf multidrop {
          type empty;
        }
      }
      leaf point-to-point-setup {
        type empty;
      }
    }
    leaf scramble {
      type empty;
    }
    container clock {
      leaf source {
        type string;
      }
      leaf rate {
        type string;
      }
    }
    leaf down-when-looped {
      type empty;
    }
    leaf crc {
      type string;
    }
    container carrier-delay {
      uses ncs_template_carrier-delay-grouping;
      container up {
        uses ncs_template_carrier-delay-grouping;
      }
      container down {
        uses ncs_template_carrier-delay-grouping;
      }
    }
    leaf trunk-group {
      type string;
    }
    container crypto {
      container engine {
        leaf slot {
          type string;
        }
        leaf location {
          type string;
        }
      }
      container map {
        container ipv4 {
          leaf map-name {
            type string;
          }
          leaf redundancy {
            type string;
          }
          leaf stateful {
            // NCS drop when statement
            type empty;
          }
        }
        container ipv6 {
          leaf map-name {
            type string;
          }
          leaf redundancy {
            type string;
          }
          leaf stateful {
            // NCS drop when statement
            type empty;
          }
        }
      }
    }
    container routing {
      leaf dynamic {
        type string;
        // NCS drop default statement
      }
    }
    container autonomic {
      leaf connect {
        type empty;
      }
    }
    container performance {
      container monitor {
        leaf context {
          // NCS drop tailf-common:cli-diff-dependency statement
          type string;
        }
      }
    }
    container qos {
      container trust {
        choice trust-choice {
          leaf dscp {
            type empty;
          }
          leaf cos {
            type empty;
          }
          leaf device {
            type string;
          }
        }
      }
      leaf pre-classify {
        type empty;
      }
    }
    list tx-queue {
      // NCS patched for predictable order
      ordered-by user;
      key "id";
      leaf id {
        type string;
      }
      container bandwidth {
        choice bandwidth-choice {
          case numeric {
            leaf value {
              type string;
            }
            leaf unit {
              type string;
            }
          }
          leaf percent {
            type string;
          }
        }
      }
      leaf priority {
        type string;
      }
    }
    container link {
      container state {
        container group {
          leaf number {
            type string;
          }
          leaf direction {
            type string;
          }
        }
      }
    }
    container source {
      leaf template {
        type string;
      }
    }
    container l2protocol {
      container peer {
        presence "true";
        leaf-list protocol {
          // NCS patched for predictable order
          ordered-by user;
          type string;
        }
      }
      container forward {
        presence "true";
        leaf-list protocol {
          // NCS patched for predictable order
          ordered-by user;
          type string;
        }
      }
    }
    container zone-member {
      leaf security {
        // NCS drop tailf-common:cli-diff-dependency statement
        type string;
      }
    }
  }

  grouping ncs_template_interface-common-grouping {
    uses ncs_template_interface-common-grouping0 {
      refine "ip/helper-address/vrf/vrf" {
        // NCS drop tailf-common:cli-diff-dependency statement
        // NCS drop tailf-common:cli-diff-dependency statement
      }
      refine "crypto/map/ipv4/map-name" {
        // NCS drop tailf-common:cli-diff-dependency statement
      }
      refine "crypto/map/ipv6/map-name" {
        // NCS drop tailf-common:cli-diff-dependency statement
      }
      refine "ip/mobile/router-service/roam" {
        // NCS drop tailf-common:cli-diff-dependency statement
      }
      refine "ip/pim/mode" {
        // NCS drop tailf-common:cli-diff-dependency statement
      }
    }
  }

  grouping ncs_template_sub-interface-common-grouping {
    uses ncs_template_interface-common-grouping0 {
      refine "ip/helper-address/vrf/vrf" {
        // NCS drop tailf-common:cli-diff-dependency statement
        // NCS drop tailf-common:cli-diff-dependency statement
      }
      refine "crypto/map/ipv4/map-name" {
        // NCS drop tailf-common:cli-diff-dependency statement
      }
      refine "crypto/map/ipv6/map-name" {
        // NCS drop tailf-common:cli-diff-dependency statement
      }
      refine "ip/mobile/router-service/roam" {
        // NCS drop tailf-common:cli-diff-dependency statement
      }
      refine "ip/pim/mode" {
        // NCS drop tailf-common:cli-diff-dependency statement
      }
    }
  }

  grouping ncs_template_interface-common-switch-grouping {
    uses ncs_template_interface-common-grouping {
      refine "ip/dhcp/snooping" {
        // NCS drop tailf-common:cli-diff-dependency statement
      }
      refine "ip/verify" {
        // NCS drop tailf-common:cli-diff-dependency statement
      }
      refine "ip/igmp" {
        // NCS drop tailf-common:cli-diff-dependency statement
        // NCS drop tailf-common:cli-diff-dependency statement
      }
      refine "ip/ospf" {
        // NCS drop tailf-common:cli-diff-dependency statement
      }
      refine "ip/redirects" {
        // NCS drop tailf-common:cli-diff-dependency statement
      }
      refine "standby" {
        // NCS drop tailf-common:cli-diff-dependency statement
      }
      refine "service-policy/input" {
        // NCS drop tailf-common:cli-diff-dependency statement
      }
      refine "service-policy/output" {
        // NCS drop tailf-common:cli-diff-dependency statement
      }
      refine "udld" {
        // NCS drop tailf-common:cli-diff-dependency statement
      }
    }
  }

  grouping ncs_template_sub-interface-common-switch-grouping {
    uses ncs_template_sub-interface-common-grouping {
      refine "ip/dhcp/snooping" {
        // NCS drop tailf-common:cli-diff-dependency statement
      }
      refine "ip/verify" {
        // NCS drop tailf-common:cli-diff-dependency statement
      }
      refine "ip/igmp" {
        // NCS drop tailf-common:cli-diff-dependency statement
        // NCS drop tailf-common:cli-diff-dependency statement
      }
      refine "ip/ospf" {
        // NCS drop tailf-common:cli-diff-dependency statement
      }
      refine "ip/redirects" {
        // NCS drop tailf-common:cli-diff-dependency statement
      }
      refine "standby" {
        // NCS drop tailf-common:cli-diff-dependency statement
      }
      refine "service-policy/input" {
        // NCS drop tailf-common:cli-diff-dependency statement
      }
      refine "service-policy/output" {
        // NCS drop tailf-common:cli-diff-dependency statement
      }
      refine "udld" {
        // NCS drop tailf-common:cli-diff-dependency statement
      }
    }
  }

  grouping ncs_template_interface-tunnel-grouping {
    container tunnel {
      leaf source {
        type string;
      }
      leaf destination {
        type string;
      }
      container mode {
        choice mode-choice {
          container ipsec {
            container ipv4 {
              presence "true";
            }
          }
          container mpls {
            container traffic-eng {
              presence "true";
              leaf gre-ip {
                type empty;
              }
              leaf point-to-multipoint {
                type empty;
              }
            }
          }
          container gre {
            choice gre-choice {
              container multipoint {
                presence "true";
                leaf ipv6 {
                  type empty;
                }
              }
              leaf ip {
                type empty;
              }
              leaf ipv6 {
                type empty;
              }
              // NCS drop default statement
            }
          }
          leaf eon {
            type empty;
          }
          leaf ipv6 {
            type empty;
          }
        }
      }
      leaf key {
        type string;
      }
      leaf vrf {
        // NCS drop tailf-common:cli-diff-dependency statement
        // NCS drop tailf-common:cli-diff-dependency statement
        type string;
      }
      container path-mtu-discovery {
        presence "true";
      }
      container protection {
        container ipsec {
          leaf profile {
            type string;
          }
          choice profile-choice {
            leaf isakmp-profile {
              type string;
            }
            leaf ikev2-profile {
              type string;
            }
            leaf shared {
              type empty;
            }
          }
        }
      }
      container mpls {
        container traffic-eng {
          // NCS drop tailf-common:cli-diff-dependency statement
          leaf name {
            type string;
          }
          container affinity {
            leaf attributes {
              type string;
            }
            leaf mask {
              type string;
            }
          }
          container autoroute {
            leaf announce {
              type empty;
            }
          }
          container priority {
            leaf setup-priority {
              type string;
            }
            leaf hold-priority {
              type string;
            }
          }
          container bandwidth {
            leaf requirement {
              type string;
            }
          }
          list path-option {
            // NCS patched for predictable order
            ordered-by user;
            key "id";
            leaf id {
              type string;
            }
            leaf protect {
              type empty;
            }
            choice path-option-choice {
              container dynamic {
                presence "true";
              }
              container explicit {
                choice explicit-choice {
                  leaf name {
                    type string;
                  }
                  leaf identifier {
                    type string;
                  }
                }
              }
            }
            leaf lockdown {
              type empty;
            }
            leaf verbatim {
              type empty;
            }
          }
          container auto-bw {
            presence "true";
          }
          container fast-reroute {
            presence "true";
          }
        }
      }
    }
    container domain {
      leaf domain-name {
        type string;
      }
      leaf path {
        type string;
      }
      leaf path-id {
        type string;
      }
      leaf internet-bound {
        type empty;
      }
      leaf zero-sla {
        type empty;
      }
      leaf path-last-resort {
        type empty;
      }
    }
  }

  grouping ncs_template_interface-ethernet-pre-grouping {
    leaf port-type {
      type string;
    }
    container platform {
      container ring {
        leaf rx {
          type string;
        }
        leaf tx {
          type string;
        }
      }
    }
    container encapsulation {
      container dot1Q {
        leaf vlan-id {
          type string;
        }
        leaf second-dot1q {
          type string;
        }
        leaf native {
          type empty;
        }
      }
    }
  }

  grouping ncs_template_interface-ethernet-grouping0 {
    container mac {
      list access-group {
        // NCS patched for predictable order
        ordered-by user;
        key "direction";
        leaf direction {
          type string;
        }
        leaf access-list {
          type string;
        }
      }
    }
    container spanning-tree {
      leaf bpdufilter {
        type string;
      }
      container bpduguard {
        choice bpduguard-choice {
          leaf disable {
            type empty;
          }
          leaf enable {
            type empty;
          }
        }
      }
      leaf cost {
        type string;
      }
      leaf guard {
        type string;
      }
      leaf link-type {
        type string;
      }
      container mst {
        choice mst-choice {
          list instance-range {
            // NCS patched for predictable order
            ordered-by user;
            key "id";
            leaf id {
              type string;
            }
            leaf cost {
              type string;
            }
            leaf port-priority {
              type string;
            }
          }
          leaf pre-standard {
            type empty;
          }
        }
      }
      container portfast {
        presence "true";
        choice portfast-choice {
          leaf disable {
            type empty;
          }
          leaf network {
            type empty;
          }
          case trunk-mode {
            leaf edge {
              type empty;
            }
            leaf trunk {
              type empty;
            }
          }
        }
      }
      container loopguard {
        leaf default {
          type empty;
        }
      }
    }
    container srr-queue {
      container bandwidth {
        leaf limit {
          type string;
        }
        container shape {
          leaf weight1 {
            type string;
          }
          leaf weight2 {
            type string;
          }
          leaf weight3 {
            type string;
          }
          leaf weight4 {
            type string;
          }
        }
        container share {
          leaf weight1 {
            type string;
          }
          leaf weight2 {
            type string;
          }
          leaf weight3 {
            type string;
          }
          leaf weight4 {
            type string;
          }
        }
      }
    }
    leaf queue-set {
      type string;
    }
    container dot1x {
      container pae {
        leaf authenticator {
          type empty;
        }
      }
      container timeout {
        leaf quiet-period {
          type string;
        }
        leaf tx-period {
          type string;
        }
        leaf supp-period {
          type string;
        }
        leaf ratelimit-period {
          type string;
        }
        leaf held-period {
          type string;
        }
      }
    }
    leaf media-type {
      type string;
      // NCS drop default statement
    }
    container mdix {
      leaf auto {
        type string;
        // NCS drop default statement
      }
    }
    leaf channel-protocol {
      type string;
    }
    container lacp {
      leaf rate {
        type string;
        // NCS drop default statement
      }
      leaf fast-switchover {
        type empty;
      }
      leaf min-bundle {
        type string;
      }
      leaf max-bundle {
        type string;
      }
    }
    container ethernet {
      container oam-conf {
        container oam {
          leaf max-rate {
            type string;
          }
          leaf min-rate {
            type string;
          }
          leaf mode {
            type string;
          }
          container remote-loopback {
            leaf supported {
              type empty;
            }
          }
          leaf timeout {
            type string;
            // NCS drop default statement
          }
          container link-monitor {
            leaf supported {
              type string;
              // NCS drop default statement
            }
            leaf on {
              type string;
              // NCS drop default statement
            }
            container receive-crc {
              leaf window {
                type string;
              }
            }
          }
        }
      }
      leaf oam {
        type empty;
      }
      container dot1ad {
        choice dot1ad-choice {
          leaf nni {
            type empty;
          }
          container uni {
            choice uni-choice {
              container c-port {
                presence "true";
                leaf isolate {
                  type empty;
                }
              }
              container s-port {
                presence "true";
                leaf isolate {
                  type empty;
                }
              }
            }
          }
        }
      }
      container cfm {
        container mip {
          list level {
            // NCS patched for predictable order
            ordered-by user;
            key "level";
            leaf level {
              type string;
            }
            leaf-list vlan {
              // NCS patched for predictable order
              ordered-by user;
              type string;
            }
          }
        }
        container mep {
          list mep-list {
            // NCS patched for predictable order
            ordered-by user;
            key "mpid";
            leaf mpid {
              type string;
            }
            leaf domain {
              type string;
            }
            leaf vlan {
              type string;
            }
            container service {
              choice service-choice {
                leaf short-ma-name {
                  type string;
                }
                leaf number {
                  type string;
                }
              }
            }
          }
        }
        leaf enable {
          type string;
          // NCS drop default statement
        }
        leaf interface {
          type string;
        }
      }
      container uni {
        leaf id {
          type string;
        }
        container bundle {
          presence "true";
          leaf all-to-one {
            type empty;
          }
        }
      }
      container lmi {
        leaf interface {
          type string;
        }
      }
    }
    container negotiation {
      leaf auto {
        type string;
      }
    }
    container synchronous {
      leaf mode {
        type empty;
      }
    }
    container esmc {
      container mode {
        leaf direction {
          type string;
        }
        leaf ql-disabled {
          type empty;
        }
      }
    }
    leaf speed {
      // NCS drop tailf-common:cli-diff-dependency statement
      // NCS drop tailf-common:cli-diff-dependency statement
      type string;
      // NCS drop default statement
    }
    leaf duplex {
      // NCS drop tailf-common:cli-diff-dependency statement
      // NCS drop tailf-common:cli-diff-dependency statement
      type string;
      // NCS drop default statement
    }
    uses ncs_template_xconnect-interface-grouping;
    container pppoe {
      container enable {
        presence "true";
        leaf group {
          type string;
        }
      }
      leaf max-sessions {
        type string;
      }
    }
    container vlan-id {
      list dot1q {
        // NCS patched for predictable order
        ordered-by user;
        key "id";
        leaf id {
          type string;
        }
      }
    }
    container service {
      list instance {
        // NCS patched for predictable order
        ordered-by user;
        key "id";
        leaf id {
          // NCS drop tailf-common:cli-diff-dependency statement
          // NCS drop tailf-common:cli-diff-dependency statement
          // NCS drop tailf-common:cli-diff-dependency statement
          // NCS drop tailf-common:cli-diff-dependency statement
          type string;
        }
        leaf trunk {
          type empty;
        }
        leaf ethernet {
          type empty;
        }
        leaf ethernet-evc-name {
          type string;
        }
        leaf description {
          type string;
        }
        container encapsulation {
          choice encapsulation-choice {
            container dot1q {
              // NCS drop tailf-common:cli-diff-dependency statement
              uses ncs_template_if-srv-encapsulation-dot1q-grouping;
            }
            container dot1ad {
              leaf-list id {
                // NCS patched for predictable order
                ordered-by user;
                type string;
              }
              leaf-list dot1q {
                // NCS patched for predictable order
                ordered-by user;
                type string;
              }
            }
            container untagged {
              // NCS drop tailf-common:cli-diff-dependency statement
              presence "true";
              leaf comma {
                tailf:alt-name ",";
                type empty;
              }
              container dot1q {
                uses ncs_template_if-srv-encapsulation-dot1q-grouping;
              }
            }
            container default {
              presence "true";
            }
          }
        }
        container rewrite {
          container ingress {
            container tag {
              // NCS drop tailf-common:cli-diff-dependency statement
              choice tag-choice {
                leaf pop {
                  type string;
                }
                case push {
                  leaf push {
                    type string;
                  }
                  leaf vlan-id {
                    type string;
                  }
                }
                case translate {
                  leaf translate {
                    type string;
                  }
                  leaf dot1ad {
                    type string;
                  }
                  leaf dot1q {
                    type string;
                  }
                  leaf second-dot1q {
                    type string;
                  }
                  leaf vlan-type {
                    type string;
                  }
                }
              }
              leaf mode {
                type string;
              }
            }
          }
        }
        container storm-control {
          container broadcast {
            leaf cir {
              type string;
            }
          }
          container multicast {
            leaf cir {
              type string;
            }
          }
        }
        leaf group {
          // NCS drop tailf-common:cli-diff-dependency statement
          type string;
        }
        container errdisable {
          container recovery {
            container cause {
              leaf mac-security {
                type string;
              }
            }
          }
        }
        container snmp {
          container trap {
            leaf link-status {
              type empty;
            }
          }
          container ifindex {
            leaf persist {
              type empty;
            }
          }
        }
        leaf shutdown {
          type empty;
        }
        container mac {
          container security {
            presence "true";
            list address {
              // NCS patched for predictable order
              ordered-by user;
              key "operation mac-address";
              leaf operation {
                type string;
              }
              leaf mac-address {
                type string;
              }
            }
            container maximum {
              leaf addresses {
                type string;
              }
            }
            leaf violation {
              type string;
            }
          }
          container static {
            list address {
              // NCS patched for predictable order
              ordered-by user;
              key "mac-addr";
              leaf mac-addr {
                type string;
              }
            }
          }
          list access-group {
            // NCS patched for predictable order
            ordered-by user;
            key "direction";
            leaf direction {
              type string;
            }
            leaf access-list {
              type string;
            }
          }
        }
        container l2protocol {
          container peer {
            presence "true";
            leaf-list protocol {
              // NCS patched for predictable order
              ordered-by user;
              type string;
            }
          }
          container forward {
            presence "true";
            leaf-list protocol {
              // NCS patched for predictable order
              ordered-by user;
              type string;
            }
          }
          container tunnel {
            presence "true";
            leaf-list protocol {
              // NCS patched for predictable order
              ordered-by user;
              type string;
            }
          }
        }
        container bridge-domain {
          // NCS drop tailf-common:cli-diff-dependency statement
          leaf from-encapsulation {
            type empty;
          }
          leaf bridge-id {
            type string;
          }
          container split-horizon {
            leaf group {
              type string;
            }
          }
        }
        container service-policy {
          list input {
            // NCS patched for predictable order
            ordered-by user;
            // NCS drop max-elements statement
            key "name";
            leaf name {
              type string;
            }
          }
          list output {
            // NCS patched for predictable order
            ordered-by user;
            // NCS drop max-elements statement
            key "name";
            leaf name {
              type string;
            }
          }
        }
        uses ncs_template_xconnect-grouping {
          refine "xconnect-choice/xconnect/xconnect" {
            // NCS drop tailf-common:cli-diff-dependency statement
          }
          refine "xconnect-choice/xconnect/xconnect/mtu" {
            // NCS drop tailf-common:cli-diff-dependency statement
          }
        }
        container cfm {
          container mip {
            leaf level {
              type string;
            }
          }
          container mep {
            leaf domain {
              // NCS drop tailf-common:cli-diff-dependency statement
              type string;
            }
            leaf mpid {
              type string;
            }
            container continuity-check {
              container static {
                leaf rmep {
                  type empty;
                }
              }
            }
            container rmep {
              leaf mpid {
                type string;
              }
            }
            leaf cos {
              type string;
            }
          }
        }
        container ethernet-if-srv {
          container ethernet {
            container lmi {
              container ce-vlan {
                leaf-list map {
                  // NCS patched for predictable order
                  ordered-by user;
                  type string;
                }
              }
            }
            container loopback {
              container permit {
                leaf external {
                  type empty;
                }
                leaf internal {
                  type empty;
                }
              }
            }
          }
        }
      }
    }
    container channel-group {
      leaf number {
        // NCS drop tailf-common:cli-diff-dependency statement
        // NCS drop tailf-common:cli-diff-dependency statement
        // NCS drop tailf-common:cli-diff-dependency statement
        // NCS drop tailf-common:cli-diff-dependency statement
        // NCS drop tailf-common:cli-diff-dependency statement
        // NCS drop tailf-common:cli-diff-dependency statement
        // NCS drop tailf-common:cli-diff-dependency statement
        // NCS drop tailf-common:cli-diff-dependency statement
        type string;
      }
      leaf mode {
        type string;
      }
    }
    container soak {
      container link {
        leaf notification {
          type string;
        }
      }
    }
  }

  grouping ncs_template_interface-ethernet-grouping {
    uses ncs_template_interface-ethernet-grouping0 {
      refine "service/instance/service-policy" {
        // NCS drop tailf-common:cli-diff-dependency statement
      }
      refine "service/instance/bridge-domain/bridge-id" {
        // NCS drop tailf-common:cli-diff-dependency statement
      }
      refine "channel-group/number" {
        // NCS drop tailf-common:cli-diff-dependency statement
      }
    }
  }

  grouping ncs_template_sub-interface-ethernet-grouping {
    uses ncs_template_interface-ethernet-grouping0 {
      refine "service/instance/service-policy" {
        // NCS drop tailf-common:cli-diff-dependency statement
      }
      refine "service/instance/bridge-domain/bridge-id" {
        // NCS drop tailf-common:cli-diff-dependency statement
      }
      refine "channel-group/number" {
        // NCS drop tailf-common:cli-diff-dependency statement
      }
    }
  }

  grouping ncs_template_interface-ethernet-switch-grouping {
    uses ncs_template_interface-ethernet-grouping {
      refine "service/instance" {
        // NCS drop tailf-common:cli-diff-dependency statement
      }
      refine "channel-group/number" {
        // NCS drop tailf-common:cli-diff-dependency statement
      }
    }
  }

  grouping ncs_template_sub-interface-ethernet-switch-grouping {
    uses ncs_template_sub-interface-ethernet-grouping {
      refine "service/instance" {
        // NCS drop tailf-common:cli-diff-dependency statement
      }
      refine "channel-group/number" {
        // NCS drop tailf-common:cli-diff-dependency statement
      }
    }
  }

  grouping ncs_template_interface-ethernet-post-grouping0 {
    leaf bridge-group {
      type string;
    }
    container bridge-group-conf {
      // NCS drop when statement
      list bridge-group {
        // NCS patched for predictable order
        ordered-by user;
        // NCS drop max-elements statement
        key "id";
        leaf id {
          type string;
        }
        leaf subscriber-loop-control {
          type empty;
        }
        leaf block-unknown-source {
          type empty;
        }
        leaf source-learning {
          type string;
          // NCS drop default statement
        }
        leaf unicast-flooding {
          type string;
          // NCS drop default statement
        }
        leaf spanning-disabled {
          type empty;
        }
      }
    }
    list vrrp {
      // NCS patched for predictable order
      ordered-by user;
      key "id";
      leaf id {
        type string;
      }
      container authentication {
        choice auth {
          leaf word {
            type string;
          }
          container md5 {
            leaf key-chain {
              type string;
            }
            container key-string {
              uses ncs_template_password-grouping;
              leaf timeout {
                type string;
              }
            }
          }
          leaf text {
            type string;
          }
        }
      }
      uses ncs_template_interface-vrrp-grouping;
      container ip {
        leaf address {
          type string;
        }
        leaf secondary {
          type empty;
        }
      }
    }
    container vrrv3p-v3 {
      // NCS drop when statement
      list vrrp {
        // NCS patched for predictable order
        ordered-by user;
        key "id address-family";
        leaf id {
          type string;
        }
        leaf address-family {
          type string;
        }
        uses ncs_template_interface-vrrp-grouping;
        container address {
          list primary-list {
            // NCS patched for predictable order
            ordered-by user;
            // NCS drop max-elements statement
            key "address";
            leaf address {
              type string;
            }
            leaf primary {
              type empty;
            }
          }
          list secondary-list {
            // NCS patched for predictable order
            ordered-by user;
            key "address";
            leaf address {
              type string;
            }
            leaf secondary {
              type empty;
            }
          }
        }
      }
    }
    container vrrs {
      list pathway {
        // NCS patched for predictable order
        ordered-by user;
        key "name";
        leaf name {
          type string;
        }
        uses ncs_template_description-grouping;
        list address {
          // NCS patched for predictable order
          ordered-by user;
          key "address";
          leaf address {
            type string;
          }
        }
      }
    }
  }

  grouping ncs_template_interface-ethernet-post-grouping {
    uses ncs_template_interface-ethernet-post-grouping0 {
      refine "vrrv3p-v3" {
        // NCS drop tailf-common:cli-diff-dependency statement
      }
    }
  }

  grouping ncs_template_sub-interface-ethernet-post-grouping {
    uses ncs_template_interface-ethernet-post-grouping0 {
      refine "vrrv3p-v3" {
        // NCS drop tailf-common:cli-diff-dependency statement
      }
    }
  }

  grouping ncs_template_interface-pointtopoint-grouping {
    container encapsulation-pointtopoint {
      container encapsulation {
        container isl {
          leaf vlan-id {
            type string;
          }
        }
        container ppp {
          presence "true";
        }
        container slip {
          presence "true";
        }
        container frame-relay {
          presence "true";
          leaf IETF {
            type empty;
          }
          leaf MFR {
            type string;
          }
        }
        container hdlc {
          presence "true";
        }
      }
    }
    container dialer {
      container in-band {
        presence "true";
        leaf parity {
          type string;
        }
      }
      container idle-timeout {
        leaf seconds {
          type string;
        }
        leaf direction {
          type string;
        }
      }
      leaf enable-timeout {
        type string;
      }
      leaf string {
        type string;
      }
      leaf pool {
        type string;
      }
      container map {
        list ip {
          // NCS patched for predictable order
          ordered-by user;
          key "address";
          leaf address {
            type string;
          }
          leaf name {
            type string;
          }
          leaf class {
            type string;
          }
        }
      }
      leaf watch-group {
        type string;
      }
    }
    leaf dialer-group {
      type string;
    }
    container ppp {
      container mtu {
        leaf adaptive {
          // NCS drop tailf-common:cli-diff-dependency statement
          type empty;
        }
      }
      container pfc {
        leaf local {
          type string;
        }
      }
      container acfc {
        leaf local {
          type string;
        }
        leaf remote {
          type string;
        }
      }
      leaf accounting {
        type string;
      }
      container authentication {
        leaf method {
          type string;
        }
        leaf list-name {
          type string;
        }
        leaf chap {
          // NCS drop when statement
          type empty;
        }
        leaf callback {
          type empty;
        }
        leaf callin {
          type empty;
        }
        leaf callout {
          type empty;
        }
        leaf default {
          type empty;
        }
        leaf eap {
          // NCS drop when statement
          type empty;
        }
        leaf ms-chap {
          // NCS drop when statement
          type empty;
        }
        leaf ms-chap-v2 {
          // NCS drop when statement
          type empty;
        }
        leaf one-time {
          type empty;
        }
        leaf optional {
          type empty;
        }
        leaf pap {
          // NCS drop when statement
          type empty;
        }
      }
      leaf authorization {
        type string;
      }
      container chap {
        leaf hostname {
          type string;
        }
        container password {
          uses ncs_template_password-grouping;
        }
      }
      container ipcp {
        container address {
          leaf accept {
            type empty;
          }
          leaf proxy {
            type string;
          }
          leaf request {
            type string;
          }
          leaf required {
            type empty;
          }
          leaf unique {
            type empty;
          }
        }
        container dns {
          choice dns-choice {
            case dns-address {
              leaf primary {
                type string;
              }
              leaf secondary {
                type string;
              }
            }
            container request {
              presence "true";
              leaf accept {
                type empty;
              }
            }
          }
        }
      }
      container multilink {
        presence "true";
        leaf interleave {
          type empty;
        }
        container links {
          container minimum {
            leaf minimum-value {
              type string;
            }
            leaf mandatory {
              type empty;
            }
          }
        }
        leaf group {
          type string;
        }
        container fragment {
          leaf disable {
            type empty;
          }
          leaf size {
            type string;
          }
          container delay {
            leaf delay-value {
              type string;
            }
            leaf additional-delay-value {
              type string;
            }
          }
        }
        leaf fragmentation {
          type string;
          // NCS drop default statement
        }
        container queue {
          container depth {
            leaf fifo {
              type string;
            }
            leaf qos {
              type string;
            }
          }
        }
        container min-links {
          leaf links {
            type string;
          }
          leaf mandatory {
            type empty;
          }
        }
      }
    }
    leaf multilink-group {
      type string;
    }
    leaf physical-layer {
      type string;
    }
    container async {
      container mode {
        leaf dedicated {
          type empty;
        }
        leaf interactive {
          type empty;
        }
      }
    }
    container pulse-time {
      choice pulse-time-choice {
        leaf seconds {
          type string;
        }
        leaf msec {
          type string;
        }
      }
    }
    container serial {
      container restart-delay {
        leaf seconds {
          type string;
        }
        leaf milliseconds {
          type string;
        }
      }
    }
  }

  grouping ncs_template_interface-switch-grouping0 {
    container switchport {
      presence "true";
      // NCS drop tailf-common:cli-diff-dependency statement
      // NCS drop tailf-common:cli-diff-dependency statement
      // NCS drop tailf-common:cli-diff-dependency statement
      // NCS drop tailf-common:cli-diff-dependency statement
      // NCS drop tailf-common:cli-diff-dependency statement
      // NCS drop tailf-common:cli-diff-dependency statement
      // NCS drop tailf-common:cli-diff-dependency statement
      // NCS drop tailf-common:cli-diff-dependency statement
      container mode {
        choice mode-choice {
          container access {
            presence "true";
          }
          container dot1q-tunnel {
            presence "true";
          }
          leaf dynamic {
            // NCS drop tailf-common:cli-diff-dependency statement
            // NCS drop tailf-common:cli-diff-dependency statement
            type string;
          }
          container trunk {
            // NCS drop tailf-common:cli-diff-dependency statement
            presence "true";
          }
          container private-vlan {
            choice private-vlan-choice {
              leaf host {
                type empty;
              }
              leaf promiscuous {
                type empty;
              }
              container trunk {
                presence "true";
              }
            }
          }
        }
      }
      container trunk {
        leaf encapsulation {
          // NCS drop tailf-common:cli-diff-dependency statement
          type string;
          // NCS drop default statement
        }
        container native {
          leaf vlan {
            type string;
          }
        }
        container allowed {
          container vlan {
            presence "true";
            choice vlan-choice {
              leaf-list vlans {
                // NCS patched for predictable order
                ordered-by user;
                // NCS drop tailf-common:cli-diff-dependency statement
                // NCS drop tailf-common:cli-diff-dependency statement
                type string;
              }
              leaf none {
                type empty;
              }
            }
          }
        }
        container pruning {
          container vlan {
            choice vlan-choice {
              leaf-list vlans {
                // NCS patched for predictable order
                ordered-by user;
                type string;
              }
              leaf none {
                type empty;
              }
            }
          }
        }
      }
      container autostate {
        leaf exclude {
          type empty;
        }
      }
      container private-vlan {
        container trunk {
          container native {
            leaf vlan {
              type string;
            }
          }
          container allowed {
            container vlan {
              choice vlan-choice {
                leaf-list vlans {
                  // NCS patched for predictable order
                  ordered-by user;
                  type string;
                }
                leaf none {
                  type empty;
                }
              }
            }
          }
        }
        container association {
          list trunk {
            // NCS patched for predictable order
            ordered-by user;
            key "primary-vlan-id";
            leaf primary-vlan-id {
              type string;
            }
            leaf secondary-vlan-id {
              type string;
            }
          }
        }
      }
      container access {
        leaf vlan {
          // NCS drop tailf-common:cli-diff-dependency statement
          type string;
          // NCS drop default statement
        }
      }
      container backup {
        list interface {
          // NCS patched for predictable order
          ordered-by user;
          key "name";
          leaf name {
            type string;
          }
          container preemption {
            leaf mode {
              type string;
            }
            leaf delay {
              type string;
            }
          }
        }
      }
      leaf nonegotiate {
        // NCS drop tailf-common:cli-diff-dependency statement
        // NCS drop tailf-common:cli-diff-dependency statement
        // NCS drop tailf-common:cli-diff-dependency statement
        type empty;
      }
      container block {
        leaf multicast {
          type empty;
        }
        leaf unicast {
          type empty;
        }
      }
      container port-security {
        // NCS drop tailf-common:cli-diff-dependency statement
        // NCS drop tailf-common:cli-diff-dependency statement
        presence "true";
        container aging {
          leaf time {
            type string;
          }
          leaf type {
            type string;
          }
        }
        container mac-address {
          leaf sticky {
            type empty;
          }
          leaf hw-address {
            type string;
          }
          leaf vlan {
            type string;
          }
        }
        leaf maximum {
          type string;
        }
        container maximum-vlan {
          leaf maximum {
            type string;
          }
          leaf vlan {
            type empty;
          }
        }
        container maximum-vlan-list {
          list maximum {
            // NCS patched for predictable order
            ordered-by user;
            key "max-addresses vlan";
            leaf max-addresses {
              type string;
            }
            leaf vlan {
              type string;
            }
          }
        }
        leaf violation {
          type string;
        }
      }
      container priority {
        container extend {
          choice trust-choice {
            leaf trust {
              type empty;
            }
            leaf cos {
              type string;
            }
          }
        }
      }
      leaf protected {
        type empty;
      }
      container voice {
        leaf vlan {
          type string;
        }
        container detect {
          container cisco-phone {
            presence "true";
            leaf full-duplex {
              type empty;
            }
          }
        }
      }
      leaf host {
        type empty;
      }
    }
    container l2protocol-tunnel {
      // NCS drop tailf-common:cli-diff-dependency statement
      presence "true";
      leaf cdp {
        type empty;
      }
      container drop-threshold {
        leaf packet-rate {
          type string;
        }
        leaf cdp {
          type string;
        }
        leaf stp {
          type string;
        }
        leaf vtp {
          type string;
        }
      }
      container shutdown-threshold {
        leaf packet-rate {
          type string;
        }
        leaf cdp {
          type string;
        }
        leaf stp {
          type string;
        }
        leaf vtp {
          type string;
        }
        leaf lldp {
          type string;
        }
      }
      leaf stp {
        type empty;
      }
      leaf vtp {
        type empty;
      }
      leaf lldp {
        type empty;
      }
      container point-to-point {
        leaf lacp {
          type empty;
        }
        leaf pagp {
          type empty;
        }
        leaf udld {
          type empty;
        }
      }
    }
  }

  grouping ncs_template_interface-switch-grouping {
    uses ncs_template_interface-switch-grouping0 {
      refine "switchport" {
        // NCS drop tailf-common:cli-diff-dependency statement
      }
    }
  }

  grouping ncs_template_sub-interface-switch-grouping {
    uses ncs_template_interface-switch-grouping0 {
      refine "switchport" {
        // NCS drop tailf-common:cli-diff-dependency statement
      }
    }
  }

  grouping ncs_template_crypto-pki-token-grouping {
    container removal {
      leaf timeout {
        type string;
      }
    }
  }

  grouping ncs_template_router-bgp-max-path-grouping {
    container paths {
      leaf number-of-paths {
        type string;
        // NCS drop default statement
      }
      leaf import {
        type string;
      }
    }
  }

  grouping ncs_template_router-bgp-redistribute-isis-grouping {
    choice osi-ip-choice {
      leaf ip {
        type empty;
      }
      leaf clns {
        type empty;
      }
    }
    leaf level {
      type string;
    }
  }

  grouping ncs_template_router-bgp-redistribute-grouping {
    leaf metric {
      type string;
    }
    leaf subnets {
      type empty;
    }
    leaf route-map {
      type string;
    }
    leaf include-connected {
      type empty;
    }
  }

  grouping ncs_template_router-bgp-redistribute-ospf-grouping {
    leaf metric {
      type string;
    }
    leaf subnets {
      type empty;
    }
    leaf route-map {
      type string;
    }
    leaf include-connected {
      type empty;
    }
    leaf match {
      type empty;
    }
    leaf internal {
      // NCS drop when statement
      type empty;
    }
    container external-1 {
      // NCS drop when statement
      leaf external {
        type string;
      }
    }
    container external-2 {
      // NCS drop when statement
      leaf external {
        type string;
      }
    }
    container nssa-external-1 {
      // NCS drop when statement
      leaf nssa-external {
        type string;
      }
    }
    container nssa-external-2 {
      // NCS drop when statement
      leaf nssa-external {
        type string;
      }
    }
  }

  grouping ncs_template_route-map-metric-grouping {
    leaf route-map {
      type string;
    }
    leaf metric {
      type string;
    }
  }

  grouping ncs_template_router-bgp-neighbor-distribute-list-grouping {
    list distribute-list {
      // NCS patched for predictable order
      ordered-by user;
      // NCS drop tailf-common:cli-diff-dependency statement
      // NCS drop tailf-common:cli-diff-dependency statement
      // NCS drop tailf-common:cli-diff-dependency statement
      // NCS drop tailf-common:cli-diff-dependency statement
      key "direction";
      leaf direction {
        type string;
      }
      uses ncs_template_distribute-list-content-grouping;
    }
    container distribute-list-interface {
      list distribute-list {
        // NCS patched for predictable order
        ordered-by user;
        // NCS drop tailf-common:cli-diff-dependency statement
        // NCS drop tailf-common:cli-diff-dependency statement
        // NCS drop tailf-common:cli-diff-dependency statement
        // NCS drop tailf-common:cli-diff-dependency statement
        key "direction interface";
        leaf direction {
          type string;
        }
        leaf interface {
          // NCS drop tailf-common:cli-diff-dependency statement
          type string;
        }
        uses ncs_template_distribute-list-content-grouping;
      }
    }
  }

  grouping ncs_template_router-bgp-peer-policy-grouping {
    leaf advertisement-interval {
      // NCS drop tailf-common:cli-diff-dependency statement
      // NCS drop tailf-common:cli-diff-dependency statement
      // NCS drop tailf-common:cli-diff-dependency statement
      // NCS drop tailf-common:cli-diff-dependency statement
      type string;
    }
    leaf next-hop-self {
      // NCS drop tailf-common:cli-diff-dependency statement
      // NCS drop tailf-common:cli-diff-dependency statement
      // NCS drop tailf-common:cli-diff-dependency statement
      // NCS drop tailf-common:cli-diff-dependency statement
      type empty;
    }
    container aigp {
      // NCS drop tailf-common:cli-diff-dependency statement
      // NCS drop tailf-common:cli-diff-dependency statement
      // NCS drop tailf-common:cli-diff-dependency statement
      // NCS drop tailf-common:cli-diff-dependency statement
      presence "true";
    }
    container send-community {
      // NCS drop tailf-common:cli-diff-dependency statement
      // NCS drop tailf-common:cli-diff-dependency statement
      // NCS drop tailf-common:cli-diff-dependency statement
      // NCS drop tailf-common:cli-diff-dependency statement
      presence "true";
      leaf send-community-where {
        type string;
      }
    }
    container send-label {
      // NCS drop tailf-common:cli-diff-dependency statement
      // NCS drop tailf-common:cli-diff-dependency statement
      // NCS drop tailf-common:cli-diff-dependency statement
      // NCS drop tailf-common:cli-diff-dependency statement
      presence "true";
      leaf explicit-null {
        type empty;
      }
    }
    container maximum-prefix {
      // NCS drop tailf-common:cli-diff-dependency statement
      // NCS drop tailf-common:cli-diff-dependency statement
      // NCS drop tailf-common:cli-diff-dependency statement
      // NCS drop tailf-common:cli-diff-dependency statement
      leaf max-prefix-no {
        type string;
      }
      leaf threshold {
        type string;
      }
      leaf restart {
        type string;
      }
      leaf warning-only {
        type empty;
      }
    }
    container allowas-in {
      // NCS drop tailf-common:cli-diff-dependency statement
      // NCS drop tailf-common:cli-diff-dependency statement
      // NCS drop tailf-common:cli-diff-dependency statement
      // NCS drop tailf-common:cli-diff-dependency statement
      presence "true";
      leaf as-no {
        type string;
      }
    }
    container as-override {
      // NCS drop tailf-common:cli-diff-dependency statement
      // NCS drop tailf-common:cli-diff-dependency statement
      // NCS drop tailf-common:cli-diff-dependency statement
      // NCS drop tailf-common:cli-diff-dependency statement
      presence "true";
      leaf disable {
        type empty;
      }
    }
    list route-map {
      // NCS patched for predictable order
      ordered-by user;
      // NCS drop tailf-common:cli-diff-dependency statement
      // NCS drop tailf-common:cli-diff-dependency statement
      // NCS drop tailf-common:cli-diff-dependency statement
      // NCS drop tailf-common:cli-diff-dependency statement
      key "direction";
      leaf direction {
        type string;
      }
      leaf route-map-name {
        type string;
      }
    }
    list advertise-map {
      // NCS patched for predictable order
      ordered-by user;
      // NCS drop tailf-common:cli-diff-dependency statement
      // NCS drop tailf-common:cli-diff-dependency statement
      // NCS drop tailf-common:cli-diff-dependency statement
      // NCS drop tailf-common:cli-diff-dependency statement
      key "name";
      leaf name {
        type string;
      }
      list exist-map {
        // NCS patched for predictable order
        ordered-by user;
        key "name";
        leaf name {
          type string;
        }
      }
    }
    container default-originate {
      // NCS drop tailf-common:cli-diff-dependency statement
      // NCS drop tailf-common:cli-diff-dependency statement
      // NCS drop tailf-common:cli-diff-dependency statement
      // NCS drop tailf-common:cli-diff-dependency statement
      presence "true";
      leaf route-map {
        type string;
      }
    }
    list prefix-list {
      // NCS patched for predictable order
      ordered-by user;
      // NCS drop tailf-common:cli-diff-dependency statement
      // NCS drop tailf-common:cli-diff-dependency statement
      // NCS drop tailf-common:cli-diff-dependency statement
      // NCS drop tailf-common:cli-diff-dependency statement
      key "direction";
      leaf direction {
        type string;
      }
      leaf prefix-list-name {
        type string;
      }
    }
    leaf route-reflector-client {
      // NCS drop tailf-common:cli-diff-dependency statement
      // NCS drop tailf-common:cli-diff-dependency statement
      // NCS drop tailf-common:cli-diff-dependency statement
      // NCS drop tailf-common:cli-diff-dependency statement
      type empty;
    }
    leaf soft-reconfiguration {
      // NCS drop tailf-common:cli-diff-dependency statement
      // NCS drop tailf-common:cli-diff-dependency statement
      // NCS drop tailf-common:cli-diff-dependency statement
      // NCS drop tailf-common:cli-diff-dependency statement
      type string;
    }
    container remove-private-as {
      // NCS drop tailf-common:cli-diff-dependency statement
      // NCS drop tailf-common:cli-diff-dependency statement
      // NCS drop tailf-common:cli-diff-dependency statement
      // NCS drop tailf-common:cli-diff-dependency statement
      presence "true";
      leaf all {
        type empty;
      }
      leaf replace-as {
        type empty;
      }
    }
  }

  grouping ncs_template_router-bgp-peer-session-grouping {
    container local-as {
      // NCS drop tailf-common:cli-diff-dependency statement
      // NCS drop tailf-common:cli-diff-dependency statement
      // NCS drop tailf-common:cli-diff-dependency statement
      // NCS drop tailf-common:cli-diff-dependency statement
      presence "true";
      leaf as-no {
        type string;
      }
      leaf no-prepend {
        type empty;
      }
      leaf replace-as {
        type empty;
      }
      leaf dual-as {
        type empty;
      }
    }
    container password {
      // NCS drop tailf-common:cli-diff-dependency statement
      // NCS drop tailf-common:cli-diff-dependency statement
      // NCS drop tailf-common:cli-diff-dependency statement
      // NCS drop tailf-common:cli-diff-dependency statement
      leaf enctype {
        type string;
        // NCS drop default statement
      }
      leaf text {
        type string;
      }
    }
    container ttl-security {
      // NCS drop tailf-common:cli-diff-dependency statement
      // NCS drop tailf-common:cli-diff-dependency statement
      // NCS drop tailf-common:cli-diff-dependency statement
      // NCS drop tailf-common:cli-diff-dependency statement
      leaf hops {
        type string;
      }
    }
    container timers {
      // NCS drop tailf-common:cli-diff-dependency statement
      // NCS drop tailf-common:cli-diff-dependency statement
      // NCS drop tailf-common:cli-diff-dependency statement
      // NCS drop tailf-common:cli-diff-dependency statement
      leaf keepalive-interval {
        type string;
      }
      leaf holdtime {
        type string;
      }
      leaf minimum-neighbor-hold {
        type string;
      }
    }
    container fall-over {
      // NCS drop tailf-common:cli-diff-dependency statement
      // NCS drop tailf-common:cli-diff-dependency statement
      // NCS drop tailf-common:cli-diff-dependency statement
      // NCS drop tailf-common:cli-diff-dependency statement
      presence "true";
      leaf route-map {
        type string;
      }
    }
    container fall-over-bfd {
      container fall-over {
        // NCS drop tailf-common:cli-diff-dependency statement
        // NCS drop tailf-common:cli-diff-dependency statement
        // NCS drop tailf-common:cli-diff-dependency statement
        // NCS drop tailf-common:cli-diff-dependency statement
        // NCS drop tailf-common:cli-diff-dependency statement
        leaf bfd {
          type empty;
        }
      }
    }
    container ebgp-multihop {
      // NCS drop tailf-common:cli-diff-dependency statement
      // NCS drop tailf-common:cli-diff-dependency statement
      // NCS drop tailf-common:cli-diff-dependency statement
      // NCS drop tailf-common:cli-diff-dependency statement
      presence "true";
      leaf max-hop {
        type string;
      }
    }
    container update-source {
      // NCS drop tailf-common:cli-diff-dependency statement
      // NCS drop tailf-common:cli-diff-dependency statement
      // NCS drop tailf-common:cli-diff-dependency statement
      // NCS drop tailf-common:cli-diff-dependency statement
      uses ncs_template_interface-name-grouping;
    }
    container path-attribute {
      list discard {
        // NCS patched for predictable order
        ordered-by user;
        key "id";
        leaf id {
          type string;
        }
        leaf in {
          type empty;
        }
      }
    }
    leaf version {
      // NCS drop tailf-common:cli-diff-dependency statement
      // NCS drop tailf-common:cli-diff-dependency statement
      // NCS drop tailf-common:cli-diff-dependency statement
      // NCS drop tailf-common:cli-diff-dependency statement
      type string;
    }
    container transport {
      leaf connection-mode {
        type string;
      }
      container path-mtu-discovery {
        presence "true";
        leaf disable {
          type empty;
        }
      }
    }
    leaf disable-connected-check {
      // NCS drop tailf-common:cli-diff-dependency statement
      // NCS drop tailf-common:cli-diff-dependency statement
      // NCS drop tailf-common:cli-diff-dependency statement
      // NCS drop tailf-common:cli-diff-dependency statement
      type empty;
    }
  }

  grouping ncs_template_router-bgp-neighbor-grouping {
    leaf remote-as {
      // NCS drop tailf-common:cli-diff-dependency statement
      // NCS drop tailf-common:cli-diff-dependency statement
      type string;
    }
    leaf activate {
      // NCS drop tailf-common:cli-diff-dependency statement
      // NCS drop tailf-common:cli-diff-dependency statement
      // NCS drop tailf-common:cli-diff-dependency statement
      type empty;
    }
    uses ncs_template_router-bgp-peer-session-grouping;
    uses ncs_template_router-bgp-peer-policy-grouping;
    leaf soo {
      // NCS drop tailf-common:cli-diff-dependency statement
      // NCS drop tailf-common:cli-diff-dependency statement
      // NCS drop tailf-common:cli-diff-dependency statement
      // NCS drop tailf-common:cli-diff-dependency statement
      type string;
    }
    container capability {
      // NCS drop tailf-common:cli-diff-dependency statement
      // NCS drop tailf-common:cli-diff-dependency statement
      // NCS drop tailf-common:cli-diff-dependency statement
      // NCS drop tailf-common:cli-diff-dependency statement
      container orf {
        leaf-list prefix-list {
          // NCS patched for predictable order
          ordered-by user;
          // NCS drop max-elements statement
          type string;
        }
      }
    }
    leaf description {
      // NCS drop tailf-common:cli-diff-dependency statement
      // NCS drop tailf-common:cli-diff-dependency statement
      // NCS drop tailf-common:cli-diff-dependency statement
      // NCS drop tailf-common:cli-diff-dependency statement
      type string;
    }
    uses ncs_template_router-bgp-neighbor-distribute-list-grouping;
    leaf dmzlink-bw {
      // NCS drop tailf-common:cli-diff-dependency statement
      // NCS drop tailf-common:cli-diff-dependency statement
      // NCS drop tailf-common:cli-diff-dependency statement
      // NCS drop tailf-common:cli-diff-dependency statement
      type empty;
    }
    list filter-list {
      // NCS patched for predictable order
      ordered-by user;
      // NCS drop tailf-common:cli-diff-dependency statement
      // NCS drop tailf-common:cli-diff-dependency statement
      // NCS drop tailf-common:cli-diff-dependency statement
      // NCS drop tailf-common:cli-diff-dependency statement
      key "direction";
      leaf direction {
        type string;
      }
      leaf as-path-list {
        type string;
      }
    }
    container inherit {
      // NCS drop tailf-common:cli-diff-dependency statement
      // NCS drop tailf-common:cli-diff-dependency statement
      leaf peer-policy {
        // NCS drop tailf-common:cli-diff-dependency statement
        // NCS drop tailf-common:cli-diff-dependency statement
        type string;
      }
      leaf peer-session {
        // NCS drop tailf-common:cli-diff-dependency statement
        // NCS drop tailf-common:cli-diff-dependency statement
        type string;
      }
    }
    container next-hop-self-arg {
      // NCS drop tailf-common:cli-diff-dependency statement
      // NCS drop tailf-common:cli-diff-dependency statement
      // NCS drop tailf-common:cli-diff-dependency statement
      // NCS drop tailf-common:cli-diff-dependency statement
      leaf next-hop-self {
        type string;
      }
    }
    leaf next-hop-unchanged {
      // NCS drop tailf-common:cli-diff-dependency statement
      // NCS drop tailf-common:cli-diff-dependency statement
      // NCS drop tailf-common:cli-diff-dependency statement
      // NCS drop tailf-common:cli-diff-dependency statement
      type empty;
    }
    leaf shutdown {
      // NCS drop tailf-common:cli-diff-dependency statement
      // NCS drop tailf-common:cli-diff-dependency statement
      // NCS drop tailf-common:cli-diff-dependency statement
      // NCS drop tailf-common:cli-diff-dependency statement
      type empty;
    }
    container translate-update {
      // NCS drop tailf-common:cli-diff-dependency statement
      // NCS drop tailf-common:cli-diff-dependency statement
      // NCS drop tailf-common:cli-diff-dependency statement
      // NCS drop tailf-common:cli-diff-dependency statement
      container ipv4 {
        container multicast {
          presence "Address Family modifier";
          leaf unicast {
            type empty;
          }
        }
      }
    }
    leaf unsuppress-map {
      // NCS drop tailf-common:cli-diff-dependency statement
      // NCS drop tailf-common:cli-diff-dependency statement
      // NCS drop tailf-common:cli-diff-dependency statement
      // NCS drop tailf-common:cli-diff-dependency statement
      type string;
    }
    leaf weight {
      // NCS drop tailf-common:cli-diff-dependency statement
      // NCS drop tailf-common:cli-diff-dependency statement
      // NCS drop tailf-common:cli-diff-dependency statement
      // NCS drop tailf-common:cli-diff-dependency statement
      type string;
    }
    container ha-mode {
      // NCS drop tailf-common:cli-diff-dependency statement
      // NCS drop tailf-common:cli-diff-dependency statement
      // NCS drop tailf-common:cli-diff-dependency statement
      // NCS drop tailf-common:cli-diff-dependency statement
      container graceful-restart {
        presence "true";
        leaf disable {
          type empty;
        }
      }
      container sso {
        presence "true";
        leaf disable {
          type empty;
        }
      }
    }
    container suppress-signaling-protocol {
      // NCS drop tailf-common:cli-diff-dependency statement
      // NCS drop tailf-common:cli-diff-dependency statement
      // NCS drop tailf-common:cli-diff-dependency statement
      // NCS drop tailf-common:cli-diff-dependency statement
      leaf ldp {
        type empty;
      }
    }
    leaf prefix-length-size {
      // NCS drop tailf-common:cli-diff-dependency statement
      // NCS drop tailf-common:cli-diff-dependency statement
      // NCS drop tailf-common:cli-diff-dependency statement
      // NCS drop tailf-common:cli-diff-dependency statement
      type string;
    }
  }

  grouping ncs_template_router-bgp-af-grouping {
    leaf synchronization {
      type empty;
    }
    leaf table-map {
      type string;
    }
    container bgp-af {
      container bgp {
        leaf redistribute-internal {
          type empty;
        }
        container dampening {
          presence "true";
          choice dampening-choice {
            leaf route-map {
              type string;
            }
            container dampen {
              leaf half-life-time {
                type string;
              }
              leaf reuse-time {
                type string;
              }
              leaf suppress-time {
                type string;
              }
              leaf max-suppress-time {
                type string;
              }
            }
          }
        }
        container additional-paths {
          choice send-receive-choice {
            leaf receive {
              type empty;
            }
            container send {
              presence "true";
              leaf receive {
                type empty;
              }
            }
          }
          leaf install {
            type empty;
          }
        }
        container bestpath {
          container igp-metric {
            leaf ignore {
              type empty;
            }
          }
        }
        leaf suppress-inactive {
          type empty;
        }
        leaf dmzlink-bw {
          type empty;
        }
        leaf soft-reconfig-backup {
          type empty;
        }
        container nexthop {
          leaf route-map {
            type string;
          }
          container trigger {
            leaf delay {
              type string;
            }
            leaf enable {
              type string;
              // NCS drop default statement
            }
          }
        }
        leaf scan-time {
          type string;
        }
        list inject-map {
          // NCS patched for predictable order
          ordered-by user;
          key "name";
          leaf name {
            type string;
          }
          leaf exist-map {
            type string;
          }
          leaf copy-attributes {
            type empty;
          }
        }
        container recursion {
          leaf host {
            type empty;
          }
        }
      }
    }
    list network {
      // NCS patched for predictable order
      ordered-by user;
      key "number";
      leaf number {
        type string;
      }
      leaf backdoor {
        type empty;
      }
      leaf mask {
        type string;
      }
      leaf route-map {
        type string;
      }
    }
    list aggregate-address {
      // NCS patched for predictable order
      ordered-by user;
      key "address mask";
      leaf address {
        type string;
      }
      leaf mask {
        type string;
      }
      uses ncs_template_router-bgp-aggregate-address-content-grouping;
    }
    container aggregate-addres-ipv6 {
      list aggregate-address {
        // NCS patched for predictable order
        ordered-by user;
        key "address";
        leaf address {
          type string;
        }
        uses ncs_template_router-bgp-aggregate-address-content-grouping;
      }
    }
    container redistribute {
      container bgp {
        leaf as-no {
          type string;
        }
        uses ncs_template_router-bgp-redistribute-grouping {
          refine "metric";
        }
      }
      container connected {
        presence "true";
        uses ncs_template_router-bgp-redistribute-grouping;
      }
      container static {
        presence "true";
        uses ncs_template_router-bgp-redistribute-grouping;
      }
      container dvmrp {
        presence "true";
        uses ncs_template_route-map-metric-grouping;
      }
      list eigrp {
        // NCS patched for predictable order
        ordered-by user;
        key "as-no";
        leaf as-no {
          type string;
        }
        uses ncs_template_router-bgp-redistribute-grouping;
      }
      container isis {
        presence "true";
        uses ncs_template_router-bgp-redistribute-isis-grouping;
        uses ncs_template_router-bgp-redistribute-grouping;
        list isis-list {
          // NCS patched for predictable order
          ordered-by user;
          key "name";
          leaf name {
            type string;
          }
          uses ncs_template_router-bgp-redistribute-isis-grouping;
          uses ncs_template_router-bgp-redistribute-grouping;
        }
      }
      container iso-igrp {
        uses ncs_template_route-map-metric-grouping;
        list iso-igrp-area {
          // NCS patched for predictable order
          ordered-by user;
          key "name";
          leaf name {
            type string;
          }
          uses ncs_template_route-map-metric-grouping;
        }
      }
      container mobile {
        presence "true";
        uses ncs_template_router-bgp-redistribute-grouping;
      }
      container odr {
        presence "true";
        uses ncs_template_router-bgp-redistribute-grouping;
      }
      list ospf {
        // NCS patched for predictable order
        ordered-by user;
        key "id";
        leaf id {
          type string;
        }
        leaf vrf {
          // NCS drop tailf-common:cli-diff-dependency statement
          // NCS drop tailf-common:cli-diff-dependency statement
          type string;
        }
        uses ncs_template_router-bgp-redistribute-ospf-grouping;
      }
      container rip {
        presence "true";
        uses ncs_template_router-bgp-redistribute-grouping;
      }
      container lisp {
        presence "true";
        uses ncs_template_router-bgp-redistribute-grouping;
      }
    }
    container neighbor-tag {
      list neighbor {
        // NCS patched for predictable order
        ordered-by user;
        key "id";
        leaf id {
          type string;
        }
        leaf peer-group {
          type empty;
        }
        uses ncs_template_router-bgp-neighbor-grouping;
      }
    }
    list neighbor {
      // NCS patched for predictable order
      ordered-by user;
      // NCS drop tailf-common:cli-diff-dependency statement
      key "id";
      leaf id {
        type string;
      }
      leaf peer-group {
        type string;
      }
      uses ncs_template_router-bgp-neighbor-grouping;
    }
    container maximum-paths {
      uses ncs_template_router-bgp-max-path-grouping;
      container eibgp {
        uses ncs_template_router-bgp-max-path-grouping;
      }
      container ibgp {
        choice ibgp-choice {
          // NCS drop default statement
          case a {
            container unequal-cost {
              uses ncs_template_router-bgp-max-path-grouping;
            }
          }
          case b {
            uses ncs_template_router-bgp-max-path-grouping;
          }
        }
      }
      leaf import {
        type string;
      }
    }
    container import {
      container path {
        container selection {
          choice selection-choice {
            leaf all {
              type empty;
            }
            container bestpath {
              presence "true";
              leaf strict {
                type empty;
              }
            }
            container multipaths {
              presence "true";
              leaf strict {
                type empty;
              }
            }
          }
        }
        leaf limit {
          type string;
        }
      }
    }
    container default-information {
      leaf originate {
        type empty;
      }
    }
    leaf default-metric {
      type string;
    }
    uses ncs_template_router-distribute-list-grouping;
    container distance {
      container bgp {
        leaf extern-as {
          type string;
        }
        leaf internal-as {
          type string;
        }
        leaf local {
          type string;
        }
      }
      list adm-distance {
        // NCS patched for predictable order
        ordered-by user;
        key "srcip wildbits";
        leaf distance {
          type string;
        }
        leaf srcip {
          type string;
        }
        leaf wildbits {
          type string;
        }
        leaf access-list {
          type string;
        }
      }
    }
    leaf auto-summary {
      type string;
    }
  }

  grouping ncs_template_router-bgp-bgp-grouping {
    container bgp {
      leaf router-id {
        type string;
      }
      leaf fast-external-fallover {
        type string;
        // NCS drop default statement
      }
      leaf always-compare-med {
        type empty;
      }
      leaf cluster-id {
        type string;
      }
      container transport {
        leaf path-mtu-discovery {
          type string;
          // NCS drop default statement
        }
      }
      leaf enforce-first-as {
        type string;
        // NCS drop default statement
      }
      container client-to-client {
        leaf reflection {
          type string;
          // NCS drop default statement
        }
      }
      leaf log-neighbor-changes {
        type string;
      }
      container confederation {
        leaf identifier {
          type string;
        }
        container peers {
          leaf-list as-no {
            // NCS patched for predictable order
            ordered-by user;
            type string;
          }
        }
      }
      leaf deterministic-med {
        type empty;
      }
      container listen {
        list range {
          // NCS patched for predictable order
          ordered-by user;
          key "network-length";
          leaf network-length {
            type string;
          }
          leaf peer-group {
            type string;
          }
        }
        leaf limit {
          type string;
        }
      }
      leaf update-delay {
        type string;
      }
      container graceful-restart-conf {
        container graceful-restart {
          leaf restart-time {
            type string;
            // NCS drop default statement
          }
          leaf stalepath-time {
            type string;
            // NCS drop default statement
          }
        }
      }
      leaf graceful-restart {
        type empty;
      }
      container regexp {
        leaf deterministic {
          type string;
          // NCS drop default statement
        }
      }
      container bestpath {
        leaf compare-routerid {
          type empty;
        }
        container cost-community {
          leaf ignore {
            type empty;
          }
        }
        container med {
          choice med-choice {
            container confed {
              presence "Compare MED among confederation paths";
              leaf missing-at-worst {
                type empty;
              }
            }
            leaf missing-at-worst {
              type empty;
            }
          }
        }
        container as-path {
          leaf multipath-relax {
            type empty;
          }
        }
      }
      leaf maxas-limit {
        type string;
      }
      container default {
        leaf ipv4-unicast {
          type string;
          // NCS drop default statement
        }
        leaf ipv4-activate {
          type string;
          // NCS drop default statement
        }
        leaf local-preference {
          type string;
        }
        container route-target {
          leaf filter {
            type string;
            // NCS drop default statement
          }
        }
      }
    }
    container timers {
      container bgp {
        leaf keepalive {
          type string;
        }
        leaf holdtime {
          type string;
        }
        leaf min-holdtime {
          type string;
        }
      }
    }
  }

  grouping ncs_template_router-ospf-af-grouping;

  grouping ncs_template_router-ospfv3-af-grouping {
    container capability {
      leaf vrf-lite {
        type empty;
      }
    }
    container discard-route {
      leaf external {
        type string;
        // NCS drop default statement
      }
      leaf internal {
        type string;
        // NCS drop default statement
      }
    }
  }

  grouping ncs_template_router-ospf-common-af-grouping {
    container default-information {
      container originate {
        presence "true";
        leaf always {
          type empty;
        }
        leaf metric {
          type string;
        }
        leaf metric-type {
          type string;
          // NCS drop default statement
        }
        leaf route-map {
          type string;
        }
      }
    }
    leaf default-metric {
      type string;
    }
    container distance {
      leaf weight {
        type string;
      }
      list distance-list {
        // NCS patched for predictable order
        ordered-by user;
        key "ip-address wildcard-mask";
        leaf ip-address {
          type string;
        }
        leaf wildcard-mask {
          type string;
        }
        leaf weight {
          type string;
        }
        leaf access-list {
          type string;
        }
      }
      container ospf {
        leaf intra-area {
          type string;
        }
        leaf inter-area {
          type string;
        }
        leaf external {
          type string;
        }
      }
    }
    leaf maximum-paths {
      type string;
    }
    leaf nsr {
      type empty;
    }
    container redistribute {
      container connected {
        presence "true";
        uses ncs_template_router-ospf-redistribute-grouping;
        uses ncs_template_router-ospf-route-map-grouping;
      }
      container static {
        presence "true";
        uses ncs_template_router-ospf-redistribute-grouping;
        uses ncs_template_router-ospf-route-map-grouping;
      }
      container odr {
        presence "true";
        uses ncs_template_router-ospf-redistribute-grouping;
        uses ncs_template_router-ospf-route-map-grouping;
      }
      container bgp {
        leaf as-no {
          // NCS drop tailf-common:cli-diff-dependency statement
          type string;
        }
        uses ncs_template_router-ospf-redistribute-grouping {
          refine "metric";
        }
        uses ncs_template_router-ospf-route-map-grouping;
      }
      list ospf {
        // NCS patched for predictable order
        ordered-by user;
        key "id";
        leaf id {
          type string;
        }
        uses ncs_template_router-ospf-redistribute-grouping;
        uses ncs_template_redistribute-ospf-match-grouping;
        uses ncs_template_router-ospf-route-map-grouping;
      }
      container isis {
        presence "true";
        uses ncs_template_router-isis-level-grouping;
        uses ncs_template_router-ospf-redistribute-grouping;
        uses ncs_template_router-ospf-route-map-grouping;
        list isis-area {
          // NCS patched for predictable order
          ordered-by user;
          key "name";
          leaf name {
            type string;
          }
          uses ncs_template_router-isis-level-grouping;
          uses ncs_template_router-ospf-redistribute-grouping;
          uses ncs_template_router-ospf-route-map-grouping;
        }
      }
      list eigrp {
        // NCS patched for predictable order
        ordered-by user;
        key "as-no";
        leaf as-no {
          type string;
        }
        uses ncs_template_router-ospf-redistribute-grouping;
        uses ncs_template_router-ospf-route-map-grouping;
      }
      container iso-igrp {
        presence "true";
        leaf area-tag {
          type string;
        }
        uses ncs_template_router-ospf-route-map-grouping;
        uses ncs_template_router-ospf-redistribute-grouping;
      }
      container maximum-prefix {
        leaf number {
          type string;
        }
        container threshold-warning-only-container {
          leaf threshold {
            type string;
          }
          leaf warning-only {
            type empty;
          }
        }
      }
      container mobile {
        presence "true";
        uses ncs_template_router-ospf-redistribute-grouping;
        uses ncs_template_router-ospf-route-map-grouping;
      }
      container rip {
        presence "true";
        uses ncs_template_router-ospf-redistribute-grouping;
        uses ncs_template_router-ospf-route-map-grouping;
        list redistribute-list-rip {
          // NCS patched for predictable order
          ordered-by user;
          key "name";
          leaf name {
            type string;
          }
          uses ncs_template_router-ospf-redistribute-grouping;
          uses ncs_template_router-ospf-route-map-grouping;
        }
      }
      container lisp {
        container subnets {
          presence "true";
        }
      }
    }
  }

  grouping ncs_template_router-ospf-common-grouping {
    list area {
      // NCS patched for predictable order
      ordered-by user;
      key "id";
      leaf id {
        type string;
      }
      container authentication {
        presence "true";
        leaf message-digest {
          type empty;
        }
        choice authentication-choice {
          leaf null {
            type empty;
          }
          leaf key-chain {
            type string;
          }
        }
      }
      container nssa {
        // NCS drop tailf-common:cli-diff-dependency statement
        presence "true";
        leaf no-redistribution {
          type empty;
        }
        leaf default-information-originate {
          type empty;
        }
        leaf metric {
          // NCS drop when statement
          type string;
        }
        leaf metric-type {
          type string;
          // NCS drop default statement
        }
        leaf nssa-only {
          type empty;
        }
        leaf no-ext-capability {
          type empty;
        }
        leaf no-summary {
          type empty;
        }
        container translate {
          container type7 {
            leaf always {
              type empty;
            }
            leaf suppress-fa {
              type empty;
            }
          }
        }
      }
      leaf default-cost {
        type string;
      }
      list filter-list {
        // NCS patched for predictable order
        ordered-by user;
        key "direction";
        leaf direction {
          type string;
        }
        leaf prefix {
          type string;
        }
      }
      list range {
        // NCS patched for predictable order
        ordered-by user;
        key "ip mask";
        leaf ip {
          type string;
        }
        leaf mask {
          type string;
        }
        leaf advertise {
          type string;
          // NCS drop default statement
        }
        leaf cost {
          type string;
        }
      }
      container range-ipv6 {
        list range {
          // NCS patched for predictable order
          ordered-by user;
          key "prefix";
          leaf prefix {
            type string;
          }
          leaf advertise {
            type string;
            // NCS drop default statement
          }
          leaf cost {
            type string;
          }
        }
      }
      list sham-link {
        // NCS patched for predictable order
        ordered-by user;
        key "source dest";
        leaf source {
          type string;
        }
        leaf dest {
          type string;
        }
        leaf cost {
          type string;
        }
      }
      container stub {
        // NCS drop tailf-common:cli-diff-dependency statement
        presence "true";
        leaf no-summary {
          type empty;
        }
        leaf no-ext-capability {
          type empty;
        }
      }
      list virtual-link {
        // NCS patched for predictable order
        ordered-by user;
        key "id";
        leaf id {
          type string;
        }
        leaf retransmit-interval {
          type string;
        }
        leaf transmit-delay {
          type string;
          // NCS drop default statement
        }
        leaf hello-interval {
          type string;
        }
        leaf dead-interval {
          type string;
        }
        leaf authentication {
          type empty;
        }
        container authentication-key {
          uses ncs_template_password-grouping;
        }
        list message-digest-key {
          // NCS patched for predictable order
          ordered-by user;
          key "id";
          leaf id {
            type string;
          }
          container md5 {
            leaf auth-type {
              type string;
              // NCS drop default statement
            }
            leaf auth-key {
              type string;
            }
          }
        }
      }
    }
    container auto-cost {
      presence "Calculate OSPF interface cost according to bandwidth";
      leaf reference-bandwidth {
        type string;
      }
    }
    container bfd {
      leaf all-interfaces {
        type empty;
      }
    }
    container interface-id {
      leaf snmp-if-index {
        type empty;
      }
    }
    container log-adjacency-changes {
      presence "true";
      leaf detail {
        type empty;
      }
    }
    container max-lsa {
      leaf maximum-number {
        type string;
      }
      leaf threshold-percentage {
        type string;
      }
      leaf warning-only {
        type empty;
      }
      leaf ignore-time {
        type string;
      }
      leaf reset-time {
        type string;
        // NCS drop default statement
      }
      leaf ignore-count {
        type string;
      }
    }
    uses ncs_template_passive-interface-grouping;
    container queue-depth {
      leaf hello {
        type string;
        // NCS drop default statement
      }
      leaf update {
        type string;
      }
    }
    container timers {
      container lsa {
        leaf arrival {
          type string;
        }
      }
      container pacing {
        leaf flood {
          type string;
        }
        leaf lsa-group {
          type string;
        }
        leaf retransmission {
          type string;
        }
      }
      container throttle {
        container lsa {
          leaf all {
            type empty;
          }
          leaf start-interval {
            type string;
          }
          leaf hold-interval {
            type string;
          }
          leaf max-interval {
            type string;
          }
        }
        container spf {
          leaf spf-start {
            type string;
          }
          leaf spf-hold {
            type string;
          }
          leaf spf-max-wait {
            type string;
          }
        }
      }
    }
    leaf router-id {
      type string;
    }
  }

  grouping ncs_template_router-ospf-grouping {
    container capability {
      leaf vrf-lite {
        type empty;
      }
      leaf opaque {
        type string;
        // NCS drop default statement
      }
      leaf lls {
        type string;
        // NCS drop default statement
      }
      leaf transit {
        type string;
        // NCS drop default statement
      }
    }
    container compatible {
      leaf rfc1583 {
        type string;
        // NCS drop default statement
      }
    }
    uses ncs_template_router-distribute-list-grouping;
    container domain-id {
      choice domain-id-choice {
        case a {
          leaf ip-format {
            type string;
          }
          container ip-format-secondary {
            leaf ip {
              type string;
            }
            leaf secondary {
              type empty;
            }
          }
        }
        leaf Null {
          type empty;
        }
        container type {
          leaf type-leaf {
            type string;
          }
          leaf value {
            type string;
          }
        }
      }
    }
    leaf domain-tag {
      type string;
    }
    container ignore {
      container lsa {
        leaf mospf {
          type empty;
        }
      }
    }
    leaf ispf {
      type empty;
    }
    container limit {
      container retransmissions {
        leaf dc {
          type string;
        }
        leaf non-dc {
          type string;
        }
      }
    }
    container local-rib-criteria {
      leaf forwarding-address {
        type empty;
      }
      leaf inter-area-summary {
        type empty;
      }
      leaf nssa-translation {
        type empty;
      }
    }
    container max-metric {
      container router-lsa {
        presence "true";
        leaf include-stub {
          type empty;
        }
        leaf summary-lsa {
          type empty;
        }
        leaf summary-lsa-max-metric-value {
          // NCS drop when statement
          type string;
        }
        leaf external-lsa {
          type empty;
        }
        leaf external-lsa-max-metric-value {
          // NCS drop when statement
          type string;
        }
        container on-startup {
          choice time-wait-for-bgp-choice {
            leaf seconds {
              type string;
            }
            leaf wait-for-bgp {
              type empty;
            }
          }
        }
      }
    }
    container mpls {
      container ldp {
        container autoconfig {
          presence "Configure LDP automatic configuration";
          leaf area {
            type string;
          }
        }
        container sync {
          presence "Configure LDP-IGP Synchronization";
        }
      }
      container traffic-eng {
        container router-id {
          uses ncs_template_interface-name-grouping;
        }
        leaf area {
          type string;
        }
        leaf multicast-intact {
          type empty;
        }
        container interface {
          container name {
            uses ncs_template_interface-name-grouping;
          }
          leaf area {
            type string;
          }
        }
        list mesh-group {
          // NCS patched for predictable order
          ordered-by user;
          key "id area";
          leaf id {
            type string;
          }
          leaf area {
            type string;
          }
          leaf interface {
            type string;
          }
        }
      }
    }
    list neighbor {
      // NCS patched for predictable order
      ordered-by user;
      key "ip";
      leaf ip {
        type string;
      }
      container cost-database-filter-container {
        leaf cost {
          type string;
        }
        container database-filter {
          container all {
            leaf out {
              type empty;
            }
          }
        }
      }
      container poll-interval-priority-container {
        leaf poll-interval {
          type string;
        }
        leaf priority {
          type string;
        }
      }
    }
    list network {
      // NCS patched for predictable order
      ordered-by user;
      key "ip mask";
      leaf ip {
        type string;
      }
      leaf mask {
        type string;
      }
      leaf area {
        type string;
      }
    }
    container nsf {
      presence "true";
      container cisco {
        presence "true";
        container helper {
          presence "true";
          leaf disable {
            type empty;
          }
        }
      }
      container ietf {
        container helper {
          presence "helper support";
          leaf disable {
            type empty;
          }
          leaf strict-lsa-checking {
            type empty;
          }
        }
      }
    }
    container prefix-priority {
      container high {
        leaf route-map {
          type string;
        }
      }
    }
    leaf prefix-suppression {
      type empty;
    }
    container process-min-time {
      leaf percent {
        type string;
      }
    }
    container traffic-share {
      container min {
        leaf across-interfaces {
          type empty;
        }
      }
    }
    leaf shutdown {
      type string;
    }
    list summary-address {
      // NCS patched for predictable order
      ordered-by user;
      key "ip wildcard";
      leaf ip {
        type string;
      }
      leaf wildcard {
        type string;
      }
      choice tag-no-advertise-choice {
        leaf tag {
          type string;
        }
        leaf not-advertise {
          type empty;
        }
      }
    }
    container discard-route {
      presence "true";
      leaf external {
        type string;
      }
      leaf internal {
        type string;
      }
    }
    container fast-reroute {
      leaf keep-all-paths {
        type empty;
      }
      container per-prefix {
        container enable {
          list area {
            // NCS patched for predictable order
            ordered-by user;
            key "area";
            leaf area {
              type string;
            }
            leaf prefix-priority {
              type string;
            }
          }
          leaf prefix-priority {
            type string;
          }
        }
        container remote-lfa {
          leaf area {
            type string;
          }
          leaf maximum-cost {
            type string;
          }
          leaf tunnel {
            type string;
          }
        }
      }
    }
  }

  grouping ncs_template_router-ospfv3-grouping {
    list summary-prefix {
      // NCS patched for predictable order
      ordered-by user;
      key "prefix";
      leaf prefix {
        type string;
      }
    }
  }

  grouping ncs_template_ospf-redistribute-match-grouping {
    leaf metric {
      type string;
    }
    leaf subnets {
      type empty;
    }
    leaf route-map {
      type string;
    }
    leaf tag {
      type string;
    }
  }

  grouping ncs_template_router-isis-level-grouping {
    leaf level {
      type string;
    }
  }

  grouping ncs_template_router-ospf-route-map-grouping {
    leaf route-map {
      type string;
    }
  }

  grouping ncs_template_router-ospf-redistribute-grouping {
    leaf metric {
      type string;
    }
    leaf metric-type {
      type string;
      // NCS drop default statement
    }
    leaf subnets {
      type empty;
    }
    leaf nssa-only {
      type empty;
    }
    leaf tag {
      type string;
    }
  }

  grouping ncs_template_router-rip-af-grouping {
    leaf auto-summary {
      type string;
      // NCS drop default statement
    }
    leaf maximum-paths {
      type string;
    }
    list neighbor {
      // NCS patched for predictable order
      ordered-by user;
      key "ip";
      leaf ip {
        type string;
      }
    }
    list network {
      // NCS patched for predictable order
      ordered-by user;
      key "ip";
      leaf ip {
        type string;
      }
    }
    leaf validate-update-source {
      type string;
      // NCS drop default statement
    }
    container default-information {
      container originate {
        presence "true";
        leaf route-map {
          type string;
        }
      }
    }
    leaf default-metric {
      type string;
    }
    container distance {
      leaf distance-leaf {
        type string;
      }
      list distance-list {
        // NCS patched for predictable order
        ordered-by user;
        key "ip mask";
        leaf number {
          type string;
        }
        leaf ip {
          type string;
        }
        leaf mask {
          type string;
        }
        leaf access-list {
          type string;
        }
      }
    }
    uses ncs_template_router-distribute-list-grouping;
    uses ncs_template_router-offset-list-grouping;
    container redistribute {
      container connected {
        presence "true";
        uses ncs_template_router-rip-redistribute-grouping;
      }
      container bgp {
        leaf as-no {
          type string;
        }
        uses ncs_template_router-rip-redistribute-grouping;
      }
      list eigrp {
        // NCS patched for predictable order
        ordered-by user;
        key "as-no";
        leaf as-no {
          type string;
        }
        uses ncs_template_router-rip-redistribute-grouping;
      }
      container isis {
        presence "true";
        list isis-list {
          // NCS patched for predictable order
          ordered-by user;
          key "name";
          leaf name {
            type string;
          }
          leaf level {
            type string;
          }
          uses ncs_template_router-rip-redistribute-grouping;
        }
        leaf level {
          type string;
        }
        uses ncs_template_router-rip-redistribute-grouping;
      }
      container iso-igrp {
        presence "true";
        list iso-igrp-list {
          // NCS patched for predictable order
          ordered-by user;
          key "name";
          leaf name {
            type string;
          }
          uses ncs_template_router-rip-redistribute-grouping;
        }
        uses ncs_template_router-rip-redistribute-grouping;
      }
      container mobile {
        presence "Mobile routes";
        uses ncs_template_router-rip-redistribute-grouping;
      }
      container odr {
        presence "On Demand stub Routes";
        uses ncs_template_router-rip-redistribute-grouping;
      }
      list ospf {
        // NCS patched for predictable order
        ordered-by user;
        key "id";
        leaf id {
          type string;
        }
        uses ncs_template_router-rip-redistribute-grouping;
        uses ncs_template_redistribute-ospf-match-grouping;
      }
      container static {
        presence "Static routes";
        uses ncs_template_router-rip-redistribute-grouping;
      }
      container rip {
        presence "true";
        uses ncs_template_router-rip-redistribute-grouping;
      }
    }
    container timers {
      container basic {
        leaf updates {
          type string;
        }
        leaf invalid {
          type string;
        }
        leaf holddown {
          type string;
        }
        leaf flush {
          type string;
        }
        leaf sleep {
          type string;
        }
      }
    }
    leaf version {
      type string;
    }
    container traffic-share {
      container min {
        leaf across-interfaces {
          type empty;
        }
      }
    }
  }

  grouping ncs_template_router-rip-grouping {
    uses ncs_template_router-rip-af-grouping;
    uses ncs_template_passive-interface-grouping;
    leaf output-delay {
      type string;
    }
    leaf input-queue {
      type string;
    }
    leaf flash-update-threshold {
      type string;
    }
  }

  grouping ncs_template_router-rip-redistribute-grouping {
    leaf metric {
      type string;
    }
    leaf route-map {
      type string;
    }
  }

  grouping ncs_template_router-eigrp-redistribute-grouping {
    container metric {
      leaf bandwidth-metric {
        type string;
      }
      leaf delay-metric {
        type string;
      }
      leaf reliability-metric {
        type string;
      }
      leaf effective-bandwidth-metric {
        type string;
      }
      leaf mtu-bytes {
        type string;
      }
    }
    leaf route-map {
      type string;
    }
  }

  grouping ncs_template_router-eigrp-grouping {
    container metric {
      leaf maximum-hops {
        type string;
      }
      container weights {
        leaf tos {
          type string;
        }
        leaf k1 {
          type string;
        }
        leaf k2 {
          type string;
        }
        leaf k3 {
          type string;
        }
        leaf k4 {
          type string;
        }
        leaf k5 {
          type string;
        }
      }
    }
    container network-ip {
      list network {
        // NCS patched for predictable order
        ordered-by user;
        key "ip";
        leaf ip {
          type string;
        }
      }
    }
    list network {
      // NCS patched for predictable order
      ordered-by user;
      key "ip mask";
      leaf ip {
        type string;
      }
      leaf mask {
        type string;
      }
    }
    container neighbor {
      list neighbor-list {
        // NCS patched for predictable order
        ordered-by user;
        key "address interface";
        leaf address {
          type string;
        }
        leaf interface {
          // NCS drop tailf-common:cli-diff-dependency statement
          type string;
        }
      }
    }
    container eigrp {
      leaf router-id {
        type string;
      }
      container stub {
        leaf connected {
          type empty;
        }
        leaf static {
          type empty;
        }
        leaf summary {
          type empty;
        }
        leaf redistributed {
          type empty;
        }
      }
      leaf stub-site {
        type string;
      }
    }
  }

  grouping ncs_template_router-eigrp-base-grouping {
    uses ncs_template_router-distribute-list-grouping;
    container default-metric {
      leaf bandwidth {
        type string;
      }
      leaf delay {
        type string;
      }
      leaf reliability {
        type string;
      }
      leaf loading {
        type string;
      }
      leaf mtu {
        type string;
      }
    }
    list summary-metric {
      // NCS patched for predictable order
      ordered-by user;
      key "prefix";
      leaf prefix {
        type string;
      }
      leaf bandwidth {
        type string;
      }
      leaf delay {
        // NCS drop when statement
        type string;
      }
      leaf reliability {
        // NCS drop when statement
        type string;
      }
      leaf load {
        // NCS drop when statement
        type string;
      }
      leaf mtu {
        // NCS drop when statement
        type string;
      }
      leaf distance {
        type string;
      }
    }
    uses ncs_template_router-offset-list-grouping;
    container redistribute {
      container connected {
        presence "true";
        uses ncs_template_router-eigrp-redistribute-grouping;
      }
      container bgp {
        leaf as-no {
          type string;
        }
        uses ncs_template_router-eigrp-redistribute-grouping;
      }
      list eigrp {
        // NCS patched for predictable order
        ordered-by user;
        key "as-no";
        leaf as-no {
          type string;
        }
        uses ncs_template_router-eigrp-redistribute-grouping;
      }
      container isis {
        presence "true";
        list isis-list {
          // NCS patched for predictable order
          ordered-by user;
          key "name";
          leaf name {
            type string;
          }
          leaf level {
            type string;
          }
          uses ncs_template_router-eigrp-redistribute-grouping;
        }
        leaf level {
          type string;
        }
        uses ncs_template_router-eigrp-redistribute-grouping;
      }
      container iso-igrp {
        presence "true";
        list iso-igrp-list {
          // NCS patched for predictable order
          ordered-by user;
          key "name";
          leaf name {
            type string;
          }
          uses ncs_template_router-eigrp-redistribute-grouping;
        }
        uses ncs_template_router-eigrp-redistribute-grouping;
      }
      container mobile {
        presence "true";
        uses ncs_template_router-eigrp-redistribute-grouping;
      }
      container odr {
        presence "true";
        uses ncs_template_router-eigrp-redistribute-grouping;
      }
      list ospf {
        // NCS patched for predictable order
        ordered-by user;
        key "id";
        leaf id {
          type string;
        }
        uses ncs_template_redistribute-ospf-match-grouping;
        uses ncs_template_router-eigrp-redistribute-grouping;
      }
      container static {
        presence "Static routes";
        uses ncs_template_router-eigrp-redistribute-grouping;
      }
      container rip {
        presence "true";
        uses ncs_template_router-eigrp-redistribute-grouping;
      }
    }
    container distance {
      container eigrp {
        leaf internal-distance {
          type string;
        }
        leaf external-distance {
          type string;
        }
      }
      list distance-list {
        // NCS patched for predictable order
        ordered-by user;
        key "ip-address wildcard-mask";
        leaf ip-address {
          type string;
        }
        leaf wildcard-mask {
          type string;
        }
        leaf weight {
          type string;
        }
        leaf access-list {
          type string;
        }
      }
    }
    leaf auto-summary {
      type empty;
    }
    uses ncs_template_passive-interface-grouping;
  }

  grouping ncs_template_router-eigrp-af-virtual-instance-grouping {
    list af-interface {
      // NCS patched for predictable order
      ordered-by user;
      key "name";
      leaf name {
        type string;
      }
      list summary-address {
        // NCS patched for predictable order
        ordered-by user;
        key "ip mask";
        leaf ip {
          type string;
        }
        leaf mask {
          type string;
        }
        leaf leak-map {
          type string;
        }
      }
      container summary-address-ipv6 {
        list summary-address {
          // NCS patched for predictable order
          ordered-by user;
          key "ipv6";
          leaf ipv6 {
            type string;
          }
          leaf leak-map {
            type string;
          }
        }
      }
      container authentication {
        container mode {
          leaf md5 {
            type empty;
          }
        }
        leaf key-chain {
          type string;
        }
      }
      leaf hello-interval {
        type string;
      }
      leaf hold-time {
        type string;
      }
      leaf next-hop-self {
        type string;
        // NCS drop default statement
      }
      leaf passive-interface {
        type empty;
      }
      leaf split-horizon {
        type string;
        // NCS drop default statement
      }
      container stub-site {
        leaf wan-interface {
          type empty;
        }
      }
    }
    container topology {
      container base {
        presence "true";
        uses ncs_template_router-eigrp-base-grouping;
      }
    }
    uses ncs_template_router-eigrp-grouping;
  }

  grouping ncs_template_narrow-wide-transition-grouping {
    leaf transition {
      type empty;
    }
    leaf level {
      type string;
    }
  }

  grouping ncs_template_spf-intervals-grouping {
    leaf interval {
      type string;
    }
    leaf initial-wait {
      type string;
    }
    leaf minimum-wait {
      type string;
    }
  }

  grouping ncs_template_router-isis-authenticate-snp-grouping {
    leaf authenticate {
      type empty;
    }
    leaf snp {
      type string;
    }
  }

  grouping ncs_template_lsp-gen-interval-grouping {
    leaf interval {
      type string;
    }
    leaf initial-wait {
      type string;
    }
    leaf wait {
      type string;
    }
  }

  grouping ncs_template_set-overload-bit-suppress-grouping {
    leaf external {
      type empty;
    }
    leaf interlevel {
      type empty;
    }
  }

  grouping ncs_template_authentication-level-grouping {
    leaf level {
      type string;
    }
  }

  grouping ncs_template_redist-level-grouping {
    leaf level {
      type string;
    }
  }

  grouping ncs_template_router-isis-redistribute-grouping {
    leaf metric {
      type string;
    }
    leaf route-map {
      type string;
    }
    leaf metric-type {
      type string;
      // NCS drop default statement
    }
    uses ncs_template_router-isis-level-grouping;
  }

  grouping ncs_template_router-isis-af-redistribute-grouping {
    leaf metric {
      type string;
    }
    leaf metric-type {
      type string;
    }
    uses ncs_template_router-isis-level-grouping;
    leaf route-map {
      type string;
    }
    leaf include-connected {
      type empty;
    }
  }

  grouping ncs_template_isis-redist-ospf-match-grouping {
    uses ncs_template_redist-level-grouping;
    leaf metric {
      type string;
    }
    leaf route-map {
      type string;
    }
  }

  grouping ncs_template_router-isis-interface-grouping {
    container authentication {
      container mode {
        container md5 {
          presence "true";
          uses ncs_template_authentication-level-grouping;
        }
        container text {
          presence "true";
          uses ncs_template_authentication-level-grouping;
        }
      }
      container key-chain {
        leaf name {
          type string;
        }
        uses ncs_template_authentication-level-grouping;
      }
      container send-only {
        presence "true";
        uses ncs_template_authentication-level-grouping;
      }
    }
  }

  grouping ncs_template_router-isis-af-grouping {
    leaf adjacency-check {
      type string;
      // NCS drop default statement
    }
    container set-overload-bit {
      presence "true";
      choice set-overload-bit-choice {
        container on-startup {
          choice on-startup-choice {
            container time {
              leaf time {
                type string;
              }
              leaf suppress {
                type empty;
              }
              uses ncs_template_set-overload-bit-suppress-grouping;
            }
            container wait-for-bgp {
              presence "Let BGP decide when to unset the overload bitW";
              container suppress {
                uses ncs_template_set-overload-bit-suppress-grouping;
              }
            }
          }
        }
        container suppress {
          uses ncs_template_set-overload-bit-suppress-grouping;
        }
      }
    }
    container spf-interval {
      choice spf-interval-choice {
        list level-1-2 {
          // NCS patched for predictable order
          ordered-by user;
          key "level";
          leaf level {
            type string;
          }
          uses ncs_template_spf-intervals-grouping;
        }
        container intervals {
          uses ncs_template_spf-intervals-grouping;
        }
      }
    }
    container prc-interval {
      leaf interval {
        type string;
      }
      leaf initial-wait {
        type string;
      }
      leaf minimum-wait {
        type string;
      }
    }
    container metric-style {
      choice metric-style-choice {
        container narrow {
          presence "true";
          uses ncs_template_narrow-wide-transition-grouping;
        }
        container transition {
          presence "true";
          leaf level {
            type string;
          }
        }
        container wide {
          presence "true";
          uses ncs_template_narrow-wide-transition-grouping;
        }
      }
    }
    choice metric-choice {
      case default-case {
        container metric {
          // NCS drop tailf-common:cli-diff-dependency statement
          leaf default {
            type string;
          }
        }
      }
      case level-case {
        container metric-level {
          // NCS drop tailf-common:cli-diff-dependency statement
          list metric {
            // NCS patched for predictable order
            ordered-by user;
            key "level";
            leaf level {
              type string;
            }
            leaf default {
              type string;
            }
          }
        }
      }
    }
    leaf maximum-paths {
      type string;
    }
    container default-information {
      container originate {
        presence "true";
        leaf route-map {
          type string;
        }
      }
    }
  }

  grouping ncs_template_router-isis-grouping {
    container protocol {
      leaf shutdown {
        type empty;
      }
    }
    leaf max-area-addresses {
      type string;
    }
    list net {
      // NCS patched for predictable order
      ordered-by user;
      key "tag";
      leaf tag {
        type string;
      }
    }
    leaf is-type {
      type string;
    }
    container advertise {
      leaf passive-only {
        type empty;
      }
    }
    uses ncs_template_router-isis-interface-grouping;
    container area-password {
      leaf name {
        type string;
      }
      uses ncs_template_router-isis-authenticate-snp-grouping;
    }
    container ispf {
      leaf level {
        type string;
      }
      leaf number {
        type string;
      }
    }
    container fast-flood {
      presence "Flood LSPs (that triggered SPF) before running SPF";
      leaf number {
        type string;
      }
    }
    container ip {
      container route {
        container priority {
          container high {
            leaf tag {
              type string;
            }
          }
        }
      }
    }
    container set-attached-bit {
      leaf route-map {
        type string;
      }
    }
    leaf max-lsp-lifetime {
      type string;
    }
    leaf lsp-refresh-interval {
      type string;
    }
    container lsp-gen-interval {
      choice lsp-gen-interval-choice {
        container intervals {
          uses ncs_template_lsp-gen-interval-grouping;
        }
        container intervals-levels {
          container intervals-level-1 {
            leaf level-1 {
              type empty;
            }
            uses ncs_template_lsp-gen-interval-grouping;
          }
          container intervals-level-2 {
            leaf level-2 {
              type empty;
            }
            uses ncs_template_lsp-gen-interval-grouping;
          }
        }
      }
    }
    container use {
      leaf external-metrics {
        type empty;
      }
    }
    leaf ignore-lsp-errors {
      type string;
      // NCS drop default statement
    }
    container hostname {
      leaf dynamic {
        type string;
        // NCS drop default statement
      }
    }
    container log-adjacency-changes {
      presence "true";
      leaf all {
        type empty;
      }
    }
    container partition {
      leaf avoidance {
        type empty;
      }
    }
    leaf lsp-mtu {
      type string;
    }
    container lsp-full {
      container suppress {
        choice lsp-full-choince {
          container external-interlevel-container {
            leaf external {
              type empty;
            }
            leaf interlevel {
              type empty;
            }
          }
          leaf none {
            type empty;
          }
        }
      }
    }
    leaf update-queue-depth {
      type string;
    }
    container nsf {
      leaf cisco {
        type empty;
      }
      leaf ietf {
        type empty;
      }
    }
    container bfd {
      leaf all-interfaces {
        type empty;
      }
    }
    container distance {
      container distance-ip {
        leaf distance {
          type string;
        }
        leaf ip {
          type empty;
        }
      }
      list distance-network-list {
        // NCS patched for predictable order
        ordered-by user;
        key "ip-address wildcard-mask";
        leaf ip-address {
          type string;
        }
        leaf wildcard-mask {
          type string;
        }
        leaf distance {
          type string;
        }
        leaf access-list {
          type string;
        }
      }
      container distance-clns {
        leaf distance {
          type string;
        }
        leaf clns {
          type empty;
        }
      }
    }
    container domain-password {
      leaf name {
        type string;
      }
      uses ncs_template_router-isis-authenticate-snp-grouping;
    }
    choice hello-padding-choice {
      container hello {
        leaf padding {
          type string;
          // NCS drop default statement
        }
      }
      container conf {
        container hello {
          leaf padding {
            type string;
          }
        }
      }
    }
    container traffic-share {
      container min {
        leaf across-interfaces {
          type empty;
        }
      }
    }
    container microloop {
      container avoidance {
        presence "true";
        choice avoidance-choice {
          leaf protected {
            type empty;
          }
          leaf disable {
            type empty;
          }
        }
      }
    }
    container segment-routing {
      leaf mpls {
        type empty;
      }
    }
    container fast-reroute {
      container per-prefix {
        container level-1 {
          choice level-choice {
            leaf route-map {
              type string;
            }
            leaf all {
              type empty;
            }
          }
        }
        container level-2 {
          choice level-choice {
            leaf route-map {
              type string;
            }
            leaf all {
              type empty;
            }
          }
        }
      }
      container remote-lfa {
        container level-1 {
          container mpls-ldp {
            presence "true";
            leaf maximum-metric {
              type string;
            }
          }
        }
        container level-2 {
          container mpls-ldp {
            presence "true";
            leaf maximum-metric {
              type string;
            }
          }
        }
      }
    }
    container mpls {
      container ldp {
        leaf sync {
          type empty;
        }
      }
      container traffic-eng {
        leaf level-1 {
          type empty;
        }
        leaf level-2 {
          type empty;
        }
        leaf multicast-intact {
          type empty;
        }
        container router-id {
          uses ncs_template_interface-name-grouping;
        }
        container scanner {
          presence "Timer parameters for TE database";
          leaf interval {
            type string;
          }
          leaf max-flash {
            type string;
          }
        }
      }
    }
    uses ncs_template_passive-interface-grouping;
    uses ncs_template_router-distribute-list-grouping;
    container redistribute {
      container maximum-prefix {
        leaf number {
          type string;
        }
        leaf threshold-value {
          type string;
        }
        leaf warning-only {
          type empty;
        }
        leaf withdraw {
          type empty;
        }
      }
      container connected {
        presence "Connected";
        uses ncs_template_router-isis-redistribute-grouping;
      }
      container static {
        presence "Static routes";
        container clns {
          presence "true";
          leaf route-map {
            type string;
          }
        }
        container ip {
          presence "true";
          uses ncs_template_router-isis-redistribute-grouping;
        }
      }
      container odr {
        presence "On Demand stub Routes";
        uses ncs_template_router-isis-redistribute-grouping;
      }
      container rip {
        presence "Routing Information Protocol (RIP)";
        uses ncs_template_router-isis-redistribute-grouping;
      }
      list bgp {
        // NCS patched for predictable order
        ordered-by user;
        key "as-no";
        leaf as-no {
          type string;
        }
        container clns {
          presence "true";
          leaf route-map {
            type string;
          }
        }
        uses ncs_template_router-isis-redistribute-grouping;
      }
      list ospf {
        // NCS patched for predictable order
        ordered-by user;
        key "id";
        leaf id {
          type string;
        }
        uses ncs_template_redistribute-ospf-match-grouping;
        uses ncs_template_router-isis-redistribute-grouping;
      }
      container isis {
        list isis-area-list {
          // NCS patched for predictable order
          ordered-by user;
          key "area-tag";
          leaf area-tag {
            type string;
          }
          leaf ip {
            type empty;
          }
          leaf metric {
            type string;
          }
          leaf route-map {
            type string;
          }
        }
        list ip {
          // NCS patched for predictable order
          ordered-by user;
          key "from into";
          leaf from {
            type string;
          }
          leaf into {
            type string;
          }
          leaf distribute-list {
            type string;
          }
          leaf route-map {
            type string;
          }
        }
      }
      list eigrp {
        // NCS patched for predictable order
        ordered-by user;
        key "as-no";
        leaf as-no {
          type string;
        }
        uses ncs_template_router-isis-redistribute-grouping;
      }
      container iso-igrp {
        presence "IGRP for OSI networks";
        choice iso-igrp-choice {
          container area-tag-route-map-container {
            leaf area-tag {
              type string;
            }
            leaf route-map {
              type string;
            }
          }
          leaf route-map {
            type string;
          }
        }
        uses ncs_template_redist-level-grouping;
        leaf metric {
          type string;
        }
        leaf metric-type {
          type string;
        }
      }
      container mobile {
        presence "Mobile routes";
        uses ncs_template_router-isis-redistribute-grouping;
      }
    }
    list summary-address {
      // NCS patched for predictable order
      ordered-by user;
      key "ip mask";
      leaf ip {
        type string;
      }
      leaf mask {
        type string;
      }
      leaf level {
        type string;
      }
      leaf tag {
        type string;
      }
      leaf metric {
        type string;
      }
    }
    uses ncs_template_router-isis-af-grouping;
    container address-family {
      container ipv6 {
        leaf af {
          type string;
          // NCS drop default statement
        }
        uses ncs_template_router-isis-af-grouping;
        list summary-prefix {
          // NCS patched for predictable order
          ordered-by user;
          key "prefix";
          leaf prefix {
            type string;
          }
          leaf level {
            type string;
          }
          leaf tag {
            type string;
          }
        }
        leaf distance {
          type string;
        }
        container multi-topology {
          presence "Enable multi-topology mode";
          leaf transition {
            type empty;
          }
        }
        container redistribute {
          container connected {
            presence "Connected";
            uses ncs_template_router-isis-af-redistribute-grouping;
          }
          container static {
            presence "Static routes";
            uses ncs_template_router-isis-redistribute-grouping;
          }
          container bgp {
            leaf as-no {
              type string;
            }
            uses ncs_template_router-isis-af-redistribute-grouping;
          }
          list ospf {
            // NCS patched for predictable order
            ordered-by user;
            key "id";
            leaf id {
              type string;
            }
            uses ncs_template_redistribute-ospf-match-grouping;
            uses ncs_template_router-isis-af-redistribute-grouping;
          }
          list rip {
            // NCS patched for predictable order
            ordered-by user;
            key "process";
            leaf process {
              type string;
            }
            uses ncs_template_router-isis-af-redistribute-grouping;
          }
          list eigrp {
            // NCS patched for predictable order
            ordered-by user;
            key "as-no";
            leaf as-no {
              type string;
            }
            uses ncs_template_router-isis-af-redistribute-grouping;
          }
          container isis {
            list isis-list {
              // NCS patched for predictable order
              ordered-by user;
              key "from into";
              leaf from {
                type string;
              }
              leaf into {
                type string;
              }
              leaf distribute-list {
                type string;
              }
              leaf route-map {
                type string;
              }
            }
          }
          container nemo {
            uses ncs_template_router-isis-af-redistribute-grouping;
          }
        }
      }
    }
  }

  grouping ncs_template_router-lisp-database-mapping-grouping {
    list database-mapping {
      // NCS patched for predictable order
      ordered-by user;
      key "prefix";
      // NCS drop max-elements statement
      leaf prefix {
        type string;
      }
      choice rloc-choice {
        leaf ipv4-address {
          type string;
        }
        container IPv4-interface {
          uses ncs_template_interface-name-grouping;
        }
        container IPv6-interface {
          uses ncs_template_interface-name-grouping;
        }
        leaf ipv6-address {
          type string;
        }
        leaf auto-discover-rlocs {
          type empty;
        }
        leaf locator-set {
          type string;
        }
      }
      leaf priority {
        type string;
      }
      leaf weight {
        type string;
      }
    }
  }

  grouping ncs_template_router-lisp-af4-common-grouping {
    leaf map-request-source {
      type string;
    }
    container proxy-itr {
      leaf ipv4-local-locator {
        type string;
      }
      leaf ipv6-local-locator {
        type string;
      }
    }
  }

  grouping ncs_template_router-lisp-af6-common-grouping {
    leaf map-request-source {
      type string;
    }
    container proxy-itr {
      leaf ipv6-local-locator {
        type string;
      }
      leaf ipv4-local-locator {
        type string;
      }
    }
  }

  grouping ncs_template_router-lisp-af-grouping {
    leaf map-resolver {
      type empty;
    }
    container map-resolver-conf {
      container map-resolver {
        container map-request {
          container validate {
            container source {
              leaf registered {
                type empty;
              }
              container list {
                choice list-choice {
                  leaf ipv4 {
                    type string;
                  }
                  leaf ipv6 {
                    type string;
                  }
                }
              }
            }
          }
        }
      }
    }
    container itr {
      list map-resolver {
        // NCS patched for predictable order
        ordered-by user;
        key "address";
        leaf address {
          type string;
        }
      }
      leaf enable {
        type empty;
      }
    }
    container etr {
      list map-server {
        // NCS patched for predictable order
        ordered-by user;
        key "address";
        leaf address {
          type string;
        }
        container key {
          uses ncs_template_crypto-key-grouping;
          leaf hash-function {
            type string;
          }
        }
      }
      leaf enable {
        type empty;
      }
    }
    leaf map-cache-limit {
      type string;
    }
    container map-cache-persistent {
      presence "true";
      leaf interval {
        type string;
      }
    }
    container route-import {
      container database {
        list static-list {
          // NCS patched for predictable order
          ordered-by user;
          key "protocol";
          leaf protocol {
            type string;
          }
          leaf route-map {
            type string;
          }
          leaf locator-set {
            type string;
          }
        }
        list id-list {
          // NCS patched for predictable order
          ordered-by user;
          key "protocol id";
          leaf protocol {
            type string;
          }
          leaf id {
            type string;
          }
          leaf route-map {
            type string;
          }
          leaf locator-set {
            type string;
          }
        }
      }
    }
    container route-export {
      leaf site-registration {
        type empty;
      }
    }
    container map-cache {
      leaf site-registration {
        type empty;
      }
    }
    leaf proxy-etr {
      type empty;
    }
    list use-petr {
      // NCS patched for predictable order
      ordered-by user;
      key "address";
      leaf address {
        type string;
      }
      leaf priority {
        type string;
      }
      leaf weight {
        type string;
      }
    }
    leaf map-server {
      type empty;
    }
  }

  grouping ncs_template_router-lisp-eid-table-grouping {
    leaf instance-id {
      type string;
    }
    list map-cache {
      // NCS patched for predictable order
      ordered-by user;
      key "prefix";
      leaf prefix {
        type string;
      }
      choice map-cache-choice {
        case locator {
          leaf locator {
            type string;
          }
          leaf priority {
            type string;
          }
          leaf weight {
            type string;
          }
        }
        leaf map-request {
          type empty;
        }
        leaf native-forward {
          type empty;
        }
        leaf drop {
          type empty;
        }
      }
    }
    uses ncs_template_router-lisp-database-mapping-grouping;
    container loc-reach-algorithm {
      leaf lsb-reports {
        type string;
      }
      leaf rloc-probing {
        type empty;
      }
    }
    container ipv4 {
      uses ncs_template_router-lisp-af-grouping;
      uses ncs_template_router-lisp-af4-common-grouping;
    }
    container ipv6 {
      uses ncs_template_router-lisp-af-grouping;
      uses ncs_template_router-lisp-af6-common-grouping;
    }
  }

  grouping ncs_template_router-lisp-service-af-grouping {
    container eid-table {
      leaf default {
        type empty;
      }
      leaf vrf {
        // NCS drop tailf-common:cli-diff-dependency statement
        type string;
      }
    }
    uses ncs_template_router-lisp-database-mapping-grouping;
    leaf encapsulation {
      type string;
    }
  }

  grouping ncs_template_router-lisp-service-grouping {
    container service {
      container ipv4 {
        presence "true";
        uses ncs_template_router-lisp-service-af-grouping;
        uses ncs_template_router-lisp-af-grouping;
        uses ncs_template_router-lisp-af4-common-grouping;
      }
      container ipv6 {
        presence "true";
        uses ncs_template_router-lisp-service-af-grouping;
        uses ncs_template_router-lisp-af-grouping;
        uses ncs_template_router-lisp-af6-common-grouping;
      }
    }
  }

  grouping ncs_template_router-lisp-grouping {
    container syslog {
      leaf verbose {
        type empty;
      }
      container session {
        leaf changes {
          type empty;
        }
      }
    }
    container etr {
      container map-server {
        container source-address {
          uses ncs_template_interface-name-grouping;
        }
      }
    }
    container locator-table {
      choice locator-table-choice {
        leaf default {
          type empty;
        }
        leaf vrf {
          type string;
        }
      }
    }
    list locator-set {
      // NCS patched for predictable order
      ordered-by user;
      key "name";
      leaf name {
        type string;
      }
      list IPv4-address {
        // NCS patched for predictable order
        ordered-by user;
        key "name";
        leaf name {
          type string;
        }
        leaf priority {
          type string;
        }
        leaf weight {
          type string;
        }
      }
      list IPv6-address {
        // NCS patched for predictable order
        ordered-by user;
        key "name";
        leaf name {
          type string;
        }
        leaf priority {
          type string;
        }
        leaf weight {
          type string;
        }
      }
      list IPv4-interface {
        // NCS patched for predictable order
        ordered-by user;
        key "name";
        leaf name {
          type string;
        }
        leaf priority {
          type string;
        }
        leaf weight {
          type string;
        }
      }
      list IPv6-interface {
        // NCS patched for predictable order
        ordered-by user;
        key "name";
        leaf name {
          type string;
        }
        leaf priority {
          type string;
        }
        leaf weight {
          type string;
        }
      }
      leaf auto-discover-rlocs {
        type empty;
      }
    }
    uses ncs_template_router-lisp-service-grouping {
      refine "service/ipv4" {
        // NCS drop tailf-common:cli-diff-dependency statement
      }
      refine "service/ipv6" {
        // NCS drop tailf-common:cli-diff-dependency statement
      }
      refine "service/ipv4/etr/map-server/key/secret";
      refine "service/ipv6/etr/map-server/key/secret";
    }
    container map-request {
      leaf itr-rlocs {
        type string;
      }
    }
    container eid-table {
      // NCS drop tailf-common:cli-diff-dependency statement
      list default-vrf {
        // NCS patched for predictable order
        ordered-by user;
        key "name";
        leaf name {
          type string;
        }
        uses ncs_template_router-lisp-eid-table-grouping;
      }
      list vrf {
        // NCS patched for predictable order
        ordered-by user;
        key "name";
        leaf name {
          type string;
        }
        uses ncs_template_router-lisp-eid-table-grouping;
      }
    }
    container loc-reach-algorithm {
      leaf rloc-probing {
        type empty;
      }
    }
    list site {
      // NCS patched for predictable order
      ordered-by user;
      key "name";
      leaf name {
        type string;
      }
      leaf description {
        type string;
      }
      container authentication-key {
        uses ncs_template_crypto-key-grouping;
      }
      list eid-prefix {
        // NCS patched for predictable order
        ordered-by user;
        key "prefix";
        leaf prefix {
          type string;
        }
        leaf route-tag {
          type string;
        }
        leaf accept-more-specifics {
          type empty;
        }
      }
      container eid-prefix-instance {
        list eid-prefix {
          // NCS patched for predictable order
          ordered-by user;
          key "instance-id prefix";
          leaf instance-id {
            type string;
          }
          leaf prefix {
            type string;
          }
          leaf route-tag {
            type string;
          }
          leaf accept-more-specifics {
            type empty;
          }
        }
      }
      list allowed-locator {
        // NCS patched for predictable order
        ordered-by user;
        key "rloc";
        leaf rloc {
          type string;
        }
      }
    }
    container ipv4 {
      uses ncs_template_router-lisp-af-grouping {
        refine "map-cache-persistent";
      }
      uses ncs_template_router-lisp-af4-common-grouping;
    }
    container ipv6 {
      uses ncs_template_router-lisp-af-grouping {
        refine "map-cache-persistent";
      }
      uses ncs_template_router-lisp-af6-common-grouping;
    }
    list instance-id {
      // NCS patched for predictable order
      ordered-by user;
      // NCS drop tailf-common:cli-diff-dependency statement
      // NCS drop tailf-common:cli-diff-dependency statement
      key "id";
      leaf id {
        type string;
      }
      uses ncs_template_router-lisp-service-grouping {
        refine "service/ipv4/etr/map-server/key/secret";
        refine "service/ipv6/etr/map-server/key/secret";
      }
    }
  }

  grouping ncs_template_ip-nat-outside-source-grouping {
    leaf redundancy {
      type string;
    }
    leaf mapping-id {
      // NCS drop when statement
      type string;
    }
    leaf add-route {
      type empty;
    }
    leaf no-payload {
      type empty;
    }
  }

  grouping ncs_template_ip-nat-source-static-grouping {
    leaf redundancy {
      type string;
    }
    leaf mapping-id {
      // NCS drop when statement
      type string;
    }
    leaf extendable {
      type empty;
    }
    leaf no-alias {
      type empty;
    }
    leaf no-payload {
      type empty;
    }
    leaf add-route {
      type empty;
    }
    leaf route-map {
      type string;
    }
    leaf reversible {
      // NCS drop when statement
      type empty;
    }
    leaf match-in-vrf {
      type empty;
    }
    leaf forced {
      type empty;
    }
    leaf overload {
      type empty;
    }
  }

  grouping ncs_template_ip-nat-inside-options-grouping {
    leaf no-payload {
      type empty;
    }
    leaf reversible {
      type empty;
    }
    leaf overload {
      type empty;
    }
    leaf oer {
      type empty;
    }
  }

  grouping ncs_template_ip-nat-inside-grouping {
    leaf pool {
      type string;
    }
    leaf redundancy {
      type string;
    }
    leaf mapping-id {
      type string;
    }
    leaf interface {
      // NCS drop when statement
      // NCS drop tailf-common:cli-diff-dependency statement
      type string;
    }
  }

  grouping ncs_template_ip-nat-inside-vrf-grouping {
    leaf pool {
      type string;
    }
    leaf redundancy {
      type string;
    }
    leaf mapping-id {
      type string;
    }
    leaf interface {
      // NCS drop when statement
      // NCS drop tailf-common:cli-diff-dependency statement
      type string;
    }
    leaf vrf {
      type string;
    }
    leaf match-in-vrf {
      type empty;
    }
  }

  grouping ncs_template_mobile-ip-spi-grouping {
    choice spi-type-choice {
      leaf hex {
        type string;
      }
      leaf decimal {
        type string;
      }
    }
  }

  grouping ncs_template_xconnect-interface-grouping {
    choice xconnect-choice {
      container xconnect {
        // NCS drop tailf-common:cli-diff-dependency statement
        leaf address {
          type string;
        }
        leaf vcid {
          type string;
        }
        leaf encapsulation {
          type string;
        }
        leaf manual {
          type empty;
        }
        leaf pw-class {
          type string;
        }
        leaf sequencing {
          // NCS drop when statement
          type string;
        }
        container backup {
          container peer {
            leaf peer-router-ip-addr {
              type string;
            }
            leaf vcid {
              type string;
            }
            leaf pw-class {
              type string;
            }
            leaf priority {
              type string;
            }
          }
          container delay {
            leaf enable-delay {
              type string;
              // NCS drop default statement
            }
            leaf disable-delay {
              type string;
              // NCS drop default statement
            }
          }
        }
        container mpls {
          leaf control-word {
            type empty;
          }
        }
        leaf mtu {
          type string;
        }
        container remote {
          container link {
            container failure {
              leaf notification {
                type string;
                // NCS drop default statement
              }
            }
          }
        }
      }
      container xconnect-pw-class {
        container xconnect {
          leaf address {
            type string;
          }
          leaf vcid {
            type string;
          }
          leaf pw-class {
            type string;
          }
        }
      }
      container xconnect-vfi {
        container xconnect {
          leaf vfi {
            // NCS drop tailf-common:cli-diff-dependency statement
            type string;
          }
        }
      }
    }
  }

  grouping ncs_template_xconnect-grouping {
    choice xconnect-choice {
      container xconnect {
        presence "true";
        leaf address {
          type string;
        }
        leaf vcid {
          type string;
        }
        leaf encapsulation {
          type string;
        }
        leaf manual {
          type empty;
        }
        leaf pw-class {
          type string;
        }
        leaf sequencing {
          // NCS drop when statement
          type string;
        }
        container backup {
          container peer {
            leaf peer-router-ip-addr {
              type string;
            }
            leaf vcid {
              type string;
            }
            leaf pw-class {
              type string;
            }
            leaf priority {
              type string;
            }
          }
          container delay {
            leaf enable-delay {
              type string;
              // NCS drop default statement
            }
            leaf disable-delay {
              type string;
              // NCS drop default statement
            }
          }
        }
        container mpls {
          leaf control-word {
            type empty;
          }
        }
        leaf mtu {
          type string;
        }
        container remote {
          container link {
            container failure {
              leaf notification {
                type string;
                // NCS drop default statement
              }
            }
          }
        }
      }
      container xconnect-pw-class {
        container xconnect {
          leaf address {
            type string;
          }
          leaf vcid {
            type string;
          }
          leaf pw-class {
            type string;
          }
        }
      }
    }
  }

  grouping ncs_template_ip-pim-grouping {
    container ssm {
      choice ip-pim-ssm-choice {
        leaf default {
          type empty;
        }
        leaf range {
          type string;
        }
      }
    }
    container register-source {
      uses ncs_template_interface-name-grouping;
    }
    leaf snooping {
      type empty;
    }
    list bsr-candidate {
      // NCS patched for predictable order
      ordered-by user;
      key "name";
      leaf name {
        type string;
      }
      leaf hash-mask-length {
        type string;
      }
      leaf priority {
        type string;
      }
      leaf accept-rp-candidate {
        type string;
      }
    }
    container send-rp-announce {
      container interface {
        uses ncs_template_interface-name-grouping;
      }
      leaf scope {
        type string;
      }
      leaf group-list {
        type string;
      }
      leaf interval {
        type string;
      }
    }
    container send-rp-discovery {
      container scope {
        leaf ttl {
          type string;
        }
        leaf interval {
          type string;
        }
      }
    }
    list rp-address {
      // NCS patched for predictable order
      ordered-by user;
      key "address";
      leaf address {
        type string;
      }
      leaf access-list {
        type string;
      }
      leaf override {
        type empty;
      }
    }
    list rp-candidate {
      // NCS patched for predictable order
      ordered-by user;
      key "name";
      leaf name {
        type string;
      }
      leaf bidir {
        type empty;
      }
      leaf group-list {
        type string;
      }
      leaf interval {
        type string;
      }
      leaf priority {
        type string;
      }
    }
    container spt-threshold {
      leaf value {
        type string;
      }
      list group-list {
        // NCS patched for predictable order
        ordered-by user;
        key "group-list";
        leaf value {
          type string;
        }
        leaf group-list {
          type string;
        }
      }
    }
    choice autorp-choice {
      leaf autorp {
        type string;
        // NCS drop default statement
      }
      container conf {
        container autorp {
          leaf listener {
            type empty;
          }
        }
      }
    }
    leaf dm-fallback {
      type empty;
    }
  }

  grouping ncs_template_event-manager-applet-event-grouping {
    container none {
      leaf maxrun {
        type string;
      }
    }
    container snmp-notification {
      leaf oid {
        type string;
      }
      leaf oid-val {
        type string;
      }
      leaf op {
        type string;
      }
      leaf src-ip-address {
        type string;
      }
      leaf dest-ip-address {
        type string;
      }
    }
    container syslog {
      leaf pattern {
        type string;
      }
    }
    container cli {
      container pattern {
        leaf regular-expression {
          type string;
        }
        leaf sync {
          type string;
        }
        leaf skip {
          type string;
        }
      }
    }
    container track {
      leaf object-number {
        type string;
      }
      leaf state {
        type string;
      }
      leaf maxrun {
        type string;
      }
    }
    container neighbor-discovery {
      container interface {
        leaf regexp {
          type string;
        }
      }
      leaf cdp {
        type string;
      }
    }
    container timer {
      leaf trigger {
        type string;
      }
      leaf name {
        type string;
      }
      leaf cron-entry {
        type string;
      }
      leaf time {
        type string;
      }
      leaf maxrun {
        type string;
      }
      leaf ratelimit {
        type string;
      }
    }
    container snmp {
      leaf oid {
        type string;
      }
      leaf get-type {
        type string;
      }
      leaf entry-op {
        type string;
      }
      leaf entry-val {
        type string;
      }
      leaf exit-op {
        type string;
      }
      leaf exit-val {
        type string;
      }
      leaf poll-interval {
        type string;
      }
    }
    container ipsla {
      leaf operation-id {
        type string;
      }
      leaf reaction-type {
        type string;
      }
      leaf maxrun {
        type string;
      }
    }
  }

  grouping ncs_template_route-target-grouping {
    list export {
      // NCS patched for predictable order
      ordered-by user;
      key "asn-ip";
      leaf asn-ip {
        type string;
      }
    }
    list import {
      // NCS patched for predictable order
      ordered-by user;
      key "asn-ip";
      leaf asn-ip {
        type string;
      }
    }
  }

  grouping ncs_template_vrf-definition-af-grouping {
    container export {
      leaf map {
        type string;
      }
    }
    container route-target {
      uses ncs_template_route-target-grouping;
    }
    container maximum {
      container routes {
        leaf limit {
          type string;
        }
        choice action {
          case a {
            leaf warning-only {
              type empty;
            }
          }
          case b {
            leaf warn-threshold {
              type string;
            }
            leaf reinstall {
              type string;
            }
          }
        }
      }
    }
  }

  grouping ncs_template_snmp-server-host-grouping {
    leaf message-type {
      type string;
      // NCS drop default statement
    }
    container version {
      leaf version {
        type string;
      }
      leaf security-level {
        // NCS drop when statement
        type string;
      }
    }
    leaf community-string {
      type string;
    }
    leaf-list allowed-traps {
      // NCS patched for predictable order
      ordered-by user;
      type string;
    }
  }

  grouping ncs_template_aaa-authentication-method-grouping {
    leaf cache {
      type string;
    }
    leaf group {
      type string;
    }
    container group2 {
      // NCS drop when statement
      leaf group {
        type string;
      }
    }
    leaf krb5 {
      type empty;
    }
    choice local-choice {
      leaf local {
        type empty;
      }
      leaf local-case {
        type empty;
      }
    }
    leaf tacacsplus {
      tailf:alt-name "tacacs+";
      type empty;
    }
    leaf line {
      type empty;
    }
    leaf enable {
      type empty;
    }
    leaf none {
      type empty;
    }
  }

  grouping ncs_template_aaa-authorization-method-grouping {
    leaf cache {
      type string;
    }
    leaf group {
      type string;
    }
    leaf krb5-instance {
      type empty;
    }
    leaf tacacsplus {
      tailf:alt-name "tacacs+";
      type empty;
    }
    leaf local {
      type empty;
    }
    leaf if-authenticated {
      type empty;
    }
    leaf none {
      type empty;
    }
  }

  grouping ncs_template_aaa-accounting-method-grouping {
    leaf action-type {
      type string;
    }
    leaf broadcast {
      type empty;
    }
    leaf group {
      type string;
    }
  }

  grouping ncs_template_cable-modulation-profile-grouping {
    leaf fec-tbytes {
      type string;
    }
    leaf fec-len {
      type string;
    }
    leaf burst-len {
      type string;
    }
    leaf guard-t {
      type string;
    }
    leaf mod {
      type string;
    }
    leaf scrambler {
      type string;
    }
    leaf seed {
      // NCS drop when statement
      type string;
    }
    leaf diff {
      type string;
    }
    leaf pre-len {
      type string;
    }
    leaf last-cw {
      type string;
    }
    leaf preamble {
      type string;
    }
    leaf rs-interleave-depth {
      type string;
    }
    leaf rs-interleave-block {
      type string;
    }
  }

  grouping ncs_template_cable-modulation-profile-list-grouping {
    container request {
      uses ncs_template_cable-modulation-profile-grouping;
    }
    container initial {
      uses ncs_template_cable-modulation-profile-grouping;
    }
    container station {
      uses ncs_template_cable-modulation-profile-grouping;
    }
    container short {
      uses ncs_template_cable-modulation-profile-grouping;
    }
    container long {
      uses ncs_template_cable-modulation-profile-grouping;
    }
    container a-short {
      uses ncs_template_cable-modulation-profile-grouping;
    }
    container a-long {
      uses ncs_template_cable-modulation-profile-grouping;
    }
    container a-ugs {
      uses ncs_template_cable-modulation-profile-grouping;
    }
  }

  grouping ncs_template_cable-load-balance-docsis-group-grouping {
    leaf restricted {
      type empty;
    }
    container downstream {
      list Modular-Cable {
        // NCS patched for predictable order
        ordered-by user;
        key "name";
        leaf name {
          type string;
        }
        leaf rf-channel {
          type string;
        }
      }
      list Integrated-Cable {
        // NCS patched for predictable order
        ordered-by user;
        key "name";
        leaf name {
          type string;
        }
        leaf rf-channel {
          type string;
        }
      }
    }
    container upstream {
      list Upstream-Cable {
        // NCS patched for predictable order
        ordered-by user;
        key "name";
        leaf name {
          type string;
        }
        leaf us-channel {
          type string;
        }
      }
      list Cable {
        // NCS patched for predictable order
        ordered-by user;
        key "name";
        leaf name {
          type string;
        }
        leaf upstream-list {
          type string;
        }
      }
    }
    container method {
      container utilization {
        presence "true";
      }
    }
    container threshold {
      container load {
        leaf percentage {
          type string;
        }
        leaf minimum {
          type string;
        }
      }
      leaf stability {
        type string;
      }
    }
    leaf policy {
      type string;
    }
    leaf interval {
      type string;
    }
    container init-tech-list {
      leaf grouplist {
        type string;
      }
      leaf ucc {
        type empty;
      }
    }
    leaf docsis-policy {
      type string;
    }
    list tag {
      // NCS patched for predictable order
      ordered-by user;
      key "name";
      leaf name {
        type string;
      }
    }
  }

  grouping ncs_template_facility-alarm-grouping {
    container major {
      leaf temperature {
        type string;
      }
    }
    container minor {
      leaf temperature {
        type string;
      }
    }
    container critical {
      leaf exceed-action {
        type string;
      }
      leaf temperature {
        type string;
      }
    }
  }

  grouping ncs_template_process-cpu-threshold-grouping {
    leaf rising {
      type string;
    }
    leaf interval {
      type string;
    }
    leaf falling {
      type string;
    }
    container falling-interval {
      leaf interval {
        type string;
      }
    }
  }

  grouping ncs_template_cable-submgmt-default-filter-group-grouping {
    leaf upstream {
      type string;
    }
    leaf downstream {
      type string;
    }
  }

  grouping ncs_template_storm-control-level-bps-pps-grouping {
    container level-bps-pps {
      container level {
        choice level-choice {
          leaf bps {
            type string;
          }
          leaf pps {
            type string;
          }
        }
      }
    }
  }

  grouping ncs_template_logging-host-grouping {
    leaf discriminator {
      type string;
    }
    container session-id {
      choice session-id-choice {
        leaf hostname {
          type empty;
        }
        leaf ipv4 {
          type empty;
        }
        leaf ipv6 {
          type empty;
        }
        leaf string {
          type string;
        }
      }
    }
    leaf transport {
      type string;
    }
    leaf port {
      // NCS drop when statement
      type string;
    }
  }

  grouping ncs_template_crypto-ikev2-profile-aaa-authorization-group-list {
    container list {
      leaf list-name {
        type string;
      }
      leaf aaa-username {
        type string;
      }
      leaf name-mangler {
        type string;
      }
      container password {
        uses ncs_template_crypto-key-grouping;
      }
    }
  }

  grouping ncs_template_parameter-map-grouping {
    leaf alert {
      type string;
    }
    leaf audit-trail {
      type string;
    }
    leaf dns-timeout {
      type string;
    }
    container icmp {
      leaf idle-time {
        type string;
      }
      leaf ageout-time {
        type string;
      }
    }
    leaf max-destination {
      type string;
    }
    container max-incomplete {
      container half-open-sessions {
        leaf number {
          type string;
        }
        container aggressive-aging {
          leaf high {
            type string;
          }
          leaf low {
            type string;
          }
        }
      }
      leaf high {
        type string;
      }
      leaf low {
        type string;
      }
    }
    container one-minute {
      leaf high {
        type string;
      }
      leaf low {
        type string;
      }
    }
    container session {
      container total {
        leaf number {
          type string;
        }
        container aggressive-aging {
          leaf high {
            type string;
          }
          leaf low {
            type string;
          }
        }
      }
    }
    container sessions {
      leaf maximum {
        type string;
      }
    }
    container tcp {
      container finwait-time {
        leaf seconds {
          type string;
        }
        leaf ageout-time {
          type string;
        }
      }
      container idle-time {
        leaf seconds {
          type string;
        }
        leaf ageout-time {
          type string;
        }
      }
      container max-incomplete {
        leaf host {
          type string;
        }
      }
      container synwait-time {
        leaf seconds {
          type string;
        }
        leaf ageout-time {
          type string;
        }
      }
      container syn-flood {
        leaf limit {
          type string;
        }
        container rate {
          leaf per-destination {
            type string;
          }
        }
      }
    }
    container udp {
      container idle-time {
        leaf seconds {
          type string;
        }
        leaf ageout-time {
          type string;
        }
      }
      container half-open {
        container idle-time {
          leaf seconds {
            type string;
          }
          leaf ageout-time {
            type string;
          }
        }
      }
    }
    container log {
      leaf dropped-packets {
        type empty;
      }
    }
    container threat-detection {
      leaf basic-threat {
        type empty;
      }
      container rate {
        container syn-attack {
          leaf average-time-frame {
            type string;
          }
          leaf average-threshold {
            type string;
          }
          leaf burst-threshold {
            type string;
          }
        }
        container inspect-drop {
          leaf average-time-frame {
            type string;
          }
          leaf average-threshold {
            type string;
          }
          leaf burst-threshold {
            type string;
          }
        }
        container fw-drop {
          leaf average-time-frame {
            type string;
          }
          leaf average-threshold {
            type string;
          }
          leaf burst-threshold {
            type string;
          }
        }
      }
    }
    list vrf {
      // NCS patched for predictable order
      ordered-by user;
      key "vrf";
      leaf vrf {
        // NCS drop tailf-common:cli-diff-dependency statement
        // NCS drop tailf-common:cli-diff-dependency statement
        type string;
      }
      leaf inspect {
        type string;
      }
    }
  }

  grouping ncs_template_dscp-value-0-7-grouping {
    leaf dscp-value0 {
      type string;
    }
    leaf dscp-value1 {
      type string;
    }
    leaf dscp-value2 {
      type string;
    }
    leaf dscp-value3 {
      type string;
    }
    leaf dscp-value4 {
      type string;
    }
    leaf dscp-value5 {
      type string;
    }
    leaf dscp-value6 {
      type string;
    }
    leaf dscp-value7 {
      type string;
    }
  }

  grouping ncs_template_cos-value-0-7-grouping {
    leaf cos-value0 {
      type string;
    }
    leaf cos-value1 {
      type string;
    }
    leaf cos-value2 {
      type string;
    }
    leaf cos-value3 {
      type string;
    }
    leaf cos-value4 {
      type string;
    }
    leaf cos-value5 {
      type string;
    }
    leaf cos-value6 {
      type string;
    }
    leaf cos-value7 {
      type string;
    }
  }

  grouping ncs_template_controller-modular-cable-rf-channel-grouping {
    list rf-channel {
      // NCS patched for predictable order
      ordered-by user;
      key "rf-port";
      leaf rf-port {
        type string;
      }
      leaf description {
        type string;
      }
      container cable {
        container downstream {
          leaf channel-id {
            type string;
          }
        }
      }
      container frequency {
        leaf freq {
          type string;
        }
        leaf annex {
          type string;
        }
        leaf modulation {
          type string;
        }
        leaf interleave {
          type string;
        }
      }
      container ip-address {
        leaf ip-address {
          type string;
        }
        leaf mac-address {
          type string;
        }
        leaf depi-remote-id {
          type string;
        }
        leaf eqam-headroom {
          type string;
        }
      }
      container network-delay {
        choice network-delay-choice {
          leaf usec {
            type string;
          }
          container auto {
            presence "true";
            leaf sampling-rate {
              type string;
            }
          }
        }
      }
      container depi-tunnel {
        leaf depi-tunnel-name {
          type string;
        }
        leaf tsid {
          type string;
        }
      }
      leaf rf-power {
        type string;
      }
      leaf rf-shutdown {
        type string;
        // NCS drop default statement
      }
    }
  }

  grouping ncs_template_controller-integrated-cable-rf-chan-grouping {
    leaf type {
      type string;
    }
    leaf frequency {
      type string;
    }
    leaf rf-output {
      type string;
    }
    leaf power-adjust {
      type string;
    }
    leaf qam-profile {
      type string;
    }
    leaf docsis-channel-id {
      type string;
    }
  }

  grouping ncs_template_object-group-service-protocol-match {
    choice match-choice {
      leaf eq {
        type empty;
      }
      leaf gt {
        type empty;
      }
      leaf lt {
        type empty;
      }
    }
  }

  grouping ncs_template_arp-grouping {
    list arp-list {
      // NCS patched for predictable order
      ordered-by user;
      key "ip-address";
      leaf ip-address {
        type string;
      }
      leaf hardware-address {
        type string;
      }
      leaf type {
        type string;
      }
      leaf alias {
        type empty;
      }
    }
  }

  grouping ncs_template_interface-encryption-mode-grouping {
    container mode {
      container ciphers {
        choice suite-choice {
          leaf ckip {
            type empty;
          }
          leaf ckip-cmic {
            type empty;
          }
          leaf cmic {
            type empty;
          }
          case a {
            leaf aes-ccm {
              type empty;
            }
            leaf tkip {
              type empty;
            }
            leaf wep {
              type string;
            }
          }
        }
      }
    }
  }

  grouping ncs_template_ip-ssh-algorithm-grouping {
    container algorithm {
      leaf-list mac {
        // NCS patched for predictable order
        ordered-by user;
        type string;
      }
      leaf-list encryption {
        // NCS patched for predictable order
        ordered-by user;
        type string;
      }
    }
  }

  grouping ncs_template_bandwidth-remaining-account-grouping {
    container account {
      choice account-choice {
        case dot1q-qing {
          leaf bras-side {
            type string;
          }
          leaf aal {
            type string;
          }
          leaf subscriber-encapsulation {
            type string;
          }
        }
        leaf user-defined {
          type string;
        }
      }
    }
  }

  grouping ncs_template_result-type-method-grouping {
    leaf authoritative {
      type empty;
    }
    leaf agent-not-found {
      type empty;
    }
    leaf none {
      type empty;
    }
    leaf success {
      type empty;
    }
    leaf method-timeout {
      type empty;
    }
    leaf aaa-timeout {
      type empty;
    }
  }

  grouping ncs_template_interface-vrrp-grouping {
    leaf description {
      type string;
    }
    container vrrs {
      list leader {
        // NCS patched for predictable order
        ordered-by user;
        key "name";
        leaf name {
          type string;
        }
      }
    }
    container preempt {
      container delay {
        leaf minimum {
          type string;
        }
      }
    }
    leaf priority {
      type string;
    }
    container timers {
      container advertise {
        leaf seconds {
          type string;
        }
        leaf msec {
          type string;
        }
      }
      leaf learn {
        type empty;
      }
    }
    list track {
      // NCS patched for predictable order
      ordered-by user;
      key "name";
      leaf name {
        type string;
      }
      leaf decrement {
        type string;
      }
    }
    leaf shutdown {
      type empty;
    }
  }

  grouping ncs_template_router-bgp-aggregate-address-content-grouping {
    leaf as-set {
      type empty;
    }
    leaf summary-only {
      type empty;
    }
    leaf attribute-map {
      type string;
    }
    leaf advertise-map {
      type string;
    }
    leaf suppress-map {
      type string;
    }
    leaf as-override {
      type empty;
    }
    leaf route-map {
      type string;
    }
  }

  grouping ncs_template_ip-dns-view-grouping {
    container domain {
      container name-server {
        list vrf {
          // NCS patched for predictable order
          ordered-by user;
          key "name address";
          leaf name {
            type string;
          }
          leaf address {
            type string;
          }
        }
        container interface {
          uses ncs_template_interface-name-grouping;
        }
      }
    }
    container dns {
      container forwarding {
        container source-interface {
          uses ncs_template_interface-name-grouping;
        }
      }
    }
  }

  grouping ncs_template_ip-igmp-grouping {
    leaf limit {
      type string;
    }
    container ssm-map {
      leaf enable {
        type empty;
      }
      container query {
        leaf dns {
          type string;
          // NCS drop default statement
        }
      }
      container static {
        leaf access-list {
          type string;
        }
        leaf source-address {
          type string;
        }
      }
    }
  }

  grouping ncs_template_ip-msdp-grouping {
    list peer {
      // NCS patched for predictable order
      ordered-by user;
      key "address";
      leaf address {
        type string;
      }
      container connect-source {
        uses ncs_template_interface-name-grouping;
      }
      leaf remote-as {
        type string;
      }
    }
    list description {
      // NCS patched for predictable order
      ordered-by user;
      // NCS drop tailf-common:cli-diff-dependency statement
      key "address";
      leaf address {
        type string;
      }
      leaf text {
        type string;
      }
    }
    list keepalive {
      // NCS patched for predictable order
      ordered-by user;
      // NCS drop tailf-common:cli-diff-dependency statement
      key "address";
      leaf address {
        type string;
      }
      leaf keepalive-interval {
        type string;
      }
      leaf hold-time-interval {
        type string;
      }
    }
    list sa-filter {
      // NCS patched for predictable order
      ordered-by user;
      // NCS drop tailf-common:cli-diff-dependency statement
      key "direction address";
      leaf direction {
        type string;
      }
      leaf address {
        type string;
      }
      choice list-choice {
        leaf list {
          type string;
        }
        leaf route-map {
          type string;
        }
        leaf rp-list {
          type string;
        }
        leaf rp-route-map {
          type string;
        }
      }
    }
    container originator-id {
      uses ncs_template_interface-name-grouping;
    }
    container mesh-group {
      leaf name {
        type string;
      }
      leaf address {
        type string;
      }
    }
  }

  grouping ncs_template_if-srv-encapsulation-dot1q-grouping {
    leaf-list id {
      // NCS patched for predictable order
      ordered-by user;
      type string;
    }
    leaf second-dot1q {
      type string;
    }
    leaf cos {
      type string;
    }
    leaf etype {
      type string;
    }
  }

  grouping ncs_template_ip-wccp-grouping {
    container source-interface {
      uses ncs_template_interface-name-grouping;
    }
    container web-cache {
      presence "true";
    }
    list wccp-list {
      // NCS patched for predictable order
      ordered-by user;
      key "service-number";
      leaf service-number {
        type string;
      }
      leaf redirect-list {
        type string;
      }
      leaf group-list {
        type string;
      }
      container password {
        uses ncs_template_password-grouping;
      }
    }
  }

  grouping ncs_template_interface-ip-wccp-grouping {
    list wccp-list {
      // NCS patched for predictable order
      ordered-by user;
      key "service-number";
      leaf service-number {
        type string;
      }
      container redirect {
        leaf in {
          type empty;
        }
        leaf out {
          type empty;
        }
      }
    }
  }

  grouping ncs_template_spanning-tree-portfast-grouping {
    leaf default {
      type empty;
    }
    container bpdufilter {
      leaf default {
        type empty;
      }
    }
    container bpduguard {
      leaf default {
        type empty;
      }
    }
  }

  grouping ncs_template_domain-path-preference-grouping {
    container path-preference {
      leaf path1 {
        type string;
      }
      leaf path2 {
        type string;
      }
      leaf path3 {
        type string;
      }
      leaf fallback {
        type empty;
      }
      leaf fallback-path1 {
        type string;
      }
      leaf fallback-path2 {
        type string;
      }
      leaf fallback-path3 {
        type string;
      }
      leaf next-fallback {
        // NCS drop when statement
        type empty;
      }
      leaf blackhole {
        type empty;
      }
      leaf routing {
        type empty;
      }
      leaf next-fallback-path1 {
        type string;
      }
      leaf next-fallback-path2 {
        type string;
      }
      leaf next-fallback-path3 {
        type string;
      }
    }
  }

  grouping ncs_template_lifetime-grouping {
    leaf start-time {
      type string;
    }
    leaf start-month {
      type string;
    }
    leaf start-date {
      type string;
    }
    leaf start-year {
      type string;
    }
    leaf duration {
      type string;
    }
    leaf infinite {
      type empty;
    }
    leaf stop-time {
      type string;
    }
    leaf stop-month {
      type string;
    }
    leaf stop-date {
      type string;
    }
    leaf stop-year {
      type string;
    }
  }

  grouping ncs_template_us-channel-grouping {
    list us-channel {
      // NCS patched for predictable order
      ordered-by user;
      key "id";
      leaf id {
        type string;
      }
      leaf frequency {
        type string;
      }
      container channel-width {
        leaf first-choice-width {
          type string;
        }
        leaf last-choice-width {
          type string;
        }
      }
      leaf power-level {
        type string;
      }
      leaf docsis-mode {
        type string;
      }
      leaf minislot-size {
        type string;
      }
      container modulation-profile {
        leaf primary-profile-number {
          type string;
        }
        leaf secondary-profile-number {
          type string;
        }
        leaf tertiary-profile-number {
          type string;
        }
      }
      leaf equalization-coefficient {
        type empty;
      }
      leaf shutdown {
        type empty;
      }
    }
  }

  grouping ncs_template_ip-explicit-path-grouping {
    list index {
      // NCS patched for predictable order
      ordered-by user;
      key "id";
      leaf id {
        type string;
      }
      choice address-choice {
        leaf next-address {
          type string;
        }
        container next-address-loose {
          container next-address {
            leaf loose {
              type string;
            }
          }
        }
        leaf exclude-address {
          type string;
        }
      }
    }
  }

  grouping ncs_template_radius-server-grouping {
    leaf auth-port {
      type string;
    }
    leaf acct-port {
      type string;
    }
    leaf timeout {
      type string;
    }
    leaf retransmit {
      type string;
    }
    container test {
      leaf username {
        type string;
      }
    }
    container key {
      uses ncs_template_password-grouping;
    }
  }

  grouping ncs_template_domain-advanced-smart-probes-grouping {
    container smart-probes {
      container burst {
        container burst {
          leaf number {
            type string;
          }
          leaf packets {
            type empty;
          }
          leaf every {
            type empty;
          }
          leaf interval {
            type string;
          }
          leaf seconds {
            type empty;
          }
        }
        container quick {
          leaf number {
            type string;
          }
          leaf packets {
            type empty;
          }
          leaf every {
            type empty;
          }
          leaf interval {
            type string;
          }
          leaf seconds {
            type empty;
          }
        }
      }
    }
  }

  grouping ncs_template_domain-master-grouping {
    list master {
      // NCS patched for predictable order
      ordered-by user;
      // NCS drop max-elements statement
      key "type";
      leaf type {
        type string;
      }
      leaf pop-id {
        // NCS drop when statement
        type string;
      }
      container source-interface {
        uses ncs_template_interface-name-grouping;
      }
      container site-prefixes {
        leaf prefix-list {
          type string;
        }
      }
      leaf hub {
        type string;
      }
      container collector {
        leaf ip-address {
          type string;
        }
        leaf port {
          type string;
        }
      }
      container load-balance {
        leaf option {
          type string;
          // NCS drop default statement
        }
        uses ncs_template_domain-path-preference-grouping;
      }
      container password {
        uses ncs_template_password-grouping;
      }
      container enterprise-prefix {
        leaf prefix-list {
          type string;
        }
      }
      list monitor-interval {
        // NCS patched for predictable order
        ordered-by user;
        key "seconds dscp";
        leaf seconds {
          type string;
        }
        leaf dscp {
          type string;
        }
      }
      container advanced {
        presence "true";
        uses ncs_template_domain-advanced-smart-probes-grouping;
        leaf channel-unreachable-timer {
          type string;
        }
      }
      list class {
        // NCS patched for predictable order
        ordered-by user;
        key "name";
        leaf name {
          type string;
        }
        leaf sequence {
          type string;
        }
        container match {
          list dscp {
            // NCS patched for predictable order
            ordered-by user;
            key "services-value";
            leaf services-value {
              type string;
            }
            leaf policy {
              type string;
            }
          }
          list application {
            // NCS patched for predictable order
            ordered-by user;
            key "services-value";
            leaf services-value {
              type string;
            }
            leaf policy {
              type string;
            }
          }
        }
        uses ncs_template_domain-path-preference-grouping;
        leaf path-last-resort {
          type string;
        }
      }
    }
  }

  grouping ncs_template_domain-border-grouping {
    container border {
      presence "true";
      leaf master {
        type string;
      }
      container source-interface {
        uses ncs_template_interface-name-grouping;
      }
      container password {
        uses ncs_template_password-grouping;
      }
    }
  }

  grouping ncs_template_carrier-delay-grouping {
    choice delay-choice {
      leaf seconds {
        type string;
      }
      leaf msec {
        type string;
      }
    }
  }

  grouping ncs_rpc_notif_description-grouping {
    leaf description {
      tailf:info
        "Description text";
      tailf:cli-multi-value;
      tailf:cli-preformatted;
      tailf:cli-full-command;
      type string {
        tailf:info
          "LINE;;Description";
      }
    }
  }

  grouping ncs_rpc_notif_password-grouping {
    leaf type {
      tailf:cli-drop-node-name;
      tailf:cli-optional-in-sequence;
      tailf:cli-incomplete-command;
      type enumeration {
        enum "0" {
          tailf:info
            "Specifies an UNENCRYPTED password/key will follow";
        }
        enum "7" {
          tailf:info
            "Specifies a HIDDEN password/key will follow";
        }
      }
    }
    leaf secret {
      tailf:cli-drop-node-name;
      tailf:cli-reset-container;
      tailf:cli-disallow-value "0|7|key-chain";
      tailf:meta-data "secret-password";
      type string {
        tailf:info
          "LINE;;The UNENCRYPTED (cleartext) password/key";
      }
    }
  }

  grouping ncs_rpc_notif_crypto-key-grouping {
    leaf encryption {
      tailf:cli-drop-node-name;
      tailf:cli-optional-in-sequence;
      tailf:cli-incomplete-command;
      type enumeration {
        enum "0" {
          tailf:info
            "Specifies an UNENCRYPTED password will follow";
        }
        enum "6" {
          tailf:info
            "Specifies an ENCRYPTED password will follow";
        }
        enum "7" {
          tailf:info
            "Specifies an HIDDEN password will follow";
        }
      }
    }
    leaf secret {
      tailf:cli-drop-node-name;
      tailf:cli-reset-container;
      tailf:cli-disallow-value "0|6|7";
      tailf:meta-data "secret-password";
      type string {
        tailf:info
          "LINE;;The UNENCRYPTED (cleartext) user password";
      }
    }
  }

  grouping ncs_rpc_notif_interface-name-grouping {
    choice interface-choice {
      leaf Null {
        tailf:info
          "Null interface";
        tailf:cli-allow-join-with-value {
          tailf:cli-display-joined;
        }
        // NCS drop tailf-common:non-strict-leafref statement
        type uint8 {
          tailf:info
            "<0-0>;;Null interface number";
          range "0";
        }
      }
      leaf Loopback {
        tailf:info
          "Loopback interface";
        tailf:cli-allow-join-with-value {
          tailf:cli-display-joined;
        }
        // NCS drop tailf-common:non-strict-leafref statement
        type string {
          tailf:info
            "<0-2147483647>;;Loopback interface number";
          pattern '([0-9\.])+';
        }
      }
      leaf VirtualPortGroup {
        tailf:info
          "Virtual Port Group";
        tailf:cli-allow-join-with-value {
          tailf:cli-display-joined;
        }
        // NCS drop tailf-common:non-strict-leafref statement
        type uint8 {
          tailf:info
            "<0-31>;;VirtualPortGroup interface number";
        }
      }
      leaf Embedded-Service-Engine {
        tailf:info
          "cisco embedded service engine module";
        tailf:cli-allow-join-with-value {
          tailf:cli-display-joined;
        }
        // NCS drop tailf-common:non-strict-leafref statement
        type string {
          tailf:info
            "<0-2>/<0-0>;;Embedded-Service-Engine interface number";
          pattern '[0-9]+.*';
        }
      }
      leaf Service-Engine {
        tailf:info
          "Cisco service engine module";
        tailf:cli-allow-join-with-value {
          tailf:cli-display-joined;
        }
        // NCS drop tailf-common:non-strict-leafref statement
        type string {
          tailf:info
            "<0-2>/<0-0>;;Service-Engine interface number";
          pattern '[0-9]+.*';
        }
      }
      leaf Tunnel {
        tailf:info
          "Tunnel interface";
        tailf:cli-allow-join-with-value {
          tailf:cli-display-joined;
        }
        // NCS drop tailf-common:non-strict-leafref statement
        type uint32 {
          tailf:info
            "<0-2147483647>;;Tunnel interface number";
        }
      }
      leaf Port-channel {
        tailf:info
          "Ethernet Channel of interfaces";
        tailf:cli-allow-join-with-value {
          tailf:cli-display-joined;
        }
        // NCS drop tailf-common:non-strict-leafref statement
        type uint32 {
          tailf:info
            "<1-512>;;Port-channel interface number";
          range "1..512";
        }
      }
      container Port-channel-subinterface {
        tailf:cli-drop-node-name;
        tailf:cli-flatten-container;
        tailf:cli-compact-syntax;
        leaf Port-channel {
          tailf:cli-allow-join-with-value {
            tailf:cli-display-joined;
          }
          // NCS drop tailf-common:non-strict-leafref statement
          type string {
            pattern '[0-9]+\.[0-9]+';
          }
        }
      }
      leaf Multilink {
        tailf:info
          "Multilink-group interface";
        tailf:cli-allow-join-with-value {
          tailf:cli-display-joined;
        }
        // NCS drop tailf-common:non-strict-leafref statement
        type uint16 {
          tailf:info
            "<1-65535>;;Multilink interface number";
          range "1..65535";
        }
      }
      leaf MFR {
        tailf:info
          "Multilink Frame Relay bundle interface";
        tailf:cli-allow-join-with-value {
          tailf:cli-display-joined;
        }
        // NCS drop tailf-common:non-strict-leafref statement
        type uint32 {
          tailf:info
            "<0-2147483647>;;MFR interface number";
        }
      }
      container MFR-subinterface {
        tailf:cli-drop-node-name;
        tailf:cli-flatten-container;
        tailf:cli-compact-syntax;
        leaf MFR {
          tailf:cli-allow-join-with-value {
            tailf:cli-display-joined;
          }
          // NCS drop tailf-common:non-strict-leafref statement
          type string {
            pattern '[0-9]+\.[0-9]+';
          }
        }
      }
      leaf BRI {
        tailf:info
          "ISDN Basic Rate Interface";
        tailf:cli-allow-join-with-value {
          tailf:cli-display-joined;
        }
        // NCS drop tailf-common:non-strict-leafref statement
        type string {
          tailf:info
            "<slot>/<port>;;BRI interface number";
          pattern '[0-9]+.*';
        }
      }
      leaf Ethernet {
        tailf:info
          "Ethernet";
        tailf:cli-allow-join-with-value {
          tailf:cli-display-joined;
        }
        // NCS drop tailf-common:non-strict-leafref statement
        type string {
          tailf:info
            "<slot>/<port>;;Ethernet interface number";
          pattern '[0-9]+.*';
        }
      }
      leaf FastEthernet {
        tailf:info
          "FastEthernet IEEE 802.3";
        tailf:cli-allow-join-with-value {
          tailf:cli-display-joined;
        }
        // NCS drop tailf-common:non-strict-leafref statement
        type string {
          tailf:info
            "<0-66>/<0-128>;;FastEthernet interface number";
          pattern '[0-9]+.*';
        }
      }
      leaf GigabitEthernet {
        tailf:info
          "GigabitEthernet IEEE 802.3z";
        tailf:cli-allow-join-with-value {
          tailf:cli-display-joined;
        }
        // NCS drop tailf-common:non-strict-leafref statement
        type string {
          tailf:info
            "<0-66>/<0-128>;;GigabitEthernet interface number";
          pattern '[0-9]+.*';
        }
      }
      leaf TenGigabitEthernet {
        tailf:info
          "Ten Gigabit Ethernet";
        tailf:cli-allow-join-with-value {
          tailf:cli-display-joined;
        }
        // NCS drop tailf-common:non-strict-leafref statement
        type string {
          tailf:info
            "<0-66>/<0-128>;;TenGigabitEthernet interface number";
          pattern '[0-9]+.*';
        }
      }
      leaf FortyGigabitEthernet {
        tailf:info
          "Forty Gigabit Ethernet";
        tailf:cli-allow-join-with-value {
          tailf:cli-display-joined;
        }
        // NCS drop tailf-common:non-strict-leafref statement
        type string {
          tailf:info
            "X/Y/Z;;FortyGigabitEthernet interface id";
          pattern '[0-9]+.*';
        }
      }
      leaf HundredGigE {
        tailf:info
          "Hundred Gigabit Ethernet";
        tailf:cli-allow-join-with-value {
          tailf:cli-display-joined;
        }
        // NCS drop tailf-common:non-strict-leafref statement
        type string {
          tailf:info
            "<0-66>/<0-128>;;HundredGigE interface number";
          pattern '[0-9]+.*';
        }
      }
      leaf Wlan-GigabitEthernet {
        tailf:info
          "Wlan-GigabitEthernet interface";
        tailf:cli-allow-join-with-value {
          tailf:cli-display-joined;
        }
        // NCS drop tailf-common:non-strict-leafref statement
        type string {
          tailf:info
            "<0-0>;;Wlan-GigabitEthernet interface number";
          pattern '[0-9]+.*';
        }
      }
      leaf wlan-ap {
        tailf:info
          "Service module interface to embedded AP";
        tailf:cli-allow-join-with-value {
          tailf:cli-display-joined;
        }
        // NCS drop tailf-common:non-strict-leafref statement
        type string {
          tailf:info
            "<0-0>;;wlan-ap interface number";
          pattern '[0-9]+.*';
        }
      }
      leaf ATM {
        tailf:info
          "ATM interface";
        tailf:cli-allow-join-with-value {
          tailf:cli-display-joined;
        }
        // NCS drop tailf-common:non-strict-leafref statement
        type string {
          pattern '[0-9]+.*';
        }
      }
      leaf CEM {
        tailf:info
          "Circuit Emulation interface";
        tailf:cli-allow-join-with-value {
          tailf:cli-display-joined;
        }
        // NCS drop tailf-common:non-strict-leafref statement
        type string {
          pattern '[0-9]+.*';
        }
      }
      leaf BDI {
        tailf:info
          "Bridge-Domain interface";
        tailf:cli-allow-join-with-value {
          tailf:cli-display-joined;
        }
        // NCS drop tailf-common:non-strict-leafref statement
        type uint16 {
          tailf:info
            "<1-4095>;;BDI interface number";
          range "1..4095";
        }
      }
      leaf BVI {
        tailf:info
          "Bridge-Group Virtual Interface";
        tailf:cli-allow-join-with-value {
          tailf:cli-display-joined;
        }
        // NCS drop tailf-common:non-strict-leafref statement
        type string {
          tailf:info
            "<1-255>;;BVI interface number";
          pattern '[0-9]+.*';
        }
      }
      leaf Cable {
        tailf:info
          "CMTS interface";
        tailf:cli-allow-join-with-value {
          tailf:cli-display-joined;
        }
        // NCS drop tailf-common:non-strict-leafref statement
        type string {
          pattern '[0-9]+.*';
        }
      }
      leaf Video {
        tailf:info
          "video service interface";
        tailf:cli-allow-join-with-value {
          tailf:cli-display-joined;
        }
        // NCS drop tailf-common:non-strict-leafref statement
        type string {
          pattern '[0-9]+.*';
        }
      }
      leaf Integrated-Cable {
        tailf:info
          "Integrated Cable interface";
        tailf:cli-allow-join-with-value {
          tailf:cli-display-joined;
        }
        // NCS drop tailf-common:non-strict-leafref statement
        type string {
          pattern '[0-9]+.*';
        }
      }
      leaf Modular-Cable {
        tailf:info
          "Modular Cable interface";
        tailf:cli-allow-join-with-value {
          tailf:cli-display-joined;
        }
        // NCS drop tailf-common:non-strict-leafref statement
        type string {
          pattern '[0-9]+.*';
        }
      }
      leaf Wideband-Cable {
        tailf:info
          "Wideband CMTS interface";
        tailf:cli-allow-join-with-value {
          tailf:cli-display-joined;
        }
        // NCS drop tailf-common:non-strict-leafref statement
        type string {
          pattern '[0-9]+.*';
        }
      }
      leaf Dialer {
        tailf:info
          "Dialer interface";
        tailf:cli-allow-join-with-value {
          tailf:cli-display-joined;
        }
        // NCS drop tailf-common:non-strict-leafref statement
        type string {
          tailf:info
            "<0-255>;;Dialer interface number";
          pattern '[0-9]+.*';
        }
      }
      leaf Bundle {
        tailf:info
          "Virtual Bundle";
        tailf:cli-allow-join-with-value {
          tailf:cli-display-joined;
        }
        // NCS drop tailf-common:non-strict-leafref statement
        type uint8 {
          tailf:info
            "<1-255>;;Bundle interface number";
          range "1..255";
        }
      }
      leaf Cellular {
        tailf:info
          "Cellular";
        tailf:cli-allow-join-with-value {
          tailf:cli-display-joined;
        }
        // NCS drop tailf-common:non-strict-leafref statement
        type string {
          pattern '[0-9]+.*';
        }
      }
      leaf Qam-red {
        tailf:info
          "QAM red interface";
        tailf:cli-allow-join-with-value {
          tailf:cli-display-joined;
        }
        // NCS drop tailf-common:non-strict-leafref statement
        type string {
          pattern '[0-9]+.*';
        }
      }
      leaf Asi {
        tailf:info
          "ASI interface";
        tailf:cli-allow-join-with-value {
          tailf:cli-display-joined;
        }
        // NCS drop tailf-common:non-strict-leafref statement
        type string {
          pattern '[0-9]+.*';
        }
      }
      leaf Vlan {
        tailf:info
          "Catalyst Vlans";
        tailf:cli-allow-join-with-value {
          tailf:cli-display-joined;
        }
        // NCS drop tailf-common:non-strict-leafref statement
        type uint16 {
          tailf:info
            "<1-4094>;;Vlan interface number";
          range "1..4094";
        }
      }
      leaf Async {
        tailf:info
          "Async interface";
        tailf:cli-allow-join-with-value {
          tailf:cli-display-joined;
        }
        // NCS drop tailf-common:non-strict-leafref statement
        type string {
          pattern '[0-9]+.*';
        }
      }
      leaf Group-Async {
        tailf:info
          "Async Group interface";
        tailf:cli-allow-join-with-value {
          tailf:cli-display-joined;
        }
        // NCS drop tailf-common:non-strict-leafref statement
        type uint16;
      }
      leaf POS {
        tailf:info
          "POS interface";
        tailf:cli-allow-join-with-value {
          tailf:cli-display-joined;
        }
        // NCS drop tailf-common:non-strict-leafref statement
        type string {
          pattern '[0-9]+.*';
        }
      }
      leaf Serial {
        tailf:info
          "Serial interface";
        tailf:cli-allow-join-with-value {
          tailf:cli-display-joined;
        }
        // NCS drop tailf-common:non-strict-leafref statement
        type string {
          pattern '[0-9]+(/[\.0-9]+)*(:[0-9]+)?';
        }
      }
      container Serial-subinterface {
        tailf:cli-drop-node-name;
        tailf:cli-flatten-container;
        tailf:cli-compact-syntax;
        leaf Serial {
          tailf:cli-allow-join-with-value {
            tailf:cli-display-joined;
          }
          // NCS drop tailf-common:non-strict-leafref statement
          type string {
            pattern '[0-9]+(/[\.0-9]+)*(:[0-9]+)?\.[0-9]+';
          }
        }
      }
      leaf Virtual-Template {
        tailf:info
          "Virtual Template interface";
        tailf:cli-allow-join-with-value {
          tailf:cli-display-joined;
        }
        // NCS drop tailf-common:non-strict-leafref statement
        type uint16 {
          tailf:info
            "<1-4095>;;Virtual-Template interface number";
          range "1..4095";
        }
      }
      leaf pseudowire {
        tailf:info
          "Pseudowire Interface";
        tailf:cli-allow-join-with-value {
          tailf:cli-display-joined;
        }
        // NCS drop tailf-common:non-strict-leafref statement
        type uint32 {
          tailf:info
            "<1-231072>;;pseudowire interface number";
          range "1..231072";
        }
      }
      leaf LISP {
        tailf:info
          "Locator/ID Separation Protocol Virtual Interface";
        tailf:cli-allow-join-with-value {
          tailf:cli-display-joined;
        }
        // NCS drop tailf-common:non-strict-leafref statement
        type uint16 {
          tailf:info
            "<0-1999>;;LISP interface number";
          range "0..1999";
        }
      }
      container LISP-subinterface {
        tailf:cli-drop-node-name;
        tailf:cli-flatten-container;
        tailf:cli-compact-syntax;
        leaf LISP {
          tailf:cli-allow-join-with-value {
            tailf:cli-display-joined;
          }
          // NCS drop tailf-common:non-strict-leafref statement
          type string {
            pattern '[0-9]+\.[0-9]+';
          }
        }
      }
      leaf ToP {
        tailf:cli-allow-join-with-value {
          tailf:cli-display-joined;
        }
        type string {
          pattern '[0-9]+/[0-9]+';
        }
      }
      leaf Dot11Radio {
        tailf:info
          "IEEE 802.11 WLAN";
        tailf:cli-allow-join-with-value {
          tailf:cli-display-joined;
        }
        // NCS drop tailf-common:non-strict-leafref statement
        type string {
          pattern '[0-9]+.*';
        }
      }
      leaf vasileft {
        tailf:info
          "VasiLeft interface";
        tailf:cli-allow-join-with-value {
          tailf:cli-display-joined;
        }
        // NCS drop tailf-common:non-strict-leafref statement
        type uint16 {
          tailf:info
            "<1-1000>;;vasileft interface number";
          range "1..1000";
        }
      }
      leaf vasiright {
        tailf:info
          "VasiRight interface";
        tailf:cli-allow-join-with-value {
          tailf:cli-display-joined;
        }
        // NCS drop tailf-common:non-strict-leafref statement
        type uint16 {
          tailf:info
            "<1-1000>;;vasiright interface number";
          range "1..1000";
        }
      }
      leaf AppNav-Compress {
        tailf:info
          "Service-Context Virtual Interface Compress";
        tailf:cli-allow-join-with-value {
          tailf:cli-display-joined;
        }
        // NCS drop tailf-common:non-strict-leafref statement
        type uint16 {
          tailf:info
            "<1-1000>;;AppNav-Compress interface number";
          range "1..1000";
        }
      }
      leaf AppNav-UnCompress {
        tailf:info
          "Service-Context Virtual interface UnCompress";
        tailf:cli-allow-join-with-value {
          tailf:cli-display-joined;
        }
        // NCS drop tailf-common:non-strict-leafref statement
        type uint16 {
          tailf:info
            "<1-1000>;;AppNav-UnCompress interface number";
          range "1..1000";
        }
      }
      leaf ucse {
        tailf:info
          "Cisco ucse server";
        tailf:cli-allow-join-with-value {
          tailf:cli-display-joined;
        }
        // NCS drop tailf-common:non-strict-leafref statement
        type string {
          pattern '[0-9]+.*';
        }
      }
    }
  }

  grouping ncs_rpc_notif_service-policy-grouping {
    leaf input {
      tailf:info
        "Assign input policy-map";
      tailf:cli-remove-before-change;
      // NCS drop tailf-common:non-strict-leafref statement
      type string {
        tailf:info
          "WORD;;input Policy-map name";
      }
    }
    leaf output {
      tailf:info
        "Assign output policy-map";
      tailf:cli-remove-before-change;
      // NCS drop tailf-common:non-strict-leafref statement
      type string {
        tailf:info
          "WORD;;output Policy-map name";
      }
    }
  }

  grouping ncs_rpc_notif_police-action-transmit-grouping {
    leaf transmit {
      tailf:info
        "transmit packet";
      type empty;
    }
  }

  grouping ncs_rpc_notif_police-action-drop-grouping {
    leaf drop {
      tailf:info
        "drop packet";
      type empty;
    }
  }

  grouping ncs_rpc_notif_police-conform-action-grouping {
    container conform-action {
      tailf:info
        "action when rate is less than conform burst";
      tailf:cli-flatten-container;
      choice conform-action-choice {
        leaf set-clp-transmit {
          tailf:info
            "set atm clp and send it";
          type empty;
        }
        leaf set-cos-transmit {
          tailf:info
            "rewrite packet cos and send it";
          type cos_value-type;
        }
        leaf set-discard-class-transmit {
          tailf:info
            "set discard-class and send it";
          type uint8 {
            tailf:info
              "<0-7>;;new discard-class";
            range "0..7";
          }
        }
        leaf set-dscp-transmit {
          tailf:info
            "set dscp and send it";
          type dscp-type;
        }
        leaf set-frde-transmit {
          tailf:info
            "set FR DE and send it";
          type empty;
        }
        leaf set-mpls-exp-imposition-transmit {
          tailf:info
            "set exp at tag imposition and send it";
          type exp_value-type;
        }
        leaf set-mpls-exp-topmost-transmit {
          tailf:info
            "set exp on topmost label and send it";
          type exp_value-type;
        }
        leaf set-prec-transmit {
          tailf:info
            "rewrite packet precedence and send it";
          type prec_value-type;
        }
        leaf set-qos-transmit {
          tailf:info
            "set qos-group and send it";
          type qos_value-type;
        }
        leaf transmit {
          tailf:info
            "transmit packet";
          type empty;
        }
        leaf drop {
          tailf:info
            "drop packet";
          type empty;
        }
      }
    }
    leaf table {
      tailf:info
        "Specify conform-action table-map";
      tailf:cli-optional-in-sequence;
      // NCS drop tailf-common:non-strict-leafref statement
      type string {
        tailf:info
          "WORD;;table-map name";
      }
    }
  }

  grouping ncs_rpc_notif_police-exceed-action-grouping {
    container exceed-action {
      tailf:info
        "action when rate is within conform and conform + exceed burst";
      tailf:cli-flatten-container;
      choice exceed-action-choice {
        leaf dscp {
          type dscp-type;
        }
        leaf set-clp-transmit {
          tailf:info
            "set atm clp and send it";
          type empty;
        }
        leaf set-cos-transmit {
          tailf:info
            "rewrite packet cos and send it";
          type cos_value-type;
        }
        leaf set-discard-class-transmit {
          tailf:info
            "set discard-class and send it";
          type uint8 {
            tailf:info
              "<0-7>;;new discard-class";
            range "0..7";
          }
        }
        leaf set-dscp-transmit {
          tailf:info
            "set dscp and send it";
          type dscp-type;
        }
        leaf set-frde-transmit {
          tailf:info
            "set FR DE and send it";
          type empty;
        }
        leaf set-mpls-exp-imposition-transmit {
          tailf:info
            "set exp at tag imposition and send it";
          type exp_value-type;
        }
        leaf set-mpls-exp-topmost-transmit {
          tailf:info
            "set exp on topmost label and send it";
          type exp_value-type;
        }
        leaf set-prec-transmit {
          tailf:info
            "rewrite packet precedence and send it";
          type prec_value-type;
        }
        leaf set-qos-transmit {
          tailf:info
            "set qos-group and send it";
          type qos_value-type;
        }
        leaf transmit {
          tailf:info
            "transmit packet";
          type empty;
        }
        leaf drop {
          tailf:info
            "drop packet";
          type empty;
        }
      }
    }
  }

  grouping ncs_rpc_notif_police-violate-action-grouping {
    container violate-action {
      tailf:info
        "action when rate is greater than conform exceed burst";
      tailf:cli-flatten-container;
      choice violate-action-choice {
        leaf set-clp-transmit {
          tailf:info
            "set atm clp and send it";
          type empty;
        }
        leaf set-cos-transmit {
          tailf:info
            "rewrite packet cos and send it";
          type cos_value-type;
        }
        leaf set-discard-class-transmit {
          tailf:info
            "set discard-class and send it";
          type uint8 {
            tailf:info
              "<0-7>;;new discard-class";
            range "0..7";
          }
        }
        leaf set-dscp-transmit {
          tailf:info
            "set dscp and send it";
          type dscp-type;
        }
        leaf set-frde-transmit {
          tailf:info
            "set FR DE and send it";
          type empty;
        }
        leaf set-mpls-exp-imposition-transmit {
          tailf:info
            "set exp at tag imposition and send it";
          type exp_value-type;
        }
        leaf set-mpls-exp-topmost-transmit {
          tailf:info
            "set exp on topmost label and send it";
          type exp_value-type;
        }
        leaf set-prec-transmit {
          tailf:info
            "rewrite packet precedence and send it";
          type prec_value-type;
        }
        leaf set-qos-transmit {
          tailf:info
            "set qos-group and send it";
          type qos_value-type;
        }
        leaf transmit {
          tailf:info
            "transmit packet";
          type empty;
        }
        leaf drop {
          tailf:info
            "drop packet";
          type empty;
        }
      }
    }
  }

  grouping ncs_rpc_notif_police-multiple-conform-action-grouping {
    container conform-set-clp-transmit {
      tailf:cli-no-keyword;
      tailf:cli-drop-node-name;
      tailf:cli-flatten-container;
      container conform-action {
        tailf:info
          "action when rate is less than conform burst";
        tailf:cli-flatten-container;
        leaf set-clp-transmit {
          tailf:info
            "set atm clp and send it";
          type empty;
        }
      }
    }
    container conform-set-cos-transmit {
      tailf:cli-no-keyword;
      tailf:cli-drop-node-name;
      tailf:cli-flatten-container;
      container conform-action {
        tailf:info
          "action when rate is less than conform burst";
        tailf:cli-flatten-container;
        leaf set-cos-transmit {
          tailf:info
            "rewrite packet cos and send it";
          type cos_value-type;
        }
      }
    }
    container conform-set-cos-transmit-table {
      tailf:cli-no-keyword;
      tailf:cli-drop-node-name;
      tailf:cli-flatten-container;
      container conform-action {
        tailf:info
          "action when rate is less than conform burst";
        tailf:cli-flatten-container;
        tailf:cli-compact-syntax;
        tailf:cli-sequence-commands;
        leaf set-cos-transmit {
          tailf:info
            "rewrite packet cos and send it";
          type cos_value-type;
        }
        leaf table {
          tailf:info
            "Specify table-map";
          // NCS drop tailf-common:non-strict-leafref statement
          type string {
            tailf:info
              "WORD;;table-map name";
          }
        }
      }
    }
    container conform-set-discard-class-transmit {
      tailf:cli-no-keyword;
      tailf:cli-drop-node-name;
      tailf:cli-flatten-container;
      container conform-action {
        tailf:info
          "action when rate is less than conform burst";
        tailf:cli-flatten-container;
        leaf set-discard-class-transmit {
          tailf:info
            "set discard-class and send it";
          type uint8 {
            tailf:info
              "<0-7>;;new discard-class";
            range "0..7";
          }
        }
      }
    }
    container conform-set-dscp-transmit {
      tailf:cli-no-keyword;
      tailf:cli-drop-node-name;
      tailf:cli-flatten-container;
      container conform-action {
        tailf:info
          "action when rate is less than conform burst";
        tailf:cli-flatten-container;
        leaf set-dscp-transmit {
          tailf:info
            "set dscp and send it";
          type dscp-type;
        }
      }
    }
    container conform-set-dscp-transmit-table {
      tailf:cli-no-keyword;
      tailf:cli-drop-node-name;
      tailf:cli-flatten-container;
      container conform-action {
        tailf:info
          "action when rate is less than conform burst";
        tailf:cli-flatten-container;
        tailf:cli-compact-syntax;
        tailf:cli-sequence-commands;
        leaf set-dscp-transmit {
          tailf:info
            "set dscp and send it";
          type dscp-type;
        }
        leaf table {
          tailf:info
            "Specify table-map";
          // NCS drop tailf-common:non-strict-leafref statement
          type string {
            tailf:info
              "WORD;;table-map name";
          }
        }
      }
    }
    container conform-set-frde-transmit {
      tailf:cli-no-keyword;
      tailf:cli-drop-node-name;
      tailf:cli-flatten-container;
      container conform-action {
        tailf:info
          "action when rate is less than conform burst";
        tailf:cli-flatten-container;
        leaf set-frde-transmit {
          tailf:info
            "set FR DE and send it";
          type empty;
        }
      }
    }
    container conform-set-mpls-exp-imposition-transmit {
      tailf:cli-no-keyword;
      tailf:cli-drop-node-name;
      tailf:cli-flatten-container;
      container conform-action {
        tailf:info
          "action when rate is less than conform burst";
        tailf:cli-flatten-container;
        leaf set-mpls-exp-imposition-transmit {
          tailf:info
            "set exp at tag imposition and send it";
          type exp_value-type;
        }
      }
    }
    container conform-set-mpls-exp-imposition-transmit-table {
      tailf:cli-no-keyword;
      tailf:cli-drop-node-name;
      tailf:cli-flatten-container;
      container conform-action {
        tailf:info
          "action when rate is less than conform burst";
        tailf:cli-flatten-container;
        tailf:cli-compact-syntax;
        tailf:cli-sequence-commands;
        leaf set-mpls-exp-imposition-transmit {
          tailf:info
            "set exp at tag imposition and send it";
          type exp_value-type;
        }
        leaf table {
          tailf:info
            "Specify table-map";
          // NCS drop tailf-common:non-strict-leafref statement
          type string {
            tailf:info
              "WORD;;table-map name";
          }
        }
      }
    }
    container conform-set-mpls-exp-topmost-transmit {
      tailf:cli-no-keyword;
      tailf:cli-drop-node-name;
      tailf:cli-flatten-container;
      container conform-action {
        tailf:info
          "action when rate is less than conform burst";
        tailf:cli-flatten-container;
        leaf set-mpls-exp-topmost-transmit {
          tailf:info
            "set exp on topmost label and send it";
          type exp_value-type;
        }
      }
    }
    container conform-set-mpls-exp-topmost-transmit-table {
      tailf:cli-no-keyword;
      tailf:cli-drop-node-name;
      tailf:cli-flatten-container;
      container conform-action {
        tailf:info
          "action when rate is less than conform burst";
        tailf:cli-flatten-container;
        tailf:cli-compact-syntax;
        tailf:cli-sequence-commands;
        leaf set-mpls-exp-topmost-transmit {
          tailf:info
            "set exp on topmost label and send it";
          type exp_value-type;
        }
        leaf table {
          tailf:info
            "Specify table-map";
          // NCS drop tailf-common:non-strict-leafref statement
          type string {
            tailf:info
              "WORD;;table-map name";
          }
        }
      }
    }
    container conform-set-prec-transmit {
      tailf:cli-no-keyword;
      tailf:cli-drop-node-name;
      tailf:cli-flatten-container;
      container conform-action {
        tailf:info
          "action when rate is less than conform burst";
        tailf:cli-flatten-container;
        leaf set-prec-transmit {
          tailf:info
            "rewrite packet precedence and send it";
          type prec_value-type;
        }
      }
    }
    container conform-set-prec-transmit-table {
      tailf:cli-no-keyword;
      tailf:cli-drop-node-name;
      tailf:cli-flatten-container;
      container conform-action {
        tailf:info
          "action when rate is less than conform burst";
        tailf:cli-flatten-container;
        tailf:cli-compact-syntax;
        tailf:cli-sequence-commands;
        leaf set-prec-transmit {
          tailf:info
            "rewrite packet precedence and send it";
          type prec_value-type;
        }
        leaf table {
          tailf:info
            "Specify table-map";
          // NCS drop tailf-common:non-strict-leafref statement
          type string {
            tailf:info
              "WORD;;table-map name";
          }
        }
      }
    }
    container conform-set-qos-transmit {
      tailf:cli-no-keyword;
      tailf:cli-drop-node-name;
      tailf:cli-flatten-container;
      container conform-action {
        tailf:info
          "action when rate is less than conform burst";
        tailf:cli-flatten-container;
        leaf set-qos-transmit {
          tailf:info
            "set qos-group and send it";
          type qos_value-type;
        }
      }
    }
    container conform-set-qos-transmit-table {
      tailf:cli-no-keyword;
      tailf:cli-drop-node-name;
      tailf:cli-flatten-container;
      container conform-action {
        tailf:info
          "action when rate is less than conform burst";
        tailf:cli-flatten-container;
        tailf:cli-compact-syntax;
        tailf:cli-sequence-commands;
        leaf set-qos-transmit {
          tailf:info
            "set qos-group and send it";
          type qos_value-type;
        }
        leaf table {
          tailf:info
            "Specify table-map";
          // NCS drop tailf-common:non-strict-leafref statement
          type string {
            tailf:info
              "WORD;;table-map name";
          }
        }
      }
    }
    container conform-transmit {
      tailf:cli-no-keyword;
      tailf:cli-drop-node-name;
      tailf:cli-flatten-container;
      container conform-action {
        tailf:info
          "action when rate is less than conform burst";
        tailf:cli-flatten-container;
        uses ncs_rpc_notif_police-action-transmit-grouping;
      }
    }
    container conform-drop {
      tailf:cli-no-keyword;
      tailf:cli-drop-node-name;
      tailf:cli-flatten-container;
      container conform-action {
        tailf:info
          "action when rate is less than conform burst";
        tailf:cli-flatten-container;
        uses ncs_rpc_notif_police-action-drop-grouping;
      }
    }
  }

  grouping ncs_rpc_notif_police-multiple-exceed-action-grouping {
    container exceed-dscp {
      tailf:cli-no-keyword;
      tailf:cli-drop-node-name;
      tailf:cli-flatten-container;
      container exceed-action {
        tailf:info
          "action when rate is within conform and conform + exceed burst";
        tailf:cli-flatten-container;
        leaf dscp {
          type dscp-type;
        }
      }
    }
    container exceed-set-clp-transmit {
      tailf:cli-no-keyword;
      tailf:cli-drop-node-name;
      tailf:cli-flatten-container;
      container exceed-action {
        tailf:info
          "action when rate is within conform and conform + exceed burst";
        tailf:cli-flatten-container;
        leaf set-clp-transmit {
          tailf:info
            "set atm clp and send it";
          type empty;
        }
      }
    }
    container exceed-set-cos-transmit {
      tailf:cli-no-keyword;
      tailf:cli-drop-node-name;
      tailf:cli-flatten-container;
      container exceed-action {
        tailf:info
          "action when rate is within conform and conform + exceed burst";
        tailf:cli-flatten-container;
        leaf set-cos-transmit {
          tailf:info
            "rewrite packet cos and send it";
          type cos_value-type;
        }
      }
    }
    container exceed-set-cos-transmit-table {
      tailf:cli-no-keyword;
      tailf:cli-drop-node-name;
      tailf:cli-flatten-container;
      container exceed-action {
        tailf:info
          "action when rate is within conform and conform + exceed burst";
        tailf:cli-flatten-container;
        tailf:cli-compact-syntax;
        tailf:cli-sequence-commands;
        leaf set-cos-transmit {
          tailf:info
            "rewrite packet cos and send it";
          type cos_value-type;
        }
        leaf table {
          tailf:info
            "Specify table-map";
          // NCS drop tailf-common:non-strict-leafref statement
          type string {
            tailf:info
              "WORD;;table-map name";
          }
        }
      }
    }
    container exceed-set-discard-class-transmit {
      tailf:cli-no-keyword;
      tailf:cli-drop-node-name;
      tailf:cli-flatten-container;
      container exceed-action {
        tailf:info
          "action when rate is within conform and conform + exceed burst";
        tailf:cli-flatten-container;
        leaf set-discard-class-transmit {
          tailf:info
            "set discard-class and send it";
          type uint8 {
            tailf:info
              "<0-7>;;new discard-class";
            range "0..7";
          }
        }
      }
    }
    container exceed-set-dscp-transmit {
      tailf:cli-no-keyword;
      tailf:cli-drop-node-name;
      tailf:cli-flatten-container;
      container exceed-action {
        tailf:info
          "action when rate is within conform and conform + exceed burst";
        tailf:cli-flatten-container;
        leaf set-dscp-transmit {
          tailf:info
            "set dscp and send it";
          type dscp-type;
        }
      }
    }
    container exceed-set-frde-transmit {
      tailf:cli-no-keyword;
      tailf:cli-drop-node-name;
      tailf:cli-flatten-container;
      container exceed-action {
        tailf:info
          "action when rate is within conform and conform + exceed burst";
        tailf:cli-flatten-container;
        leaf set-frde-transmit {
          tailf:info
            "set FR DE and send it";
          type empty;
        }
      }
    }
    container exceed-set-mpls-exp-imposition-transmit {
      tailf:cli-no-keyword;
      tailf:cli-drop-node-name;
      tailf:cli-flatten-container;
      container exceed-action {
        tailf:info
          "action when rate is within conform and conform + exceed burst";
        tailf:cli-flatten-container;
        leaf set-mpls-exp-imposition-transmit {
          tailf:info
            "set exp at tag imposition and send it";
          type exp_value-type;
        }
      }
    }
    container exceed-set-mpls-exp-topmost-transmit {
      tailf:cli-no-keyword;
      tailf:cli-drop-node-name;
      tailf:cli-flatten-container;
      container exceed-action {
        tailf:info
          "action when rate is within conform and conform + exceed burst";
        tailf:cli-flatten-container;
        leaf set-mpls-exp-topmost-transmit {
          tailf:info
            "set exp on topmost label and send it";
          type exp_value-type;
        }
      }
    }
    container exceed-set-prec-transmit {
      tailf:cli-no-keyword;
      tailf:cli-drop-node-name;
      tailf:cli-flatten-container;
      container exceed-action {
        tailf:info
          "action when rate is within conform and conform + exceed burst";
        tailf:cli-flatten-container;
        leaf set-prec-transmit {
          tailf:info
            "rewrite packet precedence and send it";
          type prec_value-type;
        }
      }
    }
    container exceed-set-qos-transmit {
      tailf:cli-no-keyword;
      tailf:cli-drop-node-name;
      tailf:cli-flatten-container;
      container exceed-action {
        tailf:info
          "action when rate is within conform and conform + exceed burst";
        tailf:cli-flatten-container;
        leaf set-qos-transmit {
          tailf:info
            "set qos-group and send it";
          type qos_value-type;
        }
      }
    }
    container exceed-set-qos-transmit-table {
      tailf:cli-no-keyword;
      tailf:cli-drop-node-name;
      tailf:cli-flatten-container;
      container exceed-action {
        tailf:info
          "action when rate is within conform and conform + exceed burst";
        tailf:cli-flatten-container;
        tailf:cli-compact-syntax;
        tailf:cli-sequence-commands;
        leaf set-qos-transmit {
          tailf:info
            "set qos-group and send it";
          type cos_value-type;
        }
        leaf table {
          tailf:info
            "Specify table-map";
          // NCS drop tailf-common:non-strict-leafref statement
          type string {
            tailf:info
              "WORD;;table-map name";
          }
        }
      }
    }
    container exceed-transmit {
      tailf:cli-no-keyword;
      tailf:cli-drop-node-name;
      tailf:cli-flatten-container;
      container exceed-action {
        tailf:info
          "action when rate is within conform and conform + exceed burst";
        tailf:cli-flatten-container;
        uses ncs_rpc_notif_police-action-transmit-grouping;
      }
    }
    container exceed-drop {
      tailf:cli-no-keyword;
      tailf:cli-drop-node-name;
      tailf:cli-flatten-container;
      container exceed-action {
        tailf:info
          "action when rate is within conform and conform + exceed burst";
        tailf:cli-flatten-container;
        uses ncs_rpc_notif_police-action-drop-grouping;
      }
    }
  }

  grouping ncs_rpc_notif_police-multiple-violate-action-grouping {
    container violate-set-clp-transmit {
      tailf:cli-no-keyword;
      tailf:cli-drop-node-name;
      tailf:cli-flatten-container;
      container violate-action {
        tailf:info
          "action when rate is greater than conform + exceed burst";
        tailf:cli-flatten-container;
        leaf set-clp-transmit {
          tailf:info
            "set atm clp and send it";
          type empty;
        }
      }
    }
    container violate-set-cos-transmit {
      tailf:cli-no-keyword;
      tailf:cli-drop-node-name;
      tailf:cli-flatten-container;
      container violate-action {
        tailf:info
          "action when rate is greater than conform + exceed burst";
        tailf:cli-flatten-container;
        leaf set-cos-transmit {
          tailf:info
            "rewrite packet cos and send it";
          type cos_value-type;
        }
      }
    }
    container violate-set-discard-class-transmit {
      tailf:cli-no-keyword;
      tailf:cli-drop-node-name;
      tailf:cli-flatten-container;
      container violate-action {
        tailf:info
          "action when rate is greater than conform + exceed burst";
        tailf:cli-flatten-container;
        leaf set-discard-class-transmit {
          tailf:info
            "set discard-class and send it";
          type uint8 {
            tailf:info
              "<0-7>;;new discard-class";
            range "0..7";
          }
        }
      }
    }
    container violate-set-dscp-transmit {
      tailf:cli-no-keyword;
      tailf:cli-drop-node-name;
      tailf:cli-flatten-container;
      container violate-action {
        tailf:info
          "action when rate is greater than conform + exceed burst";
        tailf:cli-flatten-container;
        leaf set-dscp-transmit {
          tailf:info
            "set dscp and send it";
          type dscp-type;
        }
      }
    }
    container violate-set-frde-transmit {
      tailf:cli-no-keyword;
      tailf:cli-drop-node-name;
      tailf:cli-flatten-container;
      container violate-action {
        tailf:info
          "action when rate is greater than conform + exceed burst";
        tailf:cli-flatten-container;
        leaf set-frde-transmit {
          tailf:info
            "set FR DE and send it";
          type empty;
        }
      }
    }
    container violate-set-mpls-exp-imposition-transmit {
      tailf:cli-no-keyword;
      tailf:cli-drop-node-name;
      tailf:cli-flatten-container;
      container violate-action {
        tailf:info
          "action when rate is greater than conform + exceed burst";
        tailf:cli-flatten-container;
        leaf set-mpls-exp-imposition-transmit {
          tailf:info
            "set exp at tag imposition and send it";
          type exp_value-type;
        }
      }
    }
    container violate-set-mpls-exp-topmost-transmit {
      tailf:cli-no-keyword;
      tailf:cli-drop-node-name;
      tailf:cli-flatten-container;
      container violate-action {
        tailf:info
          "action when rate is greater than conform + exceed burst";
        tailf:cli-flatten-container;
        leaf set-mpls-exp-topmost-transmit {
          tailf:info
            "set exp on topmost label and send it";
          type exp_value-type;
        }
      }
    }
    container violate-set-prec-transmit {
      tailf:cli-no-keyword;
      tailf:cli-drop-node-name;
      tailf:cli-flatten-container;
      container violate-action {
        tailf:info
          "action when rate is greater than conform + exceed burst";
        tailf:cli-flatten-container;
        leaf set-prec-transmit {
          tailf:info
            "rewrite packet precedence and send it";
          type prec_value-type;
        }
      }
    }
    container violate-set-qos-transmit {
      tailf:cli-no-keyword;
      tailf:cli-drop-node-name;
      tailf:cli-flatten-container;
      container violate-action {
        tailf:info
          "action when rate is greater than conform + exceed burst";
        tailf:cli-flatten-container;
        leaf set-qos-transmit {
          tailf:info
            "set qos-group and send it";
          type qos_value-type;
        }
      }
    }
    container violate-transmit {
      tailf:cli-no-keyword;
      tailf:cli-drop-node-name;
      tailf:cli-flatten-container;
      container violate-action {
        tailf:info
          "action when rate is greater than conform + exceed burst";
        tailf:cli-flatten-container;
        uses ncs_rpc_notif_police-action-transmit-grouping;
      }
    }
    container violate-drop {
      tailf:cli-no-keyword;
      tailf:cli-drop-node-name;
      tailf:cli-flatten-container;
      container violate-action {
        tailf:info
          "action when rate is greater than conform + exceed burst";
        tailf:cli-flatten-container;
        uses ncs_rpc_notif_police-action-drop-grouping;
      }
    }
  }

  grouping ncs_rpc_notif_police-action-grouping {
    container actions {
      tailf:cli-break-sequence-commands;
      tailf:cli-no-keyword;
      tailf:cli-drop-node-name;
      tailf:cli-flatten-container;
      uses ncs_rpc_notif_police-multiple-conform-action-grouping;
      uses ncs_rpc_notif_police-multiple-exceed-action-grouping;
      uses ncs_rpc_notif_police-multiple-violate-action-grouping;
    }
  }

  grouping ncs_rpc_notif_policy-map-class-grouping {
    leaf pass-through {
      tailf:info
        "pass-through action";
      tailf:cli-full-command;
      type empty;
    }
    container policy {
      tailf:cli-drop-node-name;
      tailf:cli-compact-syntax;
      tailf:cli-sequence-commands {
        tailf:cli-reset-siblings;
      }
      leaf action {
        tailf:cli-drop-node-name;
        tailf:cli-remove-before-change;
        type enumeration {
          enum "drop" {
            tailf:info
              "Drop the packet";
          }
          enum "inspect" {
            tailf:info
              "Context-based Access Control Engine";
          }
          enum "pass" {
            tailf:info
              "Pass the packet";
          }
        }
      }
      leaf log {
        when "(../action = 'drop') or (../action = 'pass')" {
          tailf:xpath-root 3;
          tailf:dependency "../action";
        }
        tailf:info
          "Send logging message for drop|pass";
        tailf:cli-optional-in-sequence;
        type empty;
      }
      leaf parameter-map {
        tailf:cli-drop-node-name;
        when "../action = 'inspect'" {
          tailf:xpath-root 3;
          tailf:dependency "../action";
        }
        // NCS drop tailf-common:non-strict-leafref statement
        type string {
          tailf:info
            "WORD;;Parameter-map (inspect) name";
        }
      }
    }
    container inspect-police {
      when "../policy/action = 'inspect'" {
        tailf:xpath-root 3;
        tailf:dependency "../policy/action";
      }
      tailf:cli-drop-node-name;
      container police {
        tailf:info
          "Police";
        tailf:cli-compact-syntax;
        tailf:cli-sequence-commands {
          tailf:cli-reset-siblings;
        }
        leaf rate {
          tailf:info
            "Specify police rate";
          type uint32 {
            tailf:info
              "<8000-2000000000>;;Rate value in bps";
            range "8000..2000000000";
          }
        }
        leaf burst {
          tailf:info
            "Specify 'burst' parameter";
          type uint32 {
            tailf:info
              "<1000-512000000>;;Burst value in bytes";
            range "1000..512000000";
          }
        }
      }
    }
    container bandwidth {
      tailf:info
        "Bandwidth";
      leaf bits {
        tailf:cli-drop-node-name;
        type uint32 {
          tailf:info
            "<8-10000000>;;Kilo Bits per second";
          range "8..10000000";
        }
      }
      leaf percent {
        tailf:info
          "% of total Bandwidth";
        tailf:cli-remove-before-change;
        type percentage-type;
      }
      container remaining {
        tailf:info
          "% of the remaining bandwidth";
        container percent {
          tailf:info
            "% of the remaining bandwidth";
          tailf:cli-compact-syntax;
          tailf:cli-sequence-commands;
          leaf percent {
            tailf:cli-diff-dependency "../../ratio/ratio" {
              tailf:xpath-root 3;
              tailf:cli-trigger-on-set;
            }
            tailf:cli-drop-node-name;
            type percentage-type;
          }
          uses ncs_rpc_notif_bandwidth-remaining-account-grouping;
        }
        container ratio {
          tailf:info
            "ratio for sharing excess bandwidth";
          tailf:cli-compact-syntax;
          tailf:cli-sequence-commands;
          leaf ratio {
            tailf:cli-drop-node-name;
            type uint32 {
              tailf:info
                "<1-65536>;;Ratio";
              range "1..65536";
            }
          }
          uses ncs_rpc_notif_bandwidth-remaining-account-grouping;
        }
      }
    }
    container compression {
      tailf:info
        "Activate Compression";
      presence "Activate Compression";
      container header {
        tailf:info
          "configure header compression";
        presence "configure header compression";
        leaf ip {
          tailf:info
            "configure ip header compression";
          type enumeration {
            enum "rtp" {
              tailf:code-name "header_rtp";
              tailf:info
                "configure rtp header compression";
            }
            enum "tcp" {
              tailf:info
                "configure tcp header compression";
            }
          }
        }
      }
    }
    leaf dbl {
      tailf:info
        "enable dynamic buffer limiting";
      tailf:cli-full-command;
      type empty;
    }
    container estimate {
      tailf:info
        "estimate resources required for this class";
      container bandwidth {
        tailf:info
          "bandwidth required to service this class";
        tailf:cli-compact-syntax;
        tailf:cli-sequence-commands;
        presence "true";
        container delay-one-in {
          tailf:info
            "specify QoS target delay";
          tailf:cli-compact-syntax;
          tailf:cli-sequence-commands;
          leaf doi {
            tailf:cli-drop-node-name;
            tailf:cli-incomplete-command;
            type uint32 {
              range "50..1000000";
              tailf:info
                "<50-1000000>;;delay one packet of N";
            }
          }
          leaf milliseconds {
            type uint32 {
              range "8..1000" {
                tailf:info
                  "<8-1000>;;worst-case milliseconds of delay";
              }
            }
          }
        }
        leaf drop-one-in {
          tailf:info
            "specify QoS target loss rate";
          type uint32 {
            tailf:info
              "<50-1000000>;;drop one packet of N";
          }
        }
      }
    }
    container fair-queue {
      tailf:info
        "Enable Flow-based Fair Queuing in this Class";
      tailf:cli-reset-container;
      presence "true";
      leaf dynamic-queues {
        tailf:cli-drop-node-name;
        tailf:cli-full-command;
        type uint32 {
          range "16|32|64|128|256|512|1024|2048|4096" {
            tailf:info
              "<16-4096>;;Number Dynamic Conversation Queues";
          }
        }
      }
      leaf queue-limit {
        tailf:info
          "per flow queue limit";
        tailf:cli-full-command;
        type uint16 {
          tailf:info
            "<1-32768>;;packets";
          range "1..32768";
        }
      }
    }
    container flow {
      tailf:info
        "Flow subcommands";
      leaf monitor {
        tailf:info
          "Apply a Flow Monitor";
        // NCS drop tailf-common:non-strict-leafref statement
        type string {
          tailf:info
            "WORD;;Flow Monitor name";
        }
      }
    }
    leaf netflow-sampler {
      tailf:info
        "NetFlow action";
      tailf:cli-full-command;
      type string {
        tailf:info
          "WORD;;Name of the flow sampler";
      }
    }
    container police-aggregate {
      tailf:cli-no-keyword;
      tailf:cli-drop-node-name;
      container police {
        tailf:info
          "Police";
        leaf aggregate {
          tailf:info
            "Choose aggregate policer for current class";
          tailf:cli-diff-dependency "/ios:qos/aggregate-policer" {
            tailf:xpath-root 3;
          }
          tailf:cli-diff-dependency "../../../police-policy-map/police/cir" {
            tailf:xpath-root 3;
            tailf:cli-trigger-on-set;
          }
          type string {
            tailf:info
              "WORD;;enter aggregate-policer name";
          }
        }
      }
    }
    choice police-choice {
      case police-cirmode-case {
        container police-policy-map {
          tailf:cli-no-keyword;
          tailf:cli-drop-node-name;
          container police {
            tailf:cli-add-mode;
            tailf:cli-mode-name "config-pmap-c-police";
            tailf:cli-flatten-container;
            tailf:cli-sequence-commands {
              tailf:cli-reset-siblings;
            }
            when "contains(/ios:tailfned/police, 'cirmode')" {
              tailf:xpath-root 3;
              // NCS drop tailf-common:dependency statement
            }
            leaf cir {
              tailf:info
                "Committed information rate";
              tailf:cli-hide-in-submode;
              tailf:cli-diff-dependency "../../../police-aggregate/police/aggregate" {
                tailf:xpath-root 3;
                tailf:cli-trigger-on-set;
              }
              type police-bps-type;
            }
            leaf bc {
              tailf:info
                "Conform burst";
              tailf:cli-optional-in-sequence;
              tailf:cli-hide-in-submode;
              type police-burst-type;
            }
            leaf be {
              when "../bc" {
                tailf:xpath-root 3;
                tailf:dependency "../bc";
              }
              tailf:info
                "Excess burst";
              tailf:cli-optional-in-sequence;
              tailf:cli-hide-in-submode;
              type police-burst-type;
            }
            leaf pir {
              tailf:info
                "Peak Information Rate";
              tailf:cli-optional-in-sequence;
              tailf:cli-hide-in-submode;
              type police-bps-type;
            }
            container pir-be {
              when "../pir" {
                tailf:xpath-root 3;
                tailf:dependency "../pir";
              }
              tailf:cli-drop-node-name;
              tailf:cli-optional-in-sequence;
              tailf:cli-flatten-container;
              tailf:cli-hide-in-submode;
              leaf be {
                tailf:info
                  "Excess burst";
                type police-burst-type;
              }
            }
            uses ncs_rpc_notif_police-action-grouping;
            container conform-color {
              tailf:info
                "conform color aware";
              tailf:cli-compact-syntax;
              tailf:cli-sequence-commands {
                tailf:cli-reset-siblings;
              }
              leaf class-map-name {
                tailf:cli-drop-node-name;
                // NCS drop tailf-common:non-strict-leafref statement
                type string {
                  tailf:info
                    "WORD;;class-map name for conform color aware";
                }
              }
              leaf exceed-color {
                tailf:info
                  "exceed color aware";
                // NCS drop tailf-common:non-strict-leafref statement
                type string {
                  tailf:info
                    "WORD;;lass-map name for exceed color aware";
                }
              }
            }
          }
        }
      }
      case police-cir-percent-case {
        container police-cir-percent {
          tailf:cli-no-keyword;
          tailf:cli-drop-node-name;
          container police {
            container cir {
              tailf:info
                "Committed information rate";
              container percent {
                tailf:info
                  "% of interface bandwidth for Committed information rate";
                tailf:cli-add-mode;
                tailf:cli-mode-name "config-pmap-c-police";
                tailf:cli-incomplete-command;
                tailf:cli-flatten-container;
                tailf:cli-sequence-commands {
                  tailf:cli-reset-siblings;
                }
                leaf percentage {
                  tailf:cli-drop-node-name;
                  tailf:cli-hide-in-submode;
                  type percentage-type;
                }
                leaf bc {
                  tailf:info
                    "Conform burst";
                  tailf:cli-optional-in-sequence;
                  tailf:cli-hide-in-submode;
                  type uint16 {
                    tailf:info
                      "<1-2000>;;Burst ms";
                  }
                }
                container bc-ms {
                  when "../bc" {
                    tailf:xpath-root 3;
                    tailf:dependency "../bc";
                  }
                  tailf:cli-drop-node-name;
                  tailf:cli-optional-in-sequence;
                  tailf:cli-hide-in-submode;
                  tailf:cli-flatten-container;
                  tailf:cli-compact-syntax;
                  leaf ms {
                    tailf:info
                      "Milli seconds";
                    tailf:cli-no-keyword;
                    type empty;
                  }
                }
                leaf be {
                  when "../bc-ms/ms" {
                    tailf:xpath-root 3;
                    tailf:dependency "../bc-ms/ms";
                  }
                  tailf:info
                    "Excess burst";
                  tailf:cli-optional-in-sequence;
                  tailf:cli-hide-in-submode;
                  type uint16 {
                    tailf:info
                      "<1-2000>;;Burst ms";
                  }
                }
                container be-ms {
                  when "../be" {
                    tailf:xpath-root 3;
                    tailf:dependency "../be";
                  }
                  tailf:cli-drop-node-name;
                  tailf:cli-hide-in-submode;
                  tailf:cli-flatten-container;
                  tailf:cli-compact-syntax;
                  leaf ms {
                    tailf:info
                      "Milli seconds";
                    tailf:cli-no-keyword;
                    type empty;
                  }
                }
                container pir {
                  tailf:info
                    "Peak Information Rate";
                  tailf:cli-flatten-container;
                  tailf:cli-compact-syntax;
                  tailf:cli-hide-in-submode;
                  tailf:cli-optional-in-sequence;
                  leaf percent {
                    tailf:info
                      "% of interface bandwidth for Peak Information Rate";
                    type percentage-type;
                  }
                }
                container pir-be {
                  when "../pir" {
                    tailf:xpath-root 3;
                    tailf:dependency "../pir";
                  }
                  tailf:cli-drop-node-name;
                  tailf:cli-optional-in-sequence;
                  tailf:cli-flatten-container;
                  tailf:cli-hide-in-submode;
                  leaf be {
                    tailf:info
                      "Excess burst";
                    type uint16 {
                      tailf:info
                        "<1-2000>;;Burst ms";
                    }
                  }
                }
                container pir-be-ms {
                  when "../pir-be/be" {
                    tailf:xpath-root 3;
                    tailf:dependency "../pir-be/be";
                  }
                  tailf:cli-drop-node-name;
                  tailf:cli-optional-in-sequence;
                  tailf:cli-hide-in-submode;
                  tailf:cli-flatten-container;
                  leaf ms {
                    tailf:info
                      "Milli seconds";
                    tailf:cli-no-keyword;
                    type empty;
                  }
                }
                uses ncs_rpc_notif_police-action-grouping;
              }
            }
          }
        }
      }
      case police-rate-unit-case {
        container police-rate-unit {
          tailf:cli-no-keyword;
          tailf:cli-drop-node-name;
          container police {
            container rate {
              tailf:info
                "Specify police rate";
              tailf:cli-add-mode;
              tailf:cli-mode-name "config-pmap-c-police";
              tailf:cli-sequence-commands {
                tailf:cli-reset-siblings;
              }
              leaf units {
                tailf:cli-drop-node-name;
                tailf:cli-hide-in-submode;
                type uint64 {
                  tailf:info
                    "<1-2000000000>;;Rate value in the range 8000-2,000,000,000 bps or 1-2,000,000 pps";
                }
              }
              leaf xps {
                tailf:cli-no-keyword;
                tailf:cli-drop-node-name;
                tailf:cli-optional-in-sequence;
                tailf:cli-hide-in-submode;
                type police-pps-bps-type;
              }
              leaf burst {
                tailf:info
                  "Specify 'burst' parameter";
                tailf:cli-optional-in-sequence;
                tailf:cli-hide-in-submode;
                type uint32 {
                  tailf:info
                    "<1-512000000>;;Burst value in packets/bytes";
                }
              }
              leaf burst-type {
                when "../burst" {
                  tailf:xpath-root 3;
                  tailf:dependency "../burst";
                }
                tailf:cli-no-keyword;
                tailf:cli-drop-node-name;
                tailf:cli-optional-in-sequence;
                tailf:cli-hide-in-submode;
                type police-packets-bytes-type;
              }
              leaf peak-rate {
                tailf:info
                  "Specify peak rate";
                tailf:cli-optional-in-sequence;
                tailf:cli-hide-in-submode;
                type uint32 {
                  tailf:info
                    "<1-512000000>;;Peak-rate value in packets or bytes per second";
                  range "1..512000000";
                }
              }
              leaf peak-rate-type {
                when "../peak-rate" {
                  tailf:xpath-root 3;
                  tailf:dependency "../peak-rate";
                }
                tailf:cli-no-keyword;
                tailf:cli-drop-node-name;
                tailf:cli-optional-in-sequence;
                tailf:cli-hide-in-submode;
                type police-pps-bps-type;
              }
              leaf peak-burst {
                tailf:info
                  "Specify 'peak-burst' parameter for peak-rate";
                tailf:cli-optional-in-sequence;
                tailf:cli-hide-in-submode;
                type uint32 {
                  tailf:info
                    "<1-512000000>;;Burst value in packets/bytes";
                }
              }
              leaf peak-burst-type {
                when "../peak-burst" {
                  tailf:xpath-root 3;
                  tailf:dependency "../peak-burst";
                }
                tailf:cli-no-keyword;
                tailf:cli-drop-node-name;
                tailf:cli-optional-in-sequence;
                tailf:cli-hide-in-submode;
                type police-packets-bytes-type;
              }
              uses ncs_rpc_notif_police-action-grouping;
            }
          }
        }
      }
      case police-rate-percent-case {
        container police-rate-percent {
          tailf:cli-no-keyword;
          tailf:cli-drop-node-name;
          container police {
            container rate {
              tailf:info
                "Specify police rate";
              container percent {
                tailf:info
                  "% of interface bandwidth for rate";
                tailf:cli-add-mode;
                tailf:cli-mode-name "config-pmap-c-police";
                tailf:cli-sequence-commands {
                  tailf:cli-reset-siblings;
                }
                leaf percentage {
                  tailf:cli-drop-node-name;
                  tailf:cli-hide-in-submode;
                  type percentage-type;
                }
                leaf burst {
                  tailf:info
                    "Specify 'burst' parameter";
                  tailf:cli-optional-in-sequence;
                  tailf:cli-hide-in-submode;
                  type uint16 {
                    tailf:info
                      "<1-2000>;;Burst value in milliseconds";
                  }
                }
                leaf ms {
                  when "../burst" {
                    tailf:xpath-root 3;
                    tailf:dependency "../burst";
                  }
                  tailf:info
                    "Treat 'burst' value in milliseconds";
                  tailf:cli-hide-in-submode;
                  type empty;
                }
                container peak-rate {
                  tailf:info
                    "Specify peak rate";
                  tailf:cli-hide-in-submode;
                  tailf:cli-optional-in-sequence;
                  tailf:cli-flatten-container;
                  leaf percent {
                    tailf:info
                      "% of interface bandwidth for peak-rate";
                    type percentage-type;
                  }
                }
                leaf peak-burst {
                  tailf:info
                    "Specify 'peak-burst' parameter for 'peak-rate'";
                  tailf:cli-hide-in-submode;
                  tailf:cli-optional-in-sequence;
                  type uint16 {
                    tailf:info
                      "<1-2000>;;Peak burst value in milliseconds";
                  }
                }
                container peak-burst-ms {
                  when "../peak-burst" {
                    tailf:xpath-root 3;
                    tailf:dependency "../peak-burst";
                  }
                  tailf:cli-drop-node-name;
                  tailf:cli-optional-in-sequence;
                  tailf:cli-hide-in-submode;
                  tailf:cli-flatten-container;
                  leaf ms {
                    tailf:info
                      "Milli seconds";
                    tailf:cli-no-keyword;
                    type empty;
                  }
                }
                uses ncs_rpc_notif_police-action-grouping;
              }
            }
          }
        }
      }
      case police-rate-pdp-case {
        container police-rate-pdp {
          tailf:cli-no-keyword;
          tailf:cli-drop-node-name;
          container police {
            container rate {
              tailf:info
                "Specify police rate";
              container pdp {
                tailf:info
                  "% of interface bandwidth for rate";
                tailf:cli-add-mode;
                tailf:cli-mode-name "config-pmap-c-police";
                tailf:cli-flatten-container;
                tailf:cli-sequence-commands {
                  tailf:cli-reset-siblings;
                }
                leaf burst {
                  tailf:info
                    "Conform burst";
                  tailf:cli-hide-in-submode;
                  tailf:cli-optional-in-sequence;
                  type police-burst-type;
                }
                leaf peak-rate {
                  tailf:info
                    "Specify peak rate";
                  tailf:cli-hide-in-submode;
                  tailf:cli-optional-in-sequence;
                  type enumeration {
                    enum "pdp";
                  }
                }
                leaf peak-burst {
                  when "../peak-rate" {
                    tailf:xpath-root 3;
                    tailf:dependency "../peak-rate";
                  }
                  tailf:info
                    "Specify 'peak-burst' parameter for 'peak-rate'";
                  tailf:cli-hide-in-submode;
                  tailf:cli-optional-in-sequence;
                  type police-burst-type;
                }
                uses ncs_rpc_notif_police-action-grouping;
              }
            }
          }
        }
      }
      case police-flow-case {
        container police-flow {
          tailf:cli-no-keyword;
          tailf:cli-drop-node-name;
          container police {
            container flow {
              tailf:info
                "police each flow";
              tailf:cli-add-mode;
              tailf:cli-mode-name "config-pmap-c-police";
              tailf:cli-flatten-container;
              tailf:cli-sequence-commands {
                tailf:cli-reset-siblings;
              }
              leaf mask {
                tailf:info
                  "flow mask to be used for policing";
                tailf:cli-hide-in-submode;
                tailf:cli-optional-in-sequence;
                type enumeration {
                  enum "dest-only" {
                    tailf:info
                      "destination-address only flow mask";
                  }
                  enum "full-flow" {
                    tailf:info
                      "full flow mask";
                  }
                  enum "src-only" {
                    tailf:info
                      "source-address only flow mask";
                  }
                }
              }
              leaf bps {
                tailf:cli-drop-node-name;
                tailf:cli-hide-in-submode;
                type police-bps-type;
              }
              leaf burst-normal {
                when "../bps" {
                  tailf:xpath-root 3;
                  tailf:dependency "../bps";
                }
                tailf:cli-drop-node-name;
                tailf:cli-hide-in-submode;
                tailf:cli-optional-in-sequence;
                type police-burst-type;
              }
              uses ncs_rpc_notif_police-action-grouping;
            }
          }
        }
      }
      case police-bpsflat-case {
        container police-catalyst {
          tailf:cli-no-keyword;
          tailf:cli-drop-node-name;
          container police {
            tailf:cli-add-mode;
            tailf:cli-mode-name "config-pmap-c-police";
            tailf:cli-flatten-container;
            tailf:cli-sequence-commands {
              tailf:cli-reset-siblings;
            }
            when "contains(/ios:tailfned/police, 'bpsflat')" {
              tailf:xpath-root 3;
              // NCS drop tailf-common:dependency statement
            }
            leaf bps-value {
              tailf:cli-no-keyword;
              tailf:cli-drop-node-name;
              tailf:cli-hide-in-submode;
              tailf:cli-incomplete-command;
              type string {
                tailf:info
                  "<32000-32000000000>;;Rate in bits per second (postfix k, m, g optional; decimal point allowed)";
              }
            }
            leaf bps {
              when "../bps-value" {
                tailf:xpath-root 3;
                tailf:dependency "../bps-value";
              }
              tailf:cli-hide-in-submode;
              tailf:cli-incomplete-command;
              type empty;
            }
            leaf byte-value {
              tailf:cli-no-keyword;
              tailf:cli-drop-node-name;
              tailf:cli-hide-in-submode;
              tailf:cli-incomplete-command;
              type string {
                tailf:info
                  "<32000-32000000000>;;(postfix k, m, g optional; decimal point allowed)";
              }
            }
            leaf byte {
              when "../byte-value" {
                tailf:xpath-root 3;
                tailf:dependency "../byte-value";
              }
              tailf:cli-hide-in-submode;
              type empty;
            }
            container actions {
              tailf:cli-break-sequence-commands;
              tailf:cli-no-keyword;
              tailf:cli-drop-node-name;
              tailf:cli-flatten-container;
              tailf:cli-hide-in-submode;
              uses ncs_rpc_notif_police-multiple-conform-action-grouping;
              uses ncs_rpc_notif_police-multiple-exceed-action-grouping;
              uses ncs_rpc_notif_police-multiple-violate-action-grouping;
            }
          }
        }
      }
      case police-switch-case {
        container police-switch {
          tailf:cli-no-keyword;
          tailf:cli-drop-node-name;
          container police {
            tailf:cli-compact-syntax;
            tailf:cli-sequence-commands {
              tailf:cli-reset-siblings;
            }
            when "contains(/ios:tailfned/police, 'numflat')" {
              tailf:xpath-root 3;
              // NCS drop tailf-common:dependency statement
            }
            leaf cir {
              tailf:cli-drop-node-name;
              tailf:cli-incomplete-command;
              tailf:cli-diff-dependency "../../../police-aggregate/police/aggregate" {
                tailf:xpath-root 3;
                tailf:cli-trigger-on-set;
              }
              type uint32 {
                tailf:info
                  "<8000-1000000000>;;Bits per second";
                range "8000..1000000000";
              }
            }
            leaf bc {
              tailf:cli-drop-node-name;
              type uint32 {
                tailf:info
                  "<8000-2000000>;;Normal burst bytes";
                range "8000..2000000";
              }
            }
            leaf exceed-action {
              tailf:info
                "action when rate is exceeded";
              type enumeration {
                enum "drop" {
                  tailf:info
                    "drop packet";
                }
                enum "policed-dscp-transmit" {
                  tailf:info
                    "change dscp per policed-dscp map and send it";
                }
              }
            }
          }
        }
      }
      case police-numflat-case {
        container police-numflat {
          tailf:cli-no-keyword;
          tailf:cli-drop-node-name;
          container police {
            tailf:cli-compact-syntax;
            tailf:cli-sequence-commands {
              tailf:cli-reset-siblings;
            }
            when "contains(/ios:tailfned/police, 'numflat')" {
              tailf:xpath-root 3;
              // NCS drop tailf-common:dependency statement
            }
            leaf cir {
              tailf:cli-drop-node-name;
              tailf:cli-diff-dependency "../../../police-aggregate/police/aggregate" {
                tailf:xpath-root 3;
                tailf:cli-trigger-on-set;
              }
              type police-bps-type;
            }
            leaf bc {
              tailf:cli-drop-node-name;
              tailf:cli-optional-in-sequence;
              type police-burst-type;
            }
            leaf be {
              tailf:cli-drop-node-name;
              tailf:cli-optional-in-sequence;
              type police-burst-type;
            }
            container actions {
              tailf:cli-break-sequence-commands;
              tailf:cli-no-keyword;
              tailf:cli-drop-node-name;
              tailf:cli-flatten-container;
              uses ncs_rpc_notif_police-multiple-conform-action-grouping;
              uses ncs_rpc_notif_police-multiple-exceed-action-grouping;
              uses ncs_rpc_notif_police-multiple-violate-action-grouping;
            }
          }
        }
      }
      case police-cirflat-case {
        container police-cirflat {
          tailf:cli-no-keyword;
          tailf:cli-drop-node-name;
          container police {
            tailf:cli-compact-syntax;
            tailf:cli-sequence-commands {
              tailf:cli-reset-siblings;
            }
            when "contains(/ios:tailfned/police, 'cirflat')" {
              tailf:xpath-root 3;
              // NCS drop tailf-common:dependency statement
            }
            leaf cir {
              tailf:info
                "Committed information rate";
              tailf:cli-diff-dependency "../../../police-aggregate/police/aggregate" {
                tailf:xpath-root 3;
                tailf:cli-trigger-on-set;
              }
              type police-bps-type;
            }
            leaf bc {
              tailf:info
                "Conform burst";
              tailf:cli-optional-in-sequence;
              type police-burst-type;
            }
            leaf pir {
              tailf:info
                "Peak Information Rate";
              tailf:cli-optional-in-sequence;
              type police-bps-type;
            }
            leaf be {
              tailf:info
                "Excess burst";
              tailf:cli-optional-in-sequence;
              type police-burst-type;
            }
            container actions {
              tailf:cli-break-sequence-commands;
              tailf:cli-drop-node-name;
              tailf:cli-flatten-container;
              tailf:cli-compact-syntax;
              tailf:cli-sequence-commands;
              uses ncs_rpc_notif_police-conform-action-grouping;
              uses ncs_rpc_notif_police-exceed-action-grouping;
              uses ncs_rpc_notif_police-violate-action-grouping;
            }
          }
        }
      }
    }
    container priority {
      tailf:info
        "Strict Scheduling Priority for this Class";
      tailf:cli-compact-syntax;
      tailf:cli-sequence-commands;
      tailf:cli-reset-container;
      tailf:cli-delete-when-empty;
      presence "true";
      leaf level {
        tailf:info
          "Multi-Level Priority Queue";
        tailf:cli-optional-in-sequence;
        type uint8 {
          tailf:info
            "<1-2>;;Multi-Level Priority Queue";
          range "1..2";
        }
      }
      choice priority-type {
        leaf kilo-bits {
          tailf:cli-drop-node-name;
          type uint32 {
            tailf:info
              "<8-10000000>;;Kilo Bits per second";
            range "8..10000000";
          }
        }
        leaf percent {
          tailf:info
            "% of total bandwidth";
          tailf:cli-remove-before-change;
          type uint16 {
            tailf:info
              "<1-100>;;percentage";
            range "1..100";
          }
        }
      }
      leaf burst {
        tailf:cli-drop-node-name;
        type uint32 {
          tailf:info
            "<32-64000000>;;Burst in bytes";
          range "32..64000000";
        }
      }
    }
    container shape {
      tailf:info
        "Traffic Shaping";
      leaf adaptive {
        tailf:info
          "Enable Traffic Shaping adaptation to BECN";
        tailf:cli-full-command;
        type uint32 {
          range "8000..154400000";
          tailf:info
            "<8000-154400000>;;Lower Bound Target Bit Rate (bits per second)";
        }
      }
      container average {
        tailf:info
          "configure token bucket: CIR (bps) [Bc (bits) [Be (bits)]], send out Bc only per interval";
        tailf:cli-compact-syntax;
        tailf:cli-sequence-commands;
        choice average-choice {
          case a {
            leaf bit-rate {
              tailf:cli-drop-node-name;
              type uint64 {
                tailf:info
                  "<8000-max>;;Target Bit Rate (bits per second), the value needs to be a multiple of 8000";
              }
            }
            leaf bits-per-interval-sustained {
              tailf:cli-drop-node-name;
              type uint32 {
                tailf:info
                  "<256-154400000>;;bits per interval, sustained. Needs to be multiple of 128. Recommend not to configure it, the algorithm will find out the best value";
                range "256..154400000";
              }
            }
            leaf bits-per-interval-excess {
              tailf:cli-drop-node-name;
              type uint32 {
                range "0..154400000";
                tailf:info
                  "<0-154400000>;;bits per interval, excess. Needs to be multiple of 128. Bc will be used if you don't configure it.";
              }
            }
          }
          case b {
            leaf percent {
              tailf:info
                "% of interface bandwidth for Committed information rate";
              type percentage-type;
            }
            leaf burst-size-sustained {
              tailf:cli-incomplete-command;
              tailf:cli-drop-node-name;
              type uint16 {
                tailf:info
                  "<10-2000>;;Sustained burst size in msec";
                range "10..2000";
              }
            }
            leaf ms {
              tailf:info
                "milliseconds";
              type empty;
            }
            container bse {
              tailf:cli-drop-node-name;
              tailf:cli-flatten-container;
              tailf:cli-compact-syntax;
              tailf:cli-sequence-commands;
              leaf burst-size-excess {
                tailf:cli-incomplete-command;
                type uint16 {
                  tailf:info
                    "<10-2000>;;Excess burst size in msec";
                  range "10..2000";
                }
              }
              leaf ms {
                tailf:info
                  "milliseconds";
                type empty;
              }
            }
          }
          case c {
            leaf target-bit-rate {
              tailf:cli-drop-node-name;
              type uint64 {
                tailf:info
                  "<8000-max>;;Target Bit Rate (bits per second), the value needs to be a multiple of 8000";
              }
            }
            leaf account {
              tailf:info
                "Overhead Accounting";
              tailf:cli-incomplete-command;
              type empty;
            }
            leaf user-defined {
              tailf:info
                "Offset Size";
              type int8 {
                tailf:info
                  "<-63 - 63>;;User Defined size";
                range "-63..63";
              }
            }
            leaf atm {
              tailf:info
                "ATM cell tax";
              type empty;
            }
          }
        }
      }
      leaf fecn-adapt {
        tailf:info
          "Enable Traffic Shaping reflection of FECN as BECN";
        tailf:cli-full-command;
        type empty;
      }
      container fr-voice-adapt {
        tailf:info
          "Enable rate adjustment depending on voice presence";
        presence "true";
        leaf deactivation {
          type uint16 {
            range "1..10000";
            tailf:info
              "<1-10000>;;de-activation delay in seconds";
          }
        }
      }
      leaf max-buffers {
        tailf:cli-full-command;
        tailf:info
          "Set Maximum Buffer Limit";
        type uint16 {
          tailf:info
            "<1-4096>;;Maximum Buffer Limit";
          range "1..4096";
        }
      }
    }
    container queue-limit {
      tailf:info
        "Queue Max Threshold for Tail Drop";
      tailf:cli-compact-syntax;
      tailf:cli-sequence-commands {
        tailf:cli-reset-siblings;
      }
      tailf:cli-diff-dependency "../shape" {
        tailf:xpath-root 3;
      }
      choice queue-limit-choice {
        case queue-limit-percent {
          leaf percent {
            tailf:info
              "% of threshold";
            type percentage-type;
          }
        }
        case queue-limit-dscp {
          list dscp {
            tailf:info
              "parameters for each dscp value";
            tailf:cli-suppress-mode;
            tailf:cli-delete-when-empty;
            tailf:cli-compact-syntax;
            tailf:cli-incomplete-command;
            key "dscp";
            leaf dscp {
              type dscp-type;
            }
            leaf percent {
              tailf:info
                "% of threshold";
              type percentage-type;
            }
          }
        }
        case queue-limit-value {
          leaf queue-limit-value {
            tailf:cli-drop-node-name;
            type uint32 {
              tailf:info
                "<1-8192000>;;in bytes, <1-3400> in ms, <1-32768> in packets by default";
              range "1..8192000";
            }
          }
          leaf queue-limit-type {
            tailf:cli-drop-node-name;
            type enumeration {
              enum "bytes" {
                tailf:info
                  "in bytes";
              }
              enum "ms" {
                tailf:info
                  "in milliseconds";
              }
              enum "us" {
                tailf:info
                  "in microseconds";
              }
              enum "packets" {
                tailf:info
                  "in packets";
              }
            }
          }
        }
      }
    }
    container random-detect {
      tailf:info
        "Enable Random Early Detection as drop policy";
      container base {
        tailf:cli-drop-node-name;
        tailf:cli-compact-syntax;
        tailf:cli-sequence-commands {
          tailf:cli-reset-siblings;
        }
        leaf type {
          tailf:cli-drop-node-name;
          tailf:cli-remove-before-change;
          tailf:cli-diff-dependency "../../../bandwidth/percent" {
            tailf:xpath-root 3;
          }
          type enumeration {
            enum "cos-based" {
              tailf:info
                "Enable cos-class-based WRED as drop policy";
            }
            enum "precedence-based" {
              tailf:info
                "Enable precedence-based WRED as drop policy";
            }
            enum "discard-class-based" {
              tailf:info
                "Enable discard-class-based WRED as drop policy";
            }
            enum "dscp-based" {
              tailf:info
                "Enable dscp-based WRED as drop policy";
            }
          }
        }
        leaf aggregate {
          tailf:info
            "aggregate subclasses";
          type empty;
        }
        leaf minimum-thresh {
          tailf:info
            "minimum threshold for red aggregate";
          tailf:cli-incomplete-command;
          type uint32 {
            tailf:info
              "<0-1000000>;;minimum threshold (number of packets)";
            range "0..1000000";
          }
        }
        leaf maximum-thresh {
          tailf:info
            "maximum threshold for red aggregate";
          type uint32 {
            tailf:info
              "<0-1000000>;;maximum threshold (number of packets)";
            range "0..1000000";
          }
        }
        leaf mark-probability {
          tailf:info
            "mark-probability for red aggregate";
          type empty;
        }
        leaf denominator {
          tailf:cli-drop-node-name;
          type uint32 {
            tailf:info
              "<0-65535>;;mark probability denominator";
            range "0..65535";
          }
        }
      }
      leaf exponential-weighting-constant {
        tailf:info
          "weight for mean queue depth calculation";
        tailf:cli-full-command;
        type uint16 {
          tailf:info
            "<1-16>;;integer in 1..16 used in weighted average to mean 2^number";
          range "1..16";
        }
      }
      leaf ecn {
        tailf:info
          "explicit congestion notification";
        tailf:cli-full-command;
        type empty;
      }
      list cos {
        when "../base/type = 'cos-based'" {
          tailf:xpath-root 3;
          tailf:dependency "../base/type";
        }
        tailf:info
          "parameters for each cos value";
        tailf:cli-suppress-mode;
        tailf:cli-delete-when-empty;
        tailf:cli-compact-syntax;
        tailf:cli-sequence-commands;
        tailf:cli-incomplete-command;
        tailf:cli-diff-dependency "../base/type" {
          tailf:xpath-root 3;
        }
        key "cos";
        leaf cos {
          type uint8 {
            tailf:info
              "<0-7>;;cos value";
            range "0..7";
          }
        }
        uses ncs_rpc_notif_random-detect-grouping;
      }
      list precedence {
        when "../base/type = 'precedence-based'" {
          tailf:xpath-root 3;
          tailf:dependency "../base/type";
        }
        tailf:info
          "parameters for each precedence value";
        tailf:cli-suppress-mode;
        tailf:cli-delete-when-empty;
        tailf:cli-compact-syntax;
        tailf:cli-sequence-commands;
        tailf:cli-incomplete-command;
        tailf:cli-diff-dependency "../base/type" {
          tailf:xpath-root 3;
        }
        key "prec";
        leaf prec {
          type union {
            type uint8 {
              tailf:info
                "<0-7>;;IP precedence";
              range "0..7";
            }
            type enumeration {
              enum "rsvp" {
                tailf:info
                  "rsvp traffic";
              }
            }
          }
        }
        uses ncs_rpc_notif_random-detect-grouping;
      }
      container precedence-values {
        tailf:cli-drop-node-name;
        list precedence {
          tailf:info
            "parameters for each precedence value";
          when "../../base/type = 'precedence-based'" {
            tailf:xpath-root 3;
            tailf:dependency "../../base/type";
          }
          tailf:cli-suppress-mode;
          tailf:cli-delete-when-empty;
          tailf:cli-compact-syntax;
          tailf:cli-sequence-commands;
          tailf:cli-incomplete-command;
          tailf:cli-diff-dependency "../../base/type" {
            tailf:xpath-root 3;
          }
          key "values";
          leaf values {
            tailf:info
              "multiple precedence subclasses";
            tailf:cli-expose-key-name;
            type uint8 {
              tailf:info
                "<0-7>;;SUBCLASS id";
              range "0..7";
            }
          }
          uses ncs_rpc_notif_random-detect-values-grouping;
        }
      }
      list discard-class {
        when "../base/type = 'discard-class-based'" {
          tailf:xpath-root 3;
          tailf:dependency "../base/type";
        }
        tailf:info
          "parameters for each discard-class value";
        tailf:cli-suppress-mode;
        tailf:cli-delete-when-empty;
        tailf:cli-compact-syntax;
        tailf:cli-sequence-commands;
        tailf:cli-incomplete-command;
        tailf:cli-diff-dependency "../base/type" {
          tailf:xpath-root 3;
        }
        key "dclass";
        leaf dclass {
          type uint16 {
            tailf:info
              "<0-7>;;discard-class value";
            range "0..7";
          }
        }
        uses ncs_rpc_notif_random-detect-grouping;
      }
      list dscp {
        when "../base/type = 'dscp-based'" {
          tailf:xpath-root 3;
          tailf:dependency "../base/type";
        }
        tailf:info
          "parameters for each dscp value";
        tailf:cli-suppress-mode;
        tailf:cli-delete-when-empty;
        tailf:cli-compact-syntax;
        tailf:cli-sequence-commands;
        tailf:cli-incomplete-command;
        tailf:cli-diff-dependency "../base/type" {
          tailf:xpath-root 3;
        }
        key "dscpvalue";
        leaf dscpvalue {
          type dscp-type;
        }
        uses ncs_rpc_notif_random-detect-grouping;
      }
    }
    container set {
      tailf:info
        "Set QoS values";
      leaf atm-clp {
        tailf:info
          "Set ATM CLP bit to 1";
        tailf:cli-full-command;
        type empty;
      }
      container cos {
        tailf:info
          "Set IEEE 802.1Q/ISL class of service/user priority";
        tailf:cli-compact-syntax;
        tailf:cli-sequence-commands;
        choice cos-type {
          case a {
            leaf val {
              tailf:cli-drop-node-name;
              type uint16 {
                range "0..7";
                tailf:info
                  "<0-7>;;cos value";
              }
            }
          }
          case b {
            leaf pack {
              tailf:cli-drop-node-name;
              type enumeration {
                enum "dscp" {
                  tailf:code-name "pack_dscp";
                  tailf:info
                    "Set value from packet dscp";
                }
                enum "precedence" {
                  tailf:code-name "pack_precedence";
                  tailf:info
                    "Set value from packet precedence.";
                }
              }
            }
            leaf table {
              tailf:info
                "Set codepoint value based on tablemap.";
              // NCS drop tailf-common:non-strict-leafref statement
              type string {
                tailf:info
                  "WORD;;table-map name";
              }
            }
          }
        }
      }
      leaf discard-class {
        tailf:info
          "Discard behavior identifier";
        tailf:cli-full-command;
        type uint16 {
          range "0..7";
          tailf:info
            "<0-7>;;Discard Class value";
        }
      }
      container dscp {
        tailf:info
          "Set DSCP in IP(v4) and IPv6 packets";
        leaf tunnel {
          tailf:info
            "set tunnel packet dscp";
          tailf:cli-full-command;
          type dscp-type;
        }
        leaf value {
          tailf:cli-drop-node-name;
          tailf:cli-full-command;
          type dscp-type;
        }
      }
      leaf fr-de {
        tailf:info
          "Set FR DE bit to 1";
        tailf:cli-full-command;
        type empty;
      }
      container ip {
        tailf:info
          "Set IP specific values";
        choice ip-choice {
          leaf dscp {
            tailf:info
              "Set IP DSCP (DiffServ CodePointint)";
            type dscp-type;
          }
          container precedence {
            tailf:info
              "Set IP precedence";
            presence "Set IP precedence";
            leaf precedence-val {
              tailf:cli-drop-node-name;
              type precedence-type;
            }
          }
        }
      }
      container mpls {
        tailf:info
          "Set MPLS specific values";
        container experimental {
          tailf:info
            "Set Experimental value";
          container imposition {
            tailf:info
              "Set Experimental value at tag imposition";
            leaf exp-value {
              tailf:cli-drop-node-name;
              type uint8 {
                tailf:info
                  "<0-7>;;Experimental value";
                range "0..7";
              }
            }
          }
          container topmost {
            tailf:info
              "Set Experimental value on topmost label";
            leaf exp-value {
              tailf:cli-drop-node-name;
              type uint8 {
                tailf:info
                  "<0-7>;;Experimental value";
                range "0..7";
              }
            }
          }
        }
      }
      container qos-group {
        tailf:info
          "Set QoS Group";
        leaf qos-group-value {
          tailf:cli-drop-node-name;
          tailf:cli-full-command;
          type uint8 {
            range "0..99";
          }
        }
      }
      container precedence {
        tailf:info
          "Set precedence in IP(v4) and IPv6 packets";
        tailf:cli-sequence-commands;
        tailf:cli-compact-syntax;
        choice precedence-choice {
          case precedence-value {
            leaf precedence-value {
              tailf:cli-drop-node-name;
              tailf:cli-no-keyword;
              type precedence-type;
            }
          }
          case precedence-from-field {
            leaf from-field {
              tailf:cli-drop-node-name;
              tailf:cli-no-keyword;
              type enumeration {
                enum "cos" {
                  tailf:info
                    "Set packet precedence from L2 COS";
                }
                enum "qos-group" {
                  tailf:info
                    "Set packet precedence from QoS Group.";
                }
              }
            }
            leaf table {
              tailf:info
                "Set packet precedence based on table map.";
              // NCS drop tailf-common:non-strict-leafref statement
              type string {
                tailf:info
                  "WORD;;table-map name";
              }
            }
          }
        }
      }
    }
    leaf service-policy {
      tailf:info
        "Configure QoS Service Policy";
      tailf:cli-remove-before-change;
      tailf:cli-full-command;
      // NCS drop tailf-common:non-strict-leafref statement
      type string {
        tailf:info
          "WORD;;policy-map name";
      }
    }
    leaf trust {
      tailf:info
        "Set trust value for the class";
      type enumeration {
        enum "cos" {
          tailf:info
            "trust value for the class";
        }
        enum "dscp" {
          tailf:info
            "trust value for the class";
        }
        enum "ip-precedence" {
          tailf:info
            "trust value for the class";
        }
      }
    }
    container distribute {
      tailf:info
        "Distribute action";
      list service-node-group {
        tailf:info
          "Distribute to service-node-group";
        tailf:cli-suppress-mode;
        tailf:cli-delete-when-empty;
        max-elements 2;
        key "name";
        leaf name {
          type string {
            tailf:info
              "WORD;;service-node-group name";
          }
        }
      }
    }
    leaf monitor-load {
      tailf:info
        "Monitor AO";
      tailf:cli-full-command;
      type enumeration {
        enum "MS-port-mapper" {
          tailf:info
            "Monitor Microsoft Endpoint Port Mapper load";
        }
        enum "cifs" {
          tailf:info
            "Monitor CIFS Accelerator load";
        }
        enum "http" {
          tailf:info
            "Monitor HTTP Accelerator load";
        }
        enum "ica" {
          tailf:info
            "Monitor ICA Accelerator load";
        }
        enum "mapi" {
          tailf:info
            "Monitor MAPI Accelerator load";
        }
        enum "nfs" {
          tailf:info
            "Monitor NFS Accelerator load";
        }
        enum "ssl" {
          tailf:info
            "Monitor SSL accelerator load";
        }
        enum "video" {
          tailf:info
            "Monitor Video Accelerator load";
        }
        enum "ice";
      }
    }
  }

  grouping ncs_rpc_notif_distribute-list-content-grouping {
    leaf access-list-name {
      tailf:cli-drop-node-name;
      tailf:cli-prefix-key;
      tailf:cli-optional-in-sequence;
      tailf:cli-disallow-value "route-map|prefix|gateway|in|out";
      type exp-ip-acl-type;
    }
    leaf prefix-list {
      tailf:info
        "Filter connections based on an IPv6 prefix-list";
      tailf:cli-prefix-key;
      tailf:cli-optional-in-sequence;
      tailf:cli-diff-dependency "/ios:ipv6/prefix-list/prefixes" {
        tailf:xpath-root 3;
      }
      type string {
        tailf:info
          "WORD;;Prefix-list name";
      }
    }
    leaf prefix {
      tailf:info
        "Filter prefixes in routing updates";
      tailf:cli-prefix-key;
      tailf:cli-optional-in-sequence;
      tailf:cli-diff-dependency "/ios:ip/prefix-list/prefixes" {
        tailf:xpath-root 3;
      }
      type string {
        tailf:info
          "WORD;;Name of an IP prefix-list";
      }
    }
    leaf gateway {
      tailf:info
        "Filtering incoming updates based on gateway";
      tailf:cli-prefix-key;
      tailf:cli-optional-in-sequence;
      tailf:cli-diff-dependency "/ios:ip/prefix-list/prefixes" {
        tailf:xpath-root 3;
      }
      type string {
        tailf:info
          "WORD;;Name of an IP prefix-list";
      }
    }
    leaf route-map {
      tailf:info
        "Filter prefixes based on the route-map";
      tailf:cli-prefix-key;
      tailf:cli-optional-in-sequence;
      type string {
        tailf:info
          "WORD;;route-map name";
      }
    }
  }

  grouping ncs_rpc_notif_redistribute-ospf-match-grouping {
    leaf match {
      tailf:info
        "Redistribution of OSPF routes";
      tailf:cli-incomplete-command;
      type empty;
    }
    leaf internal {
      when "../match" {
        tailf:xpath-root 3;
        tailf:dependency "../match";
      }
      tailf:info
        "Redistribute OSPF internal routes";
      type empty;
    }
    container external-1 {
      when "../match" {
        tailf:xpath-root 3;
        tailf:dependency "../match";
      }
      tailf:cli-drop-node-name;
      tailf:cli-flatten-container;
      leaf external {
        tailf:info
          "Redistribute OSPF external routes";
        type enumeration {
          enum "1" {
            tailf:info
              "Redistribute external type 1 routes";
          }
        }
      }
    }
    container external-2 {
      when "../match" {
        tailf:xpath-root 3;
        tailf:dependency "../match";
      }
      tailf:cli-drop-node-name;
      tailf:cli-flatten-container;
      leaf external {
        tailf:info
          "Redistribute OSPF external routes";
        type enumeration {
          enum "2" {
            tailf:info
              "Redistribute external type 2 routes";
          }
        }
      }
    }
    container nssa-external-1 {
      when "../match" {
        tailf:xpath-root 3;
        tailf:dependency "../match";
      }
      tailf:cli-drop-node-name;
      tailf:cli-flatten-container;
      leaf nssa-external {
        tailf:info
          "Redistribute OSPF NSSA external routes";
        type enumeration {
          enum "1" {
            tailf:info
              "Redistribute NSSA external type 1 routes";
          }
        }
      }
    }
    container nssa-external-2 {
      when "../match" {
        tailf:xpath-root 3;
        tailf:dependency "../match";
      }
      tailf:cli-drop-node-name;
      tailf:cli-flatten-container;
      leaf nssa-external {
        tailf:info
          "Redistribute OSPF NSSA external routes";
        type enumeration {
          enum "2" {
            tailf:info
              "Redistribute NSSA external type 2 routes";
          }
        }
      }
    }
  }

  grouping ncs_rpc_notif_router-distribute-list-grouping {
    list distribute-list {
      tailf:info
        "Filter networks in routing updates";
      tailf:cli-suppress-mode;
      tailf:cli-delete-when-empty;
      tailf:cli-compact-syntax;
      tailf:cli-sequence-commands;
      tailf:cli-remove-before-change;
      key "direction";
      leaf direction {
        tailf:cli-diff-dependency "../../distribute-list-interface/distribute-list" {
          tailf:xpath-root 3;
          tailf:cli-trigger-on-set;
        }
        type enumeration {
          enum "in" {
            tailf:info
              "Filter incoming routing updates";
          }
          enum "out" {
            tailf:info
              "Filter outgoing routing updates";
          }
        }
      }
      uses ncs_rpc_notif_distribute-list-content-grouping;
    }
    container distribute-list-interface {
      tailf:cli-drop-node-name;
      list distribute-list {
        tailf:info
          "Filter networks in routing updates";
        tailf:cli-suppress-mode;
        tailf:cli-delete-when-empty;
        tailf:cli-compact-syntax;
        tailf:cli-sequence-commands;
        tailf:cli-remove-before-change;
        key "direction interface";
        leaf direction {
          type enumeration {
            enum "in" {
              tailf:info
                "Filter incoming routing updates";
            }
            enum "out" {
              tailf:info
                "Filter outgoing routing updates";
            }
          }
        }
        leaf interface {
          tailf:cli-diff-dependency "/ios:interface" {
            tailf:xpath-root 3;
          }
          type string {
            tailf:info
              "WORD;;Interface name";
          }
        }
        uses ncs_rpc_notif_distribute-list-content-grouping;
      }
    }
  }

  grouping ncs_rpc_notif_router-offset-list-grouping {
    list offset-list {
      tailf:info
        "Add or subtract offset from metrics";
      tailf:cli-suppress-mode;
      tailf:cli-delete-when-empty;
      tailf:cli-compact-syntax;
      tailf:cli-sequence-commands;
      tailf:cli-incomplete-command;
      key "direction";
      leaf id {
        tailf:cli-drop-node-name;
        tailf:cli-prefix-key;
        type union {
          type uint32 {
            tailf:info
              "<0-99>;;Access list of networks to apply offset (0 selects all networks)";
            range "0..99";
          }
          type uint32 {
            tailf:info
              "<1300-1999>;;Access list of networks to apply offset (expanded range)";
            range "1300..1999";
          }
          type string {
            tailf:info
              "WORD;;Access-list name";
          }
        }
      }
      leaf direction {
        type enumeration {
          enum "in" {
            tailf:info
              "Perform offset on incoming updates";
          }
          enum "out" {
            tailf:info
              "Perform offset on outgoing updates";
          }
        }
      }
      leaf offset {
        tailf:cli-drop-node-name;
        type uint8 {
          tailf:info
            "<0-16>;;Offset";
          range "0..16";
        }
      }
    }
    container offset-list-interface {
      tailf:cli-drop-node-name;
      list offset-list {
        tailf:info
          "Add or subtract offset from metrics";
        tailf:cli-suppress-mode;
        tailf:cli-delete-when-empty;
        tailf:cli-compact-syntax;
        tailf:cli-sequence-commands;
        key "direction interface";
        leaf id {
          tailf:cli-drop-node-name;
          tailf:cli-prefix-key;
          type union {
            type uint32 {
              tailf:info
                "<0-99>;;Access list of networks to apply offset (0 selects all networks)";
              range "0..99";
            }
            type uint32 {
              tailf:info
                "<1300-1999>;;Access list of networks to apply offset (expanded range)";
              range "1300..1999";
            }
            type string {
              tailf:info
                "WORD;;Access-list name";
            }
          }
        }
        leaf direction {
          type enumeration {
            enum "in" {
              tailf:info
                "Perform offset on incoming updates";
            }
            enum "out" {
              tailf:info
                "Perform offset on outgoing updates";
            }
          }
        }
        leaf offset {
          tailf:cli-drop-node-name;
          tailf:cli-prefix-key {
            tailf:cli-before-key 2;
          }
          type uint32 {
            tailf:info
              "<0-2147483647>;;Offset";
          }
        }
        leaf interface {
          tailf:cli-diff-dependency "/ios:interface" {
            tailf:xpath-root 3;
          }
          type string {
            tailf:info
              "WORD;;Interface name";
          }
        }
      }
    }
  }

  grouping ncs_rpc_notif_passive-interface-grouping {
    container passive-interface {
      tailf:info
        "Suppress routing updates on an interface";
      choice passive-interface-choice {
        leaf default {
          tailf:info
            "Suppress routing updates on all interfaces";
          type empty;
        }
        list interface {
          tailf:cli-drop-node-name;
          tailf:cli-suppress-mode;
          tailf:cli-delete-when-empty;
          key "name";
          leaf name {
            tailf:cli-diff-dependency "/ios:interface" {
              tailf:xpath-root 3;
            }
            type string {
              tailf:info
                "WORD;;Interface name";
            }
          }
        }
      }
    }
    container disable {
      tailf:info
        "Use with 'disable passive-interface' for 'no passive-interface' config";
      when "../passive-interface/default" {
        tailf:xpath-root 3;
        tailf:dependency "../passive-interface/default";
      }
      tailf:cli-diff-dependency "../passive-interface/default" {
        tailf:xpath-root 3;
      }
      list passive-interface {
        tailf:cli-suppress-mode;
        tailf:cli-delete-when-empty;
        tailf:cli-compact-syntax;
        key "interface";
        leaf interface {
          tailf:cli-multi-word-key;
          tailf:cli-diff-dependency "/ios:interface" {
            tailf:xpath-root 3;
          }
          type string {
            tailf:info
              "WORD;;Interface name";
          }
        }
      }
    }
  }

  grouping ncs_rpc_notif_ip-community-list-grouping {
    list entry {
      tailf:cli-drop-node-name;
      tailf:cli-suppress-mode;
      tailf:cli-delete-when-empty;
      tailf:cli-compact-syntax;
      tailf:cli-show-long-obu-diffs;
      ordered-by user;
      key "expr";
      leaf expr {
        tailf:cli-multi-word-key {
          tailf:cli-max-words 11;
        }
        type string {
          tailf:info
            "<RULE>;;deny <options> | permit <options>";
          pattern '(permit.*)|(deny.*)';
        }
      }
    }
  }

  grouping ncs_rpc_notif_ip-extcommunity-list-grouping {
    list entry {
      tailf:cli-drop-node-name;
      tailf:cli-suppress-mode;
      tailf:cli-delete-when-empty;
      tailf:cli-compact-syntax;
      tailf:cli-show-long-obu-diffs;
      ordered-by user;
      key "expr";
      leaf expr {
        tailf:cli-multi-word-key;
        type string {
          tailf:info
            "<RULE>;;deny <LINE> | permit <LINE>";
          pattern '(permit.*)|(deny.*)';
        }
      }
    }
  }

  grouping ncs_rpc_notif_ip-route-options-grouping {
    leaf dhcp {
      tailf:info
        "Default Gateway obtained from DHCP";
      tailf:cli-optional-in-sequence;
      tailf:cli-case-insensitive;
      type empty;
    }
    leaf metric {
      tailf:cli-drop-node-name;
      tailf:cli-break-sequence-commands;
      type uint8 {
        tailf:info
          "<1-255>;;Distance metric for this route";
        range "1..255";
      }
    }
    leaf global {
      tailf:info
        "Next hop address is global";
      type empty;
    }
    leaf name {
      tailf:info
        "Specify name of the next hop";
      type string {
        tailf:info
          "WORD;;Name of the next hop";
      }
    }
    leaf permanent {
      tailf:info
        "permanent route";
      type empty;
    }
    leaf multicast {
      tailf:info
        "multicast route";
      type empty;
    }
    leaf tag {
      tailf:info
        "Set tag for this route";
      type uint32 {
        tailf:info
          "<1-4294967295>;;Tag value";
        range "1..4294967295";
      }
    }
    leaf track {
      tailf:info
        "Install route depending on tracked item";
      type uint16 {
        tailf:info
          "<1-1000>;;tracked object number";
        range "1..1000";
      }
    }
  }

  grouping ncs_rpc_notif_ip-route-grouping {
    list ip-route-interface-forwarding-list {
      tailf:cli-drop-node-name;
      tailf:cli-suppress-mode;
      tailf:cli-delete-when-empty;
      tailf:cli-compact-syntax;
      tailf:cli-sequence-commands;
      tailf:cli-reset-container;
      key "prefix mask interface forwarding-address";
      leaf prefix {
        tailf:cli-disallow-value "vrf";
        type inet:ipv4-address {
          tailf:info
            "A.B.C.D;;Destination prefix";
        }
      }
      leaf mask {
        type inet:ipv4-address {
          tailf:info
            "A.B.C.D;;Destination prefix mask";
        }
      }
      leaf interface {
        type string {
          tailf:info
            "WORD;;Interface name";
        }
      }
      leaf forwarding-address {
        type union {
          type inet:ipv4-address {
            tailf:info
              "A.B.C.D;;Forwarding router's address";
          }
          type enumeration {
            enum "multicast" {
              tailf:info
                "multicast route";
            }
          }
        }
      }
      uses ncs_rpc_notif_ip-route-options-grouping;
    }
    list ip-route-forwarding-list {
      tailf:cli-drop-node-name;
      tailf:cli-suppress-mode;
      tailf:cli-delete-when-empty;
      tailf:cli-compact-syntax;
      tailf:cli-sequence-commands;
      tailf:cli-reset-container;
      key "prefix mask forwarding-address";
      leaf prefix {
        tailf:cli-disallow-value "vrf";
        type inet:ipv4-address {
          tailf:info
            "A.B.C.D;;Destination prefix";
        }
      }
      leaf mask {
        type inet:ipv4-address {
          tailf:info
            "A.B.C.D;;Destination prefix mask";
        }
      }
      leaf forwarding-address {
        type inet:ipv4-address {
          tailf:info
            "A.B.C.D;;Forwarding router's address";
        }
      }
      uses ncs_rpc_notif_ip-route-options-grouping;
    }
    list ip-route-interface-list {
      tailf:cli-drop-node-name;
      tailf:cli-suppress-mode;
      tailf:cli-delete-when-empty;
      tailf:cli-compact-syntax;
      tailf:cli-sequence-commands;
      tailf:cli-reset-container;
      key "prefix mask interface";
      leaf prefix {
        tailf:cli-disallow-value "vrf";
        type inet:ipv4-address {
          tailf:info
            "A.B.C.D;;Destination prefix";
        }
      }
      leaf mask {
        type inet:ipv4-address {
          tailf:info
            "A.B.C.D;;Destination prefix mask";
        }
      }
      leaf interface {
        tailf:cli-disallow-value "metric|global|name|permanent|multicast|tag|track";
        type union {
          type string {
            tailf:info
              "WORD;;Interface name";
          }
          type enumeration {
            enum "dhcp" {
              tailf:info
                "Default Gateway obtained from DHCP";
            }
          }
        }
      }
      uses ncs_rpc_notif_ip-route-options-grouping;
    }
  }

  grouping ncs_rpc_notif_ipv6-route-options-grouping {
    leaf distance {
      tailf:cli-drop-node-name;
      tailf:cli-break-sequence-commands;
      type uint8 {
        tailf:info
          "<1-254>;;Administrative distance";
        range "1..254";
      }
    }
    choice type-choice {
      leaf multicast {
        tailf:info
          "Route only usable by multicast";
        tailf:cli-full-command;
        type empty;
      }
      leaf unicast {
        tailf:info
          "Route only usable by unicast";
        type empty;
      }
    }
    leaf tag {
      tailf:info
        "Tag value";
      tailf:cli-full-command;
      type uint32 {
        tailf:info
          "<0-4294967295>;;Tag value";
      }
    }
  }

  grouping ncs_rpc_notif_ipv6-route-grouping {
    list ipv6-route-interface-destination-list {
      tailf:cli-drop-node-name;
      tailf:cli-suppress-mode;
      tailf:cli-delete-when-empty;
      tailf:cli-compact-syntax;
      tailf:cli-sequence-commands {
        tailf:cli-reset-all-siblings;
      }
      key "prefix interface destination";
      leaf prefix {
        tailf:cli-disallow-value "vrf";
        type ipv6-prefix {
          tailf:info
            "X:X:X:X::X/<0-128>;;IPv6 prefix x:x::y/<z>";
        }
      }
      leaf interface {
        tailf:cli-diff-dependency "../../../../../interface" {
          tailf:xpath-root 3;
        }
        type string {
          tailf:info
            "WORD;;Interface name";
        }
      }
      leaf destination {
        type inet:ipv6-address {
          tailf:info
            "X:X:X:X::X;;IPv6 address of next-hop";
        }
      }
      uses ncs_rpc_notif_ipv6-route-options-grouping;
    }
    list ipv6-route-destination-list {
      tailf:cli-drop-node-name;
      tailf:cli-suppress-mode;
      tailf:cli-delete-when-empty;
      tailf:cli-compact-syntax;
      tailf:cli-sequence-commands {
        tailf:cli-reset-all-siblings;
      }
      key "prefix destination";
      leaf prefix {
        tailf:cli-disallow-value "vrf";
        type ipv6-prefix {
          tailf:info
            "X:X:X:X::X/<0-128>;;IPv6 prefix x:x::y/<z>";
        }
      }
      leaf destination {
        type inet:ipv6-address {
          tailf:info
            "X:X:X:X::X;;IPv6 address of next-hop";
        }
      }
      uses ncs_rpc_notif_ipv6-route-options-grouping;
    }
    list ipv6-route-interface-list {
      tailf:cli-drop-node-name;
      tailf:cli-suppress-mode;
      tailf:cli-delete-when-empty;
      tailf:cli-compact-syntax;
      tailf:cli-sequence-commands {
        tailf:cli-reset-all-siblings;
      }
      key "prefix interface";
      leaf prefix {
        tailf:cli-disallow-value "vrf";
        type ipv6-prefix {
          tailf:info
            "X:X:X:X::X/<0-128>;;IPv6 prefix x:x::y/<z>";
        }
      }
      leaf interface {
        tailf:cli-diff-dependency "../../../../../interface" {
          tailf:xpath-root 3;
        }
        type string {
          tailf:info
            "WORD;;Interface name";
        }
      }
      uses ncs_rpc_notif_ipv6-route-options-grouping;
    }
  }

  grouping ncs_rpc_notif_random-detect-grouping {
    leaf min-threshold {
      tailf:cli-drop-node-name;
      tailf:cli-incomplete-command;
      type uint32 {
        tailf:info
          "<1-262143>;;minimum threshold (in packet by default)";
      }
    }
    leaf min-threshold-unit {
      tailf:cli-drop-node-name;
      tailf:cli-optional-in-sequence;
      type enumeration {
        enum "bytes" {
          tailf:info
            "number of bytes";
        }
        enum "ms" {
          tailf:info
            "milliseconds";
        }
        enum "us" {
          tailf:info
            "microseconds";
        }
      }
    }
    leaf max-threshold {
      tailf:cli-drop-node-name;
      type uint32 {
        tailf:info
          "<1-262143>;;maximum threshold (number of packets)";
      }
    }
    leaf max-threshold-unit {
      tailf:cli-drop-node-name;
      tailf:cli-optional-in-sequence;
      type enumeration {
        enum "bytes" {
          tailf:info
            "number of bytes";
        }
        enum "ms" {
          tailf:info
            "milliseconds";
        }
        enum "us" {
          tailf:info
            "microseconds";
        }
      }
    }
    leaf denominator {
      tailf:cli-drop-node-name;
      type uint32 {
        tailf:info
          "<1-65535>;;mark probability denominator";
      }
    }
  }

  grouping ncs_rpc_notif_random-detect-values-grouping {
    leaf minimum-thresh {
      tailf:info
        "minimum threshold for red aggregate";
      tailf:cli-incomplete-command;
      type uint32 {
        tailf:info
          "<1-512000000>;;minimum threshold (number of packets)";
      }
    }
    leaf maximum-thresh {
      tailf:info
        "maximum threshold for red aggregate";
      type uint32 {
        tailf:info
          "<1-512000000>;;maximum threshold (number of packets)";
      }
    }
    leaf mark-prob {
      tailf:info
        "mark-probability for red aggregate";
      type uint32 {
        tailf:info
          "<0-65535>;;mark probability denominator";
        range "0..65535";
      }
    }
  }

  grouping ncs_rpc_notif_class-map-match-grouping {
    container access-group {
      tailf:info
        "Access group";
      leaf-list index {
        tailf:cli-drop-node-name;
        tailf:cli-list-syntax;
        type uint32 {
          tailf:info
            "<1-2799>;;Access list index";
          range "1..2799";
        }
      }
      leaf-list name {
        tailf:info
          "Named Access List";
        tailf:cli-list-syntax;
        type string {
          tailf:info
            "WORD;;Access List name";
        }
      }
    }
    leaf any {
      tailf:info
        "Any packets";
      type empty;
    }
    leaf-list class-map {
      tailf:info
        "Class map";
      tailf:cli-list-syntax;
      // NCS drop tailf-common:non-strict-leafref statement
      type string {
        tailf:info
          "WORD;;Match class-map name";
      }
    }
    leaf-list cos {
      tailf:info
        "IEEE 802.1Q/ISL class of service/user priority values";
      tailf:cli-flat-list-syntax;
      tailf:cli-disallow-value "inner";
      max-elements 8;
      type uint16 {
        tailf:info
          "<0-7>;;Enter up to 8 class-of-service values separated by white-spaces";
        range "0..7";
      }
    }
    container cos-inner {
      tailf:cli-drop-node-name;
      container cos {
        tailf:info
          "IEEE 802.1Q/ISL class of service/user priority values";
        leaf-list inner {
          tailf:info
            "ATM VC configured as Access VC class of service/user priority values";
          tailf:cli-flat-list-syntax;
          max-elements 8;
          type uint16 {
            tailf:info
              "<0-7>;;Enter up to 8 class-of-service values separated by white-spaces";
            range "0..7";
          }
        }
      }
    }
    container destination-address {
      tailf:info
        "Destination address";
      leaf-list mac {
        tailf:info
          "MAC address";
        tailf:cli-list-syntax;
        type string {
          tailf:info
            "H.H.H;;MAC address";
        }
      }
    }
    leaf-list discard-class {
      tailf:info
        "Discard behavior identifier";
      tailf:cli-list-syntax;
      type uint8 {
        tailf:info
          "<0-7>;;Discard Class value";
        range "0..7";
      }
    }
    leaf-list dscp {
      tailf:info
        "Match DSCP in IP(v4) and IPv6 packets";
      tailf:cli-flat-list-syntax;
      tailf:cli-full-command;
      tailf:meta-data "max-values" {
        tailf:meta-value "2 :: 8";
      }
      type dscp-type;
    }
    leaf fr-de {
      tailf:info
        "Match on Frame-relay DE bit";
      type empty;
    }
    leaf-list fr-dlci {
      tailf:info
        "Match on fr-dlci";
      tailf:cli-list-syntax;
      type uint16 {
        tailf:info
          "<16-1007>;;frame-relay dlci number";
        range "16..1007";
      }
    }
    leaf-list input-interface {
      tailf:info
        "Select an input interface to match";
      tailf:cli-list-syntax;
      type string {
        tailf:info
          "WORD;;Interface name";
      }
    }
    container ip {
      tailf:info
        "IP specific values";
      leaf-list dscp {
        tailf:info
          "Match IP DSCP (DiffServ CodePoints)";
        tailf:cli-flat-list-syntax;
        type dscp-type;
      }
      leaf-list precedence {
        tailf:info
          "Match IP precedence";
        tailf:cli-flat-list-syntax;
        type precedence-type;
      }
      list rtp {
        tailf:info
          "Match RTP port nos";
        tailf:cli-suppress-mode;
        tailf:cli-delete-when-empty;
        key "port1 port2";
        leaf port1 {
          type uint16 {
            tailf:info
              "<2000-65535>;;Lower bound of UDP destination port";
            range "2000..65535";
          }
        }
        leaf port2 {
          type uint16 {
            tailf:info
              "<0-16383>;;Range of UDP ports";
            range "0..16383";
          }
        }
      }
    }
    container mpls {
      tailf:info
        "Multi Protocol Label Switching specific values";
      container experimental {
        tailf:info
          "Match MPLS experimental";
        leaf-list topmost {
          tailf:info
            "Match MPLS experimental value on topmost label";
          tailf:cli-flat-list-syntax;
          type uint16 {
            tailf:info
              "<0-7>;;Enter up to 8 experimental values separated by white-spaces";
            range "0..7";
          }
        }
      }
    }
    leaf-list precedence {
      tailf:info
        "Match Precedence in IP(v4) and IPv6 packets";
      tailf:cli-flat-list-syntax;
      type precedence-type;
    }
    container protocol {
      tailf:info
        "Protocol";
      container attribute {
        tailf:info
          "Attribute based protocol match";
        list category {
          tailf:info
            "Category attribute";
          tailf:cli-suppress-mode;
          tailf:cli-delete-when-empty;
          key "category-type";
          leaf category-type {
            type enumeration {
              enum "voice-and-video" {
                tailf:info
                  "Filter incoming connections";
              }
              enum "database" {
                tailf:info
                  "Filter outgoing connections";
              }
              enum "email" {
                tailf:info
                  "Email related applications";
              }
              enum "browsing" {
                tailf:info
                  "Browsing related applications";
              }
              enum "trojan" {
                tailf:info
                  "Trojan related applications";
              }
              enum "gaming" {
                tailf:info
                  "Gaming related applications";
              }
              enum "anonymizers" {
                tailf:info
                  "Anonymizers applications";
              }
              enum "backup-and-storage" {
                tailf:info
                  "Backup and storage related applications";
              }
              enum "business-and-productivity-tools" {
                tailf:info
                  "Business-and-productivity-tools related applications";
              }
              enum "epayement" {
                tailf:info
                  "Epayement related applications";
              }
              enum "file-sharing" {
                tailf:info
                  "File-sharing related applications";
              }
              enum "industrial-protocols" {
                tailf:info
                  "Industrial-protocols related applications";
              }
              enum "instant-messaging" {
                tailf:info
                  "Instant-messaging related applications";
              }
              enum "inter-process-rpc" {
                tailf:info
                  "Inter-process-rpc related applications";
              }
              enum "internet-security" {
                tailf:info
                  "Internet security related applications";
              }
              enum "layer3-over-ip" {
                tailf:info
                  "Layer3-over-IP related applications";
              }
              enum "location-based-services" {
                tailf:info
                  "Location-based-services related applications";
              }
              enum "net-admin" {
                tailf:info
                  "Net-admin related applications";
              }
              enum "newsgroup" {
                tailf:info
                  "Newsgroup related applications";
              }
              enum "other" {
                tailf:info
                  "Other related applications";
              }
              enum "social-networking" {
                tailf:info
                  "Social-networking related applications";
              }
              enum "software-updates" {
                tailf:info
                  "Software updates and downloads related applications";
              }
            }
          }
        }
        list traffic-class {
          tailf:info
            "traffic-class attribute";
          tailf:cli-suppress-mode;
          tailf:cli-delete-when-empty;
          key "traffic-class-type";
          leaf traffic-class-type {
            type enumeration {
              enum "broadcast-video" {
                tailf:info
                  "Broadcast TV, live events, video surveillance";
              }
              enum "bulk-data" {
                tailf:info
                  "Non-interactive data applications";
              }
              enum "multimedia-conferencing" {
                tailf:info
                  "Desktop software multimedia collaboration applications";
              }
              enum "multimedia-streaming" {
                tailf:info
                  "Video-on-Demand (VoD) streaming video";
              }
              enum "network-control" {
                tailf:info
                  "Network control plane traffic";
              }
              enum "ops-admin-mgmt" {
                tailf:info
                  "Network operations, administration, and management";
              }
              enum "real-time-interactive" {
                tailf:info
                  "High-definition interactive video applications";
              }
              enum "signaling" {
                tailf:info
                  "Signaling traffic that supports IP voice and video telephony";
              }
              enum "transactional-data" {
                tailf:info
                  "Interactive data applications";
              }
              enum "voip-telephony" {
                tailf:info
                  "VoIP telephony (bearer-only) traffic";
              }
            }
          }
        }
        list business-relevance {
          tailf:info
            "business-relevance attribute";
          tailf:cli-suppress-mode;
          tailf:cli-delete-when-empty;
          key "business-relevance-type";
          leaf business-relevance-type {
            type enumeration {
              enum "business-irrelevant" {
                tailf:info
                  "Undesirable business traffic";
              }
              enum "business-relevant" {
                tailf:info
                  "Business critical applications";
              }
              enum "default" {
                tailf:info
                  "Related business applications";
              }
            }
          }
        }
      }
      list protocol-list {
        tailf:cli-drop-node-name;
        tailf:cli-suppress-mode;
        tailf:cli-delete-when-empty;
        key "name";
        leaf name {
          tailf:cli-disallow-value "attribute";
          type string {
            tailf:info
              "WORD;;protocol";
          }
        }
        list values {
          tailf:cli-drop-node-name;
          tailf:cli-suppress-mode;
          tailf:cli-delete-when-empty;
          tailf:cli-show-long-obu-diffs;
          ordered-by user;
          key "value";
          leaf value {
            tailf:cli-multi-word-key;
            type string;
          }
        }
      }
    }
    container packet {
      tailf:info
        "Layer 3 Packet length";
      list length {
        tailf:info
          "Layer 3 Packet length";
        tailf:cli-suppress-mode;
        tailf:cli-delete-when-empty;
        tailf:cli-show-long-obu-diffs;
        ordered-by user;
        key "line";
        leaf line {
          tailf:cli-multi-word-key;
          type string {
            tailf:info
              "LINE;;min X | max X | min X max Y";
            pattern '(min \d+)|(max \d+)|(min \d+ max \d+)';
          }
        }
      }
    }
    leaf-list qos-group {
      tailf:info
        "Qos-group";
      tailf:cli-list-syntax;
      type uint16 {
        tailf:info
          "<0-99>;;Qos Group value";
        range "0..99";
      }
    }
    container source-address {
      tailf:info
        "Source address";
      leaf-list mac {
        tailf:info
          "MAC address";
        tailf:cli-list-syntax;
        type string {
          tailf:info
            "H.H.H;;MAC address";
        }
      }
    }
    leaf-list vlan {
      tailf:info
        "VLANs to match";
      tailf:cli-range-list-syntax;
      type uint16 {
        tailf:info
          "<1-4094>;;VLAN id";
        range "1..4094";
      }
    }
    container service {
      tailf:info
        "Service Instance to match";
      container instance {
        tailf:info
          "Service Instance to match";
        leaf-list ethernet {
          tailf:info
            "Service Instance to match";
          tailf:cli-list-syntax;
          type uint32 {
            tailf:info
              "<1-4294967295>;;Service Instance Identifier";
          }
        }
      }
    }
  }

  grouping ncs_rpc_notif_ip-name-server-grouping {
    list name-server-list {
      tailf:cli-drop-node-name;
      tailf:cli-suppress-mode;
      tailf:cli-delete-when-empty;
      tailf:cli-show-long-obu-diffs;
      ordered-by user;
      max-elements 6;
      key "address";
      leaf address {
        type union {
          type inet:ipv4-address {
            tailf:info
              "A.B.C.D;;Domain server IP address (maximum of 6)";
          }
          type inet:ipv6-address {
            tailf:info
              "X:X:X:X::X;;Domain server IPv6 address (maximum of 6)";
          }
        }
      }
    }
  }

  grouping ncs_rpc_notif_ip-host-grouping {
    list host-list {
      tailf:cli-drop-node-name;
      tailf:cli-suppress-mode;
      tailf:cli-delete-when-empty;
      tailf:cli-compact-syntax;
      tailf:cli-sequence-commands;
      tailf:cli-incomplete-command;
      key "hostname";
      leaf hostname {
        tailf:cli-disallow-value "vrf";
        type string {
          tailf:info
            "WORD;;Name of host";
        }
      }
      leaf tcp-port-number {
        tailf:cli-drop-node-name;
        tailf:cli-optional-in-sequence;
        tailf:cli-incomplete-command;
        type uint16 {
          tailf:info
            "<0-65535>;;Default telnet port number";
        }
      }
      leaf-list ip-address1 {
        tailf:cli-drop-node-name;
        tailf:cli-flat-list-syntax;
        tailf:cli-replace-all;
        type inet:ipv4-address {
          tailf:info
            "A.B.C.D;;Host IP address";
        }
      }
    }
  }

  grouping ncs_rpc_notif_ip-dhcp-excluded-address-grouping {
    list low-list {
      tailf:cli-drop-node-name;
      tailf:cli-suppress-mode;
      tailf:cli-delete-when-empty;
      key "low";
      leaf low {
        tailf:cli-disallow-value "vrf";
        type inet:ipv4-address {
          tailf:info
            "A.B.C.D;;Low IP address";
        }
      }
    }
    list low-high-list {
      tailf:cli-drop-node-name;
      tailf:cli-suppress-mode;
      tailf:cli-delete-when-empty;
      key "low high";
      leaf low {
        tailf:cli-disallow-value "vrf";
        type inet:ipv4-address {
          tailf:info
            "A.B.C.D;;Low IP address";
        }
      }
      leaf high {
        tailf:cli-disallow-value "vrf";
        type inet:ipv4-address {
          tailf:info
            "A.B.C.D;;High IP address";
        }
      }
    }
  }

  grouping ncs_rpc_notif_ntp-peer-grouping {
    list peer-list {
      tailf:cli-drop-node-name;
      tailf:cli-suppress-mode;
      tailf:cli-delete-when-empty;
      tailf:cli-compact-syntax;
      tailf:cli-reset-container;
      key "name";
      leaf name {
        tailf:cli-disallow-value "vrf";
        type inet:host {
          tailf:info
            "Hostname, A.B.C.D or X:X:X:X::X;;Address of peer";
        }
      }
      leaf burst {
        tailf:info
          "Send a burst when peer is reachable (Default)";
        type empty;
      }
      leaf iburst {
        tailf:info
          "Send a burst when peer is unreachable (Default)";
        type empty;
      }
      leaf key {
        tailf:info
          "Configure peer authentication key";
        type uint32 {
          tailf:info
            "<1-4294967295>;;Peer key number";
          range "1..4294967295";
        }
      }
      leaf maxpoll {
        tailf:info
          "Maximum poll interval";
        type uint8 {
          tailf:info
            "<4-17>;;Poll value in Log2";
          range "4..17";
        }
      }
      leaf minpoll {
        tailf:info
          "Minimum poll interval";
        type uint8 {
          tailf:info
            "<4-17>;;Poll value in Log2";
          range "4..17";
        }
      }
      leaf normal-sync {
        tailf:info
          "Disable rapid sync at startup";
        type empty;
      }
      leaf prefer {
        tailf:info
          "Prefer this peer when possible";
        type empty;
      }
      container source {
        tailf:info
          "Interface for source address";
        tailf:cli-flatten-container;
        tailf:cli-compact-syntax;
        uses ncs_rpc_notif_interface-name-grouping;
      }
      leaf version {
        tailf:info
          "Configure NTP version";
        type uint8 {
          tailf:info
            "<1-4>;;NTP version number";
        }
      }
    }
  }

  grouping ncs_rpc_notif_sntp-server-grouping {
    list server-list {
      tailf:cli-drop-node-name;
      tailf:cli-suppress-mode;
      tailf:cli-delete-when-empty;
      tailf:cli-compact-syntax;
      tailf:cli-reset-container;
      key "name";
      leaf name {
        tailf:cli-disallow-value "vrf";
        type inet:host {
          tailf:info
            "Hostname, A.B.C.D or X:X:X:X::X;;Address of peer";
        }
      }
      leaf key {
        tailf:info
          "Configure server authentication key";
        type uint32 {
          tailf:info
            "<1-4294967295>;;Server key number";
          range "1..4294967295";
        }
      }
      leaf version {
        tailf:info
          "Configure NTP version";
        type uint8 {
          tailf:info
            "<1-4>;;NTP version number";
        }
      }
    }
  }

  grouping ncs_rpc_notif_line-grouping {
    leaf location {
      tailf:info
        "Enter terminal location description";
      tailf:cli-multi-value;
      tailf:cli-preformatted;
      tailf:cli-full-command;
      type string {
        tailf:info
          "LINE;;One text line describing the terminal's location";
      }
    }
    leaf absolute-timeout {
      tailf:info
        "Set absolute timeout for line disconnection";
      tailf:cli-full-command;
      type uint32 {
        tailf:info
          "<0-10000>;;Absolute timeout interval in minutes";
      }
    }
    container access-class {
      tailf:info
        "Filter connections based on an IP access list";
      tailf:cli-flatten-container;
      tailf:cli-compact-syntax;
      tailf:cli-sequence-commands {
        tailf:cli-reset-siblings;
      }
      list access-list {
        tailf:cli-drop-node-name;
        tailf:cli-suppress-mode;
        tailf:cli-delete-when-empty;
        tailf:cli-compact-syntax;
        tailf:cli-sequence-commands {
          tailf:cli-reset-siblings;
        }
        key "direction";
        leaf direction {
          type enumeration {
            enum "in" {
              tailf:info
                "Filter incoming connections";
            }
            enum "out" {
              tailf:info
                "Filter outgoing connections";
            }
          }
        }
        leaf access-list {
          tailf:cli-drop-node-name;
          tailf:cli-prefix-key;
          type exp-ip-acl-type;
        }
        leaf vrf-also {
          tailf:info
            "Same access list is applied for all VRFs";
          type empty;
        }
      }
    }
    leaf flush-at-activation {
      tailf:info
        "Clear input stream at activation";
      tailf:cli-boolean-no;
      tailf:cli-full-command;
      type boolean;
      default "true";
    }
    container activation-character-choice {
      tailf:cli-drop-node-name;
      choice activation-character-choice {
        leaf activation-character {
          tailf:info
            "Define the activation character";
          tailf:cli-boolean-no;
          type boolean;
          default "true";
        }
        container activation-character-conf {
          tailf:cli-drop-node-name;
          tailf:cli-incomplete-command;
          tailf:cli-incomplete-no;
          leaf activation-character {
            type string {
              tailf:info
                "CHAR or <0-127>;;Activation character or its decimal equivalent";
            }
          }
        }
      }
    }
    leaf escape-character {
      tailf:info
        "Change the current line's escape character";
      type union {
        type uint8 {
          tailf:info
            "ASCII decimal equivalent";
        }
        type enumeration {
          enum "BREAK" {
            tailf:info
              "Cause escape on BREAK";
          }
          enum "DEFAULT" {
            tailf:info
              "Use default escape character";
          }
          enum "NONE" {
            tailf:info
              "Disable escape entirely";
          }
        }
      }
    }
    container script {
      tailf:info
        "specify event related chat scripts to run on the line";
      leaf dialer {
        tailf:info
          "chat script to run whenever dialer makes an outgoing call";
        // NCS drop tailf-common:non-strict-leafref statement
        type string {
          tailf:info
            "WORD;;chat script name";
        }
      }
    }
    container modem {
      tailf:info
        "Configure the Modem Control Lines";
      leaf enable {
        tailf:info
          "Console port is used for connecting modem";
        tailf:cli-boolean-no;
        type boolean;
      }
      leaf InOut {
        tailf:info
          "Configure line for incoming AND outgoing use of modem";
        type empty;
      }
      container autoconfigure {
        tailf:info
          "Automatically configure modem on line";
        leaf discovery {
          tailf:info
            "Attempt to determine modem type automatically";
          type empty;
        }
        leaf type {
          tailf:info
            "Specify modem type";
          type string {
            tailf:info
              "WORD;;Modem type";
          }
        }
      }
    }
    container exec-choice {
      tailf:cli-drop-node-name;
      choice exec-choice {
        default "exec";
        leaf exec {
          tailf:info
            "Configure EXEC";
          tailf:cli-boolean-no;
          type boolean;
          default "true";
        }
        container exec-conf {
          tailf:cli-drop-node-name;
          tailf:cli-incomplete-command;
          tailf:cli-incomplete-no;
          container exec {
            tailf:cli-incomplete-command;
            tailf:cli-incomplete-no;
            container prompt {
              tailf:info
                "EXEC prompt";
              leaf timestamp {
                tailf:info
                  "Print timestamps for show commands";
                type empty;
              }
            }
          }
        }
      }
    }
    container exec-timeout {
      tailf:info
        "Set the EXEC timeout";
      tailf:cli-compact-syntax;
      tailf:cli-sequence-commands;
      leaf minutes {
        tailf:cli-drop-node-name;
        type uint32 {
          tailf:info
            "<0-35791>;;Timeout in minutes";
        }
      }
      leaf seconds {
        tailf:cli-drop-node-name;
        type uint32 {
          tailf:info
            "<0-2147483>;;Timeout in seconds";
        }
      }
    }
    container timeout {
      tailf:info
        "Timeouts for the line";
      container login {
        tailf:info
          "Timeouts related to the login sequence";
        leaf response {
          tailf:info
            "Timeout for any user input during login sequences";
          type uint16 {
            tailf:info
              "<1-300>;;Timeout in seconds";
            range "1..300";
          }
        }
      }
    }
    container session-disconnect-warning {
      tailf:info
        "Set warning countdown for session-timeout";
      tailf:cli-compact-syntax;
      tailf:cli-sequence-commands {
        tailf:cli-reset-siblings;
      }
      leaf seconds {
        tailf:cli-drop-node-name;
        type uint32 {
          tailf:info
            "<0-4294967295>;;Session timeout warning in seconds";
        }
      }
      leaf message {
        tailf:info
          "Optional warning message";
        tailf:cli-multi-value;
        type string {
          tailf:info
            "LINE;;One text line optional warning message";
        }
      }
    }
    container logging {
      tailf:info
        "Modify message logging facilities";
      container synchronous {
        tailf:info
          "Synchronized message output";
        tailf:cli-delete-when-empty;
        presence "true";
        leaf level {
          tailf:info
            "Severity level to output asynchronously";
          type union {
            type uint8 {
              tailf:info
                "<0-7>;;Severity level; lower number for higher severity";
              range "0..7";
            }
            type enumeration {
              enum "all" {
                tailf:info
                  "Turn off all severity level for asynchronous output";
              }
            }
          }
        }
      }
    }
    leaf rotary {
      tailf:info
        "Add line to a rotary group";
      type uint8 {
        tailf:info
          "<0-100>;;Rotary group to add line to";
        range "0..100";
      }
    }
    container login {
      tailf:info
        "Enable password checking";
      tailf:cli-delete-when-empty;
      presence "true";
      leaf local {
        tailf:info
          "Local password checking";
        type empty;
      }
    }
    container local-authentication {
      tailf:cli-drop-node-name;
      container login {
        tailf:info
          "Enable password checking";
        tailf:cli-incomplete-command;
        tailf:cli-incomplete-no;
        leaf tacacs {
          type empty;
        }
        leaf authentication {
          tailf:info
            "Authentication parameters.";
          type union {
            type string {
              tailf:info
                "WORD;;Use an authentication list with this name.";
            }
            type enumeration {
              enum "default" {
                tailf:info
                  "Use the default authentication list.";
              }
            }
          }
          default "default";
        }
      }
    }
    container autocommand {
      tailf:info
        "Automatically execute an EXEC command";
      leaf command {
        tailf:cli-drop-node-name;
        tailf:cli-multi-value;
        type string {
          tailf:info
            "LINE;;Appropriate EXEC command";
        }
      }
    }
    container accounting {
      tailf:info
        "Accounting parameters";
      leaf exec {
        tailf:info
          "For starting an exec (shell)";
        type union {
          type string {
            tailf:info
              "WORD;;Use an accounting list with this name";
          }
          type enumeration {
            enum "default" {
              tailf:info
                "Use the default accounting list.";
            }
          }
        }
        default "default";
      }
      list commands {
        tailf:info
          "For exec (shell) commands.";
        tailf:cli-suppress-mode;
        tailf:cli-delete-when-empty;
        tailf:cli-compact-syntax;
        tailf:cli-incomplete-command;
        key "level";
        leaf level {
          type uint8 {
            tailf:info
              "<0-15>;;Enable level";
            range "0..15";
          }
        }
        leaf name {
          tailf:cli-drop-node-name;
          type union {
            type string {
              tailf:info
                "WORD;;Use an accounting list with this name";
            }
            type enumeration {
              enum "default" {
                tailf:info
                  "Use the default accounting list";
              }
            }
          }
          default "default";
        }
      }
    }
    leaf logout-warning {
      tailf:info
        "Set Warning countdown for absolute timeout of line";
      tailf:cli-full-command;
      type uint32 {
        tailf:info
          "<0-4294967295>;;Warning time in seconds";
      }
    }
    container ipv6 {
      tailf:info
        "IPv6 options";
      list access-class {
        tailf:info
          "Filter connections based on an IPv6 access list";
        tailf:cli-suppress-mode;
        tailf:cli-delete-when-empty;
        tailf:cli-compact-syntax;
        tailf:cli-sequence-commands;
        key "direction";
        leaf direction {
          type enumeration {
            enum "in" {
              tailf:info
                "Filter incoming connections";
            }
            enum "out" {
              tailf:info
                "Filter outgoing connections";
            }
          }
        }
        leaf access-list {
          tailf:cli-drop-node-name;
          tailf:cli-prefix-key;
          type exp-ip-acl-type;
        }
      }
    }
    container authorization {
      tailf:info
        "Authorization parameters";
      leaf exec {
        tailf:info
          "For starting an exec (shell)";
        type union {
          type enumeration {
            enum "default" {
              tailf:info
                "Use the default authorization list";
            }
          }
          type string {
            tailf:info
              "WORD;;Use an authorization list with this name";
          }
        }
        default "default";
      }
      list commands {
        tailf:info
          "For exec (shell) commands.";
        tailf:cli-suppress-mode;
        tailf:cli-delete-when-empty;
        tailf:cli-compact-syntax;
        tailf:cli-incomplete-command;
        key "level";
        leaf level {
          type uint8 {
            tailf:info
              "<0-15>;;Enable level";
            range "0..15";
          }
        }
        leaf name {
          tailf:cli-drop-node-name;
          type union {
            type string {
              tailf:info
                "WORD;;Use an authorization list with this name";
            }
            type enumeration {
              enum "default" {
                tailf:info
                  "Use the default authorization list";
              }
            }
          }
          default "default";
        }
      }
    }
    container history {
      tailf:info
        "Enable and control the command history function";
      leaf size {
        tailf:info
          "Set history buffer size";
        type uint16 {
          tailf:info
            "<0-256>;;Size of history buffer";
          range "0..256";
        }
      }
    }
    leaf full-help {
      tailf:info
        "Provide help to unprivileged user";
      type empty;
    }
    container password {
      tailf:info
        "Set a password";
      tailf:cli-compact-syntax;
      tailf:cli-sequence-commands;
      uses ncs_rpc_notif_password-grouping;
    }
    container privilege {
      tailf:info
        "Change privilege level for line";
      leaf level {
        tailf:info
          "Assign default privilege level for line";
        type uint8 {
          tailf:info
            "<0-15>;;Default privilege level for line";
          range "0..15";
        }
      }
    }
    container session-timeout {
      tailf:info
        "Set interval for closing connection when there is no input traffic";
      tailf:cli-sequence-commands;
      tailf:cli-compact-syntax;
      leaf session-timeout-value {
        tailf:cli-drop-node-name;
        type uint16 {
          tailf:info
            "<0-35791>;;Session timeout interval in minutes";
          range "0..35791";
        }
      }
      leaf output {
        tailf:info
          "Include output traffic as well as input traffic";
        type empty;
      }
    }
    leaf stopbits {
      tailf:info
        "Set async line stop bits";
      type enumeration {
        enum "1" {
          tailf:info
            "One stop bit";
        }
        enum "1.5" {
          tailf:info
            "One and one-half stop bits";
        }
        enum "2" {
          tailf:info
            "Two stop bits";
        }
      }
    }
    container telnet {
      tailf:info
        "Telnet protocol-specific configuration";
      leaf transparent {
        tailf:info
          "Send a CR as a CR followed by a NULL instead of a CR followed by a LF";
        type empty;
      }
    }
    container transport {
      tailf:info
        "Define transport protocols for line";
      tailf:cli-incomplete-no;
      leaf-list input {
        tailf:info
          "Define which protocols to use when connecting to the terminal server";
        tailf:cli-flat-list-syntax;
        tailf:cli-replace-all;
        tailf:cli-no-value-on-delete;
        type enumeration {
          enum "all" {
            tailf:info
              "All protocols";
          }
          enum "none" {
            tailf:info
              "No protocols";
          }
          enum "ssh" {
            tailf:info
              "TCP/IP SSH protocol";
          }
          enum "telnet" {
            tailf:info
              "TCP/IP Telnet protocol";
          }
          enum "lat" {
            tailf:info
              "DEC LAT protocol";
          }
          enum "pad" {
            tailf:info
              "X.3 PAD";
          }
          enum "udptn" {
            tailf:info
              "UDPTN async via UDP protocol";
          }
          enum "rlogin" {
            tailf:info
              "Unix rlogin protocol";
          }
          enum "lapb-ta";
          enum "mop";
          enum "v120";
          enum "acercon";
        }
      }
      leaf-list output {
        tailf:info
          "Define which protocols to use for outgoing connections";
        tailf:cli-flat-list-syntax;
        tailf:cli-replace-all;
        tailf:cli-no-value-on-delete;
        type enumeration {
          enum "all" {
            tailf:info
              "All protocols";
          }
          enum "none" {
            tailf:info
              "No protocols";
          }
          enum "ssh" {
            tailf:info
              "TCP/IP SSH protocol";
          }
          enum "telnet" {
            tailf:info
              "TCP/IP Telnet protocol";
          }
          enum "lat" {
            tailf:info
              "DEC LAT protocol";
          }
          enum "pad" {
            tailf:info
              "X.3 PAD";
          }
          enum "udptn" {
            tailf:info
              "UDPTN async via UDP protocol";
          }
          enum "rlogin" {
            tailf:info
              "Unix rlogin protocol";
          }
          enum "lapb-ta";
          enum "mop";
          enum "v120";
        }
      }
      leaf preferred {
        tailf:info
          "Specify the preferred protocol to use";
        tailf:cli-no-value-on-delete;
        type enumeration {
          enum "none" {
            tailf:info
              "No protocols";
          }
          enum "ssh" {
            tailf:info
              "TCP/IP SSH protocol";
          }
          enum "telnet" {
            tailf:info
              "TCP/IP Telnet protocol";
          }
        }
      }
    }
    leaf speed {
      tailf:info
        "Set the transmit and receive speeds";
      tailf:cli-full-command;
      type uint32 {
        tailf:info
          "<0-4294967295>;;Transmit and receive speeds";
      }
    }
    leaf rxspeed {
      tailf:info
        "Set the receive speed";
      type uint32 {
        tailf:info
          "<0-4294967295>;;Receive speed";
      }
    }
    leaf txspeed {
      tailf:info
        "Set the transmit speed";
      type uint32 {
        tailf:info
          "<0-4294967295>;;Transmit speed";
      }
    }
    leaf flowcontrol {
      tailf:info
        "Set the flow control";
      type enumeration {
        enum "hardware" {
          tailf:info
            "Set hardware flow control";
        }
        enum "software" {
          tailf:info
            "Set software flow control";
        }
      }
    }
    leaf length {
      tailf:info
        "Set number of lines on a screen";
      tailf:cli-full-command;
      type uint16 {
        tailf:info
          "<0-512>;;Number of lines on screen (0 for no pausing)";
        range "0..512";
      }
    }
    leaf width {
      tailf:info
        "Set width of the display terminal";
      tailf:cli-full-command;
      type uint16 {
        tailf:info
          "Number of characters on a screen line";
        range "0..512";
      }
    }
  }

  grouping ncs_rpc_notif_queue-size-grouping {
    leaf queue-size-1 {
      tailf:cli-drop-node-name;
      type uint8 {
        tailf:info
          "<1-100>;;enter percent of queue size between 1 and 100";
        range "1..100";
      }
    }
    leaf queue-size-2 {
      tailf:cli-drop-node-name;
      type uint8 {
        tailf:info
          "<1-100>;;enter percent of queue size between 1 and 100";
        range "1..100";
      }
    }
    leaf queue-size-3 {
      tailf:cli-drop-node-name;
      type uint8 {
        tailf:info
          "<1-100>;;enter percent of queue size between 1 and 100";
        range "1..100";
      }
    }
    leaf queue-size-4 {
      tailf:cli-drop-node-name;
      type uint8 {
        tailf:info
          "<1-100>;;enter percent of queue size between 1 and 100";
        range "1..100";
      }
    }
    leaf queue-size-5 {
      tailf:cli-drop-node-name;
      type uint8 {
        tailf:info
          "<1-100>;;enter percent of queue size between 1 and 100";
        range "1..100";
      }
    }
    leaf queue-size-6 {
      tailf:cli-drop-node-name;
      type uint8 {
        tailf:info
          "<1-100>;;enter percent of queue size between 1 and 100";
        range "1..100";
      }
    }
    leaf queue-size-7 {
      tailf:cli-drop-node-name;
      type uint8 {
        tailf:info
          "<1-100>;;enter percent of queue size between 1 and 100";
        range "1..100";
      }
    }
    leaf queue-size-8 {
      tailf:cli-drop-node-name;
      type uint8 {
        tailf:info
          "<1-100>;;enter percent of queue size between 1 and 100";
        range "1..100";
      }
    }
  }

  grouping ncs_rpc_notif_interface-common-pre-grouping {
    leaf mac-address {
      tailf:info
        "Manually set interface MAC address";
      type string {
        tailf:info
          "H.H.H;;MAC address";
      }
    }
    leaf description {
      tailf:info
        "Interface specific description";
      tailf:cli-multi-value;
      tailf:cli-preformatted;
      tailf:cli-full-command;
      type string {
        tailf:info
          "LINE;;Up to 240 characters describing this interface";
        length "0..240";
      }
    }
    container backup {
      tailf:info
        "Modify backup parameters";
      container interface {
        tailf:info
          "Configure an interface as a backup";
        uses ncs_rpc_notif_interface-name-grouping;
      }
    }
    list glbp {
      tailf:info
        "Gateway Load Balancing Protocol interface commands";
      tailf:cli-suppress-mode;
      tailf:cli-delete-when-empty;
      key "group-number";
      leaf group-number {
        type uint16 {
          tailf:info
            "<0-1023>;;Group number";
          range "0..1023";
        }
      }
      leaf ip {
        tailf:info
          "Enable group and set virtual IP address";
        type inet:ipv4-address {
          tailf:info
            "A.B.C.D;;Virtual IP address";
        }
      }
      container ip-secondary-list {
        tailf:cli-drop-node-name;
        list ip {
          tailf:cli-suppress-mode;
          tailf:cli-delete-when-empty;
          tailf:cli-incomplete-command;
          key "address";
          leaf address {
            type inet:ipv4-address {
              tailf:info
                "A.B.C.D;;Virtual IP address";
            }
          }
          leaf secondary {
            tailf:info
              "Make this IP address a secondary address";
            type empty;
          }
        }
      }
      leaf priority {
        tailf:info
          "Priority level";
        type uint8 {
          tailf:info
            "<1-255>;;Priority value";
          range "1..255";
        }
      }
      container preempt {
        tailf:info
          "Overthrow lower priority designated routers";
        tailf:cli-delete-when-empty;
        presence "true";
        container delay {
          tailf:info
            "Wait before preempting";
          leaf minimum {
            tailf:info
              "Delay at least this long";
            type uint32 {
              tailf:info
                "<0-3600>;;Number of seconds for minimum delay";
              range "0..3600";
            }
          }
        }
      }
    }
  }

  grouping ncs_rpc_notif_interface-ospfv3-grouping {
    container area {
      tailf:info
        "Set the OSPF area ID";
      tailf:cli-compact-syntax;
      tailf:cli-sequence-commands;
      leaf id {
        tailf:cli-drop-node-name;
        tailf:cli-reset-container;
        type union {
          type uint32 {
            tailf:info
              "<0-4294967295>;;OSPF area ID as a decimal value";
          }
          type inet:ipv4-address {
            tailf:info
              "A.B.C.D;;OSPF area ID in IP address format";
          }
        }
      }
      leaf instance {
        tailf:info
          "Set the OSPF instance";
        type uint8 {
          tailf:info
            "<0-31>;;Instance ID";
          range "0..31";
        }
      }
    }
    leaf priority {
      tailf:info
        "Router priority";
      tailf:cli-full-command;
      type uint8 {
        tailf:info
          "<0-255>;;Priority";
      }
    }
    container authentication {
      tailf:info
        "Enable authentication";
      choice authentication-choice {
        leaf key-chain {
          tailf:info
            "Use a key-chain for cryptographic authentication keys";
          // NCS drop tailf-common:non-strict-leafref statement
          type string {
            tailf:info
              "WORD;;Key-chain name";
          }
        }
        leaf null {
          tailf:info
            "Use no authentication";
          type empty;
        }
      }
    }
  }

  grouping ncs_rpc_notif_interface-common-grouping0 {
    container arp {
      tailf:info
        "Set arp type (arpa, probe, snap), timeout, log options orpacket priority";
      leaf timeout {
        tailf:info
          "Set ARP cache timeout";
        tailf:cli-full-command;
        type uint32 {
          tailf:info
            "<0-2147483>;;Seconds";
          range "0..2147483";
        }
      }
      leaf frame-relay {
        tailf:info
          "Enable ARP for a frame relay interface";
        tailf:cli-boolean-no;
        tailf:cli-full-command;
        type boolean;
      }
    }
    container authentication {
      tailf:info
        "set the port-control value";
      container event {
        tailf:info
          "Set action for authentication events";
        container server {
          tailf:info
            "Configure actions for AAA server events";
          container dead {
            tailf:info
              "Configure AAA server dead actions";
            container action {
              tailf:info
                "Required action for authentication event";
              container authorize {
                tailf:info
                  "Authorize the port";
                leaf vlan {
                  tailf:info
                    "Configure Critical Authorization VLAN";
                  type uint16 {
                    tailf:info
                      "<1-4094>;;Enter a VlanId";
                  }
                }
              }
            }
          }
        }
        container no-response {
          tailf:info
            "Configure non-responsive host actions";
          container action {
            tailf:info
              "Required action for authentication event";
            container authorize {
              tailf:info
                "Authorize the port";
              leaf vlan {
                tailf:info
                  "Configure Guest vlan";
                type uint16 {
                  tailf:info
                    "<1-4094>;;Enter a VlanId";
                  range "1..4094";
                }
              }
            }
          }
        }
      }
      leaf host-mode {
        tailf:info
          "Set the Host mode for authentication on this interface";
        type enumeration {
          enum "multi-auth" {
            tailf:info
              "Multiple Authentication Mode";
          }
          enum "multi-domain" {
            tailf:info
              "Multiple Domain Mode";
          }
          enum "multi-host" {
            tailf:info
              "Multiple Host Mode";
          }
          enum "single-host" {
            tailf:info
              "SINGLE HOST Mode";
          }
        }
      }
      container order {
        tailf:info
          "Add an authentication method to the order list";
        leaf dot1x {
          tailf:info
            "Authentication method 'dot1x' allowed";
          type enumeration {
            enum "mab" {
              tailf:info
                "Authentication method 'mab' allowed";
            }
            enum "webauth" {
              tailf:info
                "Authentication method 'webauth' allowed";
            }
          }
        }
      }
      container priority {
        tailf:info
          "Add an authentication method to the priority list";
        leaf dot1x {
          tailf:info
            "Authentication method 'dot1x' allowed";
          type enumeration {
            enum "mab" {
              tailf:info
                "Authentication method 'mab' allowed";
            }
            enum "webauth" {
              tailf:info
                "Authentication method 'webauth' allowed";
            }
          }
        }
      }
      leaf port-control {
        tailf:info
          "Set the port-control value";
        type enumeration {
          enum "auto" {
            tailf:info
              "PortState will be set to AUTO";
          }
          enum "force-authorized" {
            tailf:info
              "PortState set to Authorized";
          }
          enum "force-unauthorized" {
            tailf:info
              "PortState will be set to UnAuthorized";
          }
        }
      }
      leaf periodic {
        tailf:info
          "Enable or Disable Reauthentication for this port";
        type empty;
      }
      container timer {
        tailf:info
          "Set authentication timer values";
        leaf reauthenticate {
          tailf:info
            "Time in seconds after which an automatic re-authentication should be initiated (default 1 hour)";
          type union {
            type uint16 {
              tailf:info
                "<1-65535>;;Enter a value between 1 and 65535";
              range "1..65535";
            }
            type enumeration {
              enum "server" {
                tailf:info
                  "Obtain re-authentication timeout value from the server";
              }
            }
          }
        }
      }
    }
    container access-session {
      tailf:info
        "Access Session specific Interface Configuration Commands";
      leaf closed {
        tailf:info
          "Enable closed access on port (disabled by default, i.e. open access)";
        type empty;
      }
      leaf port-control {
        tailf:info
          "Set the port-control value";
        type enumeration {
          enum "auto" {
            tailf:info
              "PortState set to automatic";
          }
          enum "force-authorized" {
            tailf:info
              "PortState set to AUTHORIZED";
          }
          enum "force-unauthorized" {
            tailf:info
              "PortState set to UnAuthorized";
          }
        }
        default "force-authorized";
      }
    }
    container mab {
      tailf:info
        "MAC Authentication Bypass Interface Config Commands";
      presence "true";
      leaf eap {
        tailf:info
          "Use EAP authentication for MAC Auth Bypass";
        type empty;
      }
    }
    leaf medium {
      tailf:info
        "Configures the interface as point-to-point";
      type enumeration {
        enum "p2p";
      }
    }
    container frame-relay {
      tailf:info
        "Set frame relay parameters";
      container multilink {
        tailf:info
          "Set Multilink FR parameters";
        leaf output-threshold {
          tailf:info
            "Set output-threshold as xmt credit on one bundle link";
          type uint32 {
            tailf:info
              "<20-2147483647>;;number of bytes";
            range "20..2147483647";
          }
        }
        container bid {
          tailf:info
            "Bundle id for this bundle interface";
          tailf:cli-reset-container;
          leaf bid {
            tailf:cli-drop-node-name;
            type string {
              tailf:info
                "LINE;;String to identify this bundle to the peer";
            }
          }
        }
      }
      leaf lmi-type {
        tailf:info
          "Use CISCO-ANSI-CCITT type LMI";
        tailf:cli-full-command;
        type enumeration {
          enum "ansi";
          enum "cisco";
          enum "q933a";
        }
      }
      leaf intf-type {
        tailf:info
          "Configure a FR DTE/DCE/NNI interface";
        tailf:cli-full-command;
        type enumeration {
          enum "dce" {
            tailf:info
              "Configure a FR DCE";
          }
          enum "dte" {
            tailf:info
              "Configure a FR DTE";
          }
          enum "nni" {
            tailf:info
              "Configure a FR NNI";
          }
        }
      }
      container interface-dlci {
        tailf:info
          "Define a DLCI on an interface/subinterface";
        tailf:cli-add-mode;
        tailf:cli-mode-name "config-fr-dlci";
        tailf:cli-compact-syntax;
        tailf:cli-sequence-commands {
          tailf:cli-reset-siblings;
        }
        leaf dlci {
          tailf:cli-drop-node-name;
          tailf:cli-hide-in-submode;
          type uint16 {
            tailf:info
              "<16-1007>;;Define a switched or locally terminated DLCI";
          }
        }
        leaf encapsulation {
          tailf:cli-drop-node-name;
          tailf:cli-hide-in-submode;
          type enumeration {
            enum "cisco" {
              tailf:info
                "Use CISCO Encapsulation";
            }
            enum "IETF" {
              tailf:info
                "Use RFC1490/RFC2427 Encapsulation";
            }
          }
        }
        leaf class {
          // NCS drop tailf-common:non-strict-leafref statement
          type string;
        }
      }
    }
    container fair-queue {
      tailf:info
        "Enable Fair Queuing on an Interface";
      tailf:cli-compact-syntax;
      tailf:cli-sequence-commands;
      tailf:cli-reset-container;
      tailf:cli-delete-when-empty;
      presence "true";
      leaf congestive-discard-threshold {
        tailf:cli-drop-node-name;
        type uint16 {
          tailf:info
            "<1-4096>;;Congestive Discard Threshold";
        }
      }
      leaf dynamic-queues {
        tailf:cli-drop-node-name;
        type uint16 {
          tailf:info
            "<16-4096>;;Number Dynamic Conversation Queues";
        }
      }
      leaf reservable-queues {
        tailf:cli-drop-node-name;
        type uint16 {
          tailf:info
            "<0-1000>;;Number Reservable Conversation Queues";
        }
      }
    }
    container flowcontrol {
      tailf:info
        "Configure flow operation.";
      leaf bidirectional {
        tailf:cli-boolean-no;
        tailf:cli-full-command;
        type boolean;
        default "true";
      }
      leaf receive {
        tailf:info
          "Configure receiving flow operation";
        type enumeration {
          enum "desired" {
            tailf:info
              "Allow but do not require flow-control packets on port";
          }
          enum "off" {
            tailf:info
              "Disable flow-control packets on port";
          }
          enum "on" {
            tailf:info
              "Enable flow-control packets on port";
          }
        }
      }
      leaf send {
        tailf:info
          "Configure sending flow operation";
        type enumeration {
          enum "desired" {
            tailf:info
              "Allow but do not require flow-control packets on port";
          }
          enum "off" {
            tailf:info
              "Disable flow-control packets on port";
          }
          enum "on" {
            tailf:info
              "Enable flow-control packets on port";
          }
        }
      }
    }
    container traffic-shape {
      tailf:info
        "Enable Traffic Shaping on an Interface or Sub-Interface";
      container rate {
        tailf:info
          "configure token bucket: CIR (bps) [Bc (bits) [Be (bits)]]";
        tailf:cli-compact-syntax;
        tailf:cli-sequence-commands;
        leaf bit-rate {
          tailf:cli-drop-node-name;
          tailf:cli-diff-dependency "../../group/access-list" {
            tailf:xpath-root 3;
            tailf:cli-trigger-on-set;
          }
          type uint32 {
            tailf:info
              "<8000-100000000>;;Target Bit Rate (bits per second)";
          }
        }
        leaf burst-size {
          tailf:cli-drop-node-name;
          type uint32 {
            tailf:info
              "<0-100000000>;;bits per interval, sustained";
            range "0..100000000";
          }
        }
        leaf excess-burst-size {
          tailf:cli-drop-node-name;
          type uint32 {
            tailf:info
              "<0-100000000>;;bits per interval, excess in first interval";
            range "0..100000000";
          }
        }
        leaf max-buffers {
          tailf:cli-drop-node-name;
          type uint16 {
            tailf:info
              "<1-4096>;;Set buffer limit";
            range "1..4096";
          }
        }
      }
      list group {
        tailf:info
          "configure token bucket: group <access-list> CIR (bps) [Bc (bits) [Be (bits)]] ";
        tailf:cli-suppress-mode;
        tailf:cli-delete-when-empty;
        tailf:cli-compact-syntax;
        tailf:cli-sequence-commands;
        key "access-list";
        leaf access-list {
          tailf:cli-diff-dependency "../../rate/bit-rate" {
            tailf:xpath-root 3;
            tailf:cli-trigger-on-set;
          }
          type uint16 {
            tailf:info
              "<1-2799>;;selecting Access list";
            range "1..2799";
          }
        }
        leaf bit-rate {
          tailf:cli-drop-node-name;
          type uint32 {
            tailf:info
              "<8000-100000000>;;Target Bit Rate (bits per second)";
          }
        }
        leaf burst-size {
          tailf:cli-drop-node-name;
          type uint32 {
            tailf:info
              "<0-100000000>;;bits per interval, sustained";
            range "0..100000000";
          }
        }
        leaf excess-burst-size {
          tailf:cli-drop-node-name;
          type uint32 {
            tailf:info
              "<0-100000000>;;bits per interval, excess in first interval";
            range "0..100000000";
          }
        }
        leaf max-buffers {
          tailf:cli-drop-node-name;
          type uint16 {
            tailf:info
              "<1-4096>;;Set buffer limit";
            range "1..4096";
          }
        }
      }
    }
    choice keepalive-choice {
      leaf keepalive {
        tailf:info
          "Enable keepalive";
        tailf:cli-boolean-no;
        tailf:cli-full-command;
        type boolean;
        default "true";
      }
      container keepalive-period {
        tailf:cli-drop-node-name;
        leaf keepalive {
          tailf:info
            "Enable keepalive";
          type uint16 {
            tailf:info
              "<0-32767>;;Keepalive period (default 10 seconds)";
            range "0..32767";
          }
          default "10";
        }
      }
      container keepalive-period-retries {
        tailf:cli-drop-node-name;
        container keepalive {
          tailf:cli-compact-syntax;
          tailf:cli-sequence-commands {
            tailf:cli-reset-siblings;
          }
          leaf period {
            tailf:cli-drop-node-name;
            type uint16 {
              tailf:info
                "<0-32767>;;Keepalive period (default 10 seconds)";
              range "0..32767";
            }
          }
          leaf retries {
            tailf:cli-drop-node-name;
            type uint8 {
              range "1..255";
            }
          }
        }
      }
    }
    container snmp {
      tailf:info
        "Modify SNMP interface parameters";
      container ifindex {
        tailf:info
          "Persist ifindex for the interface";
        leaf persist {
          tailf:info
            "Enable/Disable ifIndex persistence ";
          type empty;
        }
      }
      container trap {
        tailf:info
          "Allow a specific SNMP trap";
        leaf link-status {
          tailf:info
            "Allow SNMP LINKUP and LINKDOWN traps";
          tailf:cli-boolean-no;
          tailf:cli-full-command;
          type boolean;
          default "true";
        }
        container link-status-capas {
          tailf:cli-drop-node-name;
          container link-status {
            tailf:info
              "Allow SNMP LINKUP and LINKDOWN traps";
            container permit {
              tailf:info
                "Permit the following capability";
              leaf duplicates {
                tailf:info
                  "Permit duplicate SNMP LINKUP and LINKDOWN traps";
                type empty;
              }
            }
          }
        }
        container mac-notification {
          tailf:info
            "MAC Address notification for the interface";
          container change {
            tailf:info
              "Enable Mac Address notification feature for this port";
            leaf added {
              tailf:info
                "Enable Mac Address added notification for this port";
              type empty;
            }
            leaf removed {
              tailf:info
                "Enable Mac Address removed notification for this port";
              type empty;
            }
          }
        }
      }
    }
    container flow-sampler {
      tailf:info
        "Attach flow sampler to the interface";
      leaf name {
        tailf:cli-drop-node-name;
        // NCS drop tailf-common:non-strict-leafref statement
        type string {
          tailf:info
            "WORD;;Name of the flow sampler";
        }
      }
      container egress {
        tailf:cli-drop-node-name;
        tailf:cli-compact-syntax;
        tailf:cli-sequence-commands;
        leaf name {
          tailf:cli-drop-node-name;
          tailf:cli-incomplete-command;
          // NCS drop tailf-common:non-strict-leafref statement
          type string {
            tailf:info
              "WORD;;Name of the flow sampler";
          }
        }
        leaf egress {
          tailf:info
            "Egress flow sampler";
          type empty;
        }
      }
    }
    container lldp {
      tailf:info
        "LLDP interface subcommands";
      leaf transmit {
        tailf:info
          "Enable LLDP transmission on interface";
        tailf:cli-boolean-no;
        tailf:cli-full-command;
        type boolean;
        default "true";
      }
      leaf receive {
        tailf:info
          "Enable LLDP reception on interface";
        tailf:cli-boolean-no;
        tailf:cli-full-command;
        type boolean;
        default "true";
      }
    }
    container bfd {
      tailf:info
        "BFD interface configuration commands";
      container interval {
        tailf:info
          "Transmit interval between BFD packets";
        tailf:cli-compact-syntax;
        tailf:cli-sequence-commands {
          tailf:cli-reset-all-siblings;
        }
        leaf msecs {
          tailf:cli-drop-node-name;
          tailf:cli-incomplete-command;
          type uint16 {
            tailf:info
              "<15-999>;;Milliseconds";
            range "15..999";
          }
        }
        leaf min_rx {
          tailf:info
            "Minimum receive interval capability";
          tailf:cli-incomplete-command;
          type uint16 {
            tailf:info
              "<15-999>;;Milliseconds";
            range "15..999";
          }
        }
        leaf multiplier {
          tailf:info
            "Multiplier value used to compute holddown";
          type uint8 {
            tailf:info
              "<3-50>;;value used to multiply the interval";
            range "3..50";
          }
        }
      }
      leaf echo {
        tailf:info
          "Use echo adjunct as bfd detection mechanism";
        tailf:cli-boolean-no;
        tailf:cli-full-command;
        type boolean;
        default "true";
      }
      leaf template {
        tailf:info
          "BFD template";
        tailf:cli-full-command;
        type string {
          tailf:info
            "WORD;;bfd template name";
        }
      }
    }
    container bandwidth {
      tailf:info
        "Set bandwidth informational parameter";
      tailf:cli-compact-syntax;
      tailf:cli-sequence-commands {
        tailf:cli-reset-siblings;
      }
      leaf inherit {
        tailf:cli-optional-in-sequence;
        tailf:info
          "Specify how bandwidth is inherited";
        type empty;
      }
      leaf kilobits {
        tailf:cli-drop-node-name;
        type uint32 {
          tailf:info
            "<1-10000000>;;Bandwidth in kilobits";
          range "1..10000000";
        }
      }
    }
    container cdp {
      tailf:info
        "CDP interface subcommands";
      leaf enable {
        tailf:info
          "Enable CDP on interface";
        tailf:cli-boolean-no;
        tailf:cli-full-command;
        type boolean;
        default "true";
      }
      container tlv {
        tailf:info
          "Enable exchange of specific tlv information";
        container app {
          tailf:info
            "Enable/Configure Application TLV";
          tailf:cli-display-separated;
          tailf:cli-compact-syntax;
          tailf:cli-reset-container;
          tailf:cli-sequence-commands;
          presence "true";
          leaf tlvtype {
            tailf:info
              "Configure APP TLV";
            tailf:cli-incomplete-command;
            type uint16 {
              tailf:info
                "Configure App TLV Type information";
              range "1001..65535";
            }
          }
          leaf value {
            tailf:info
              "Configure App TLV Value information";
            type string {
              tailf:info
                "WORD;;Configure App TLV value information";
            }
          }
        }
        leaf server-location {
          tailf:info
            "Enable CDP location server on interface";
          tailf:cli-full-command;
          type empty;
        }
        leaf location {
          tailf:info
            "Exchange location information";
          tailf:cli-full-command;
          type empty;
        }
      }
    }
    container mop {
      tailf:info
        "DEC MOP server commands";
      leaf xenabled {
        tailf:alt-name "enabled";
        tailf:info
          "Enable MOP for interface";
        tailf:cli-boolean-no;
        tailf:cli-full-command;
        type boolean;
        default "true";
      }
      leaf sysid {
        tailf:cli-boolean-no;
        tailf:cli-full-command;
        type boolean;
        default "true";
      }
    }
    container dampening {
      tailf:info
        "Enable event dampening";
      presence "true";
      leaf dampening-time {
        tailf:cli-drop-node-name;
        tailf:cli-delete-container-on-delete;
        type uint16 {
          tailf:info
            "<1-30>;;Half-life time for penalty";
          range "1..30";
        }
      }
    }
    list vlan-range {
      tailf:cli-mode-name "config-if-vlan-range";
      key "id";
      leaf id {
        type uint16 {
          tailf:info
            "WORD;;VLAN IDs 1-4094";
          range "1..4094";
        }
      }
      container service-policy {
        tailf:info
          "Configure Service Policy";
        uses ncs_rpc_notif_service-policy-grouping;
      }
    }
    list hold-queue {
      tailf:info
        "Set hold queue depth";
      tailf:cli-suppress-mode;
      tailf:cli-delete-when-empty;
      tailf:cli-compact-syntax;
      tailf:cli-sequence-commands {
        tailf:cli-reset-siblings;
      }
      key "direction";
      leaf direction {
        type enumeration {
          enum "in" {
            tailf:info
              "Input queue";
          }
          enum "out" {
            tailf:info
              "Output queue";
          }
        }
      }
      leaf queue-length {
        tailf:cli-drop-node-name;
        tailf:cli-prefix-key;
        type uint16 {
          tailf:info
            "<0-4096>;;Queue length";
          range "0..4096";
        }
      }
    }
    container mpls {
      tailf:info
        "Configure MPLS interface parameters";
      container accounting {
        tailf:info
          "Enable MPLS accounting on this interface";
        container experimental {
          tailf:info
            "Count packets by MPLS experimental value on this interface";
          leaf input {
            tailf:info
              "received packets";
            type empty;
          }
          leaf output {
            tailf:info
              "transmitted packets";
            type empty;
          }
        }
      }
      container bgp {
        tailf:info
          "MPLS BGP";
        leaf forwarding {
          tailf:info
            "Configure MPLS forwarding for directly connected BGP peers";
          type empty;
        }
      }
      container label {
        tailf:info
          "Label properties";
        leaf protocol {
          tailf:info
            "Configure label/tag distribution protocol (LDP/TDP)";
          type enumeration {
            enum "both" {
              tailf:info
                "Use LDP or TDP (Adapt to peer on multiaccess interface)";
            }
            enum "ldp" {
              tailf:info
                "Use LDP (default)";
            }
            enum "tdp" {
              tailf:info
                "Use TDP";
            }
          }
        }
      }
      container ldp {
        tailf:info
          "Configure Label Distribution Protocol (LDP) parameters";
        container igp {
          tailf:info
            "Configure IGP-related parameters";
          choice sync-choice {
            leaf sync {
              tailf:info
                "Allow LDP-IGP Synchronization on this interface";
              tailf:cli-boolean-no;
              tailf:cli-full-command;
              type boolean;
              default "true";
            }
            container sync-delay {
              tailf:cli-drop-node-name;
              container sync {
                tailf:info
                  "Allow LDP-IGP Synchronization on this interface";
                tailf:cli-incomplete-command;
                tailf:cli-incomplete-no;
                leaf delay {
                  tailf:info
                    "Configure LDP to IGP sync achieved notification delay time";
                  type uint8 {
                    tailf:info
                      "<5-60>;;Delay time (seconds)";
                    range "5..60";
                  }
                }
              }
            }
          }
        }
        container discovery {
          tailf:info
            "Configure interface LDP Discovery parameters";
          leaf transport-address {
            tailf:info
              "Specify interface LDP transport address";
            type ldp-discovery-address-type;
          }
        }
      }
      leaf mtu {
        tailf:info
          "Set MPLS Maximum Transmission Unit";
        tailf:cli-full-command;
        type union {
          type uint16 {
            tailf:info
              "<1501-1524>;;MTU (baby giants bytes)";
            range "1501..1524";
          }
          type uint16 {
            tailf:info
              "<64-1500>;;MTU (bytes)";
            range "64..1500";
          }
          type uint16 {
            tailf:info
              "<64-9216>;;MTU size in bytes";
            range "64..9216";
          }
        }
        default "1500";
      }
      container traffic-eng {
        tailf:info
          "Configure Traffic Engineering parameters";
        leaf administrative-weight {
          tailf:info
            "Set the administrative weight for the interface";
          tailf:cli-full-command;
          type uint32 {
            tailf:info
              "<0-4294967295>;;Weight";
            range "0..4294967295";
          }
        }
        leaf backup-path {
          tailf:info
            "Configure an MPLS TE backup for this interface";
          type string {
            tailf:info
              "Tunnel;;Tunnel interface";
          }
        }
        leaf attribute-flags {
          tailf:info
            "Set user-defined interface attibute flags";
          tailf:cli-full-command;
          type string {
            tailf:info
              "<0x0-0xFFFFFFFF>;;Attribute flags";
          }
        }
        container flooding {
          tailf:info
            "Set flooding parameters";
          container thresholds {
            tailf:info
              "Set flooding thresholds";
            leaf-list down {
              tailf:info
                "Set the thresholds for decreased resource availability";
              tailf:cli-flat-list-syntax;
              type uint8 {
                tailf:info
                  "<0-100>;;decreased bandwidth usage (percent)";
                range "0..100";
              }
            }
            leaf-list up {
              tailf:info
                "Set the thresholds for increased resource availability";
              tailf:cli-flat-list-syntax;
              type uint8 {
                tailf:info
                  "<0-100>;;increased bandwidth usage (percent)";
                range "0..100";
              }
            }
          }
        }
        leaf tunnels {
          tailf:info
            "enable MPLS Traffic Engineering tunnels";
          tailf:cli-full-command;
          type empty;
        }
      }
      leaf ip {
        tailf:info
          "Configure dynamic MPLS forwarding for IP";
        tailf:cli-full-command;
        type empty;
      }
      leaf propagate-cos {
        type empty;
      }
    }
    container isis {
      tailf:info
        "IS-IS commands";
      container bfd {
        tailf:info
          "Bidirectional Forwarding Protocol";
        tailf:cli-reset-container;
        tailf:cli-delete-when-empty;
        presence "true";
        leaf disable {
          tailf:info
            "disable bfd";
          type empty;
        }
      }
      leaf tag {
        tailf:info
          "Assign an admin tag to an ISIS interface IP route";
        type uint32 {
          tailf:info
            "<1-4294967295>;;Admin tag number";
        }
      }
      leaf circuit-type {
        tailf:info
          "Configure circuit type for interface";
        type enumeration {
          enum "level-1" {
            tailf:info
              "Level-1 only adjacencies are formed";
          }
          enum "level-1-2" {
            tailf:info
              "Level-1-2 adjacencies are formed";
          }
          enum "level-2-only" {
            tailf:info
              "Level-2 only adjacencies are formed";
          }
        }
        default "level-1-2";
      }
      leaf network {
        tailf:info
          "Network type";
        tailf:cli-full-command;
        type enumeration {
          enum "point-to-point" {
            tailf:info
              "Specify ISIS point-to-point network";
          }
        }
      }
      choice metric-choice {
        case default-case {
          leaf metric {
            tailf:info
              "Configure the metric for interface";
            type uint32 {
              tailf:info
                "<1-16777214>;;Default metric";
              range "1..16777214";
            }
          }
        }
        case level-case {
          container metric-level {
            tailf:cli-drop-node-name;
            list metric {
              tailf:cli-suppress-mode;
              tailf:cli-delete-when-empty;
              tailf:cli-compact-syntax;
              key "level";
              leaf level {
                type enumeration {
                  enum "level-1" {
                    tailf:info
                      "Apply metric to level-1 links";
                  }
                  enum "level-2" {
                    tailf:info
                      "Apply metric to level-2 links";
                  }
                }
              }
              leaf default {
                tailf:cli-drop-node-name;
                tailf:cli-prefix-key;
                type uint32 {
                  tailf:info
                    "<1-16777214>;;Default metric";
                  range "1..16777214";
                }
              }
            }
          }
        }
      }
      uses ncs_rpc_notif_router-isis-interface-grouping;
      container ipv6 {
        tailf:info
          "IPv6 interface configuration";
        tailf:cli-diff-dependency "../../ipv6/enable" {
          tailf:xpath-root 3;
          tailf:cli-trigger-on-set;
        }
        choice metric-choice {
          leaf metric {
            tailf:info
              "Configure the metric for interface";
            type union {
              type uint32 {
                tailf:info
                  "<1-16777214>;;Default metric";
                range "1..16777214";
              }
              type enumeration {
                enum "maximum" {
                  tailf:info
                    "Maximum metric. All routers will exclude this link from their SPF";
                }
              }
            }
          }
          container metric-level {
            tailf:cli-drop-node-name;
            list metric {
              tailf:info
                "Configure the metric for interface";
              tailf:cli-suppress-mode;
              tailf:cli-delete-when-empty;
              tailf:cli-compact-syntax;
              tailf:cli-sequence-commands;
              key "level";
              leaf level {
                type enumeration {
                  enum "level-1" {
                    tailf:info
                      "Apply metric to level-1 links";
                  }
                  enum "level-2" {
                    tailf:info
                      "Apply metric to level-2 links";
                  }
                }
              }
              leaf value {
                tailf:cli-drop-node-name;
                tailf:cli-prefix-key;
                type union {
                  type uint32 {
                    tailf:info
                      "<1-16777214>;;Default metric";
                    range "1..16777214";
                  }
                  type enumeration {
                    enum "maximum" {
                      tailf:info
                        "Maximum metric. All routers will exclude this link from their SPF";
                    }
                  }
                }
              }
            }
          }
        }
      }
      leaf three-way-handshake {
        tailf:info
          "Select Cisco or IETF three-way handshake";
        tailf:cli-diff-dependency "../../ipv6/router/isis" {
          tailf:xpath-root 3;
          tailf:cli-trigger-on-set;
        }
        type enumeration {
          enum "cisco" {
            tailf:info
              "Cisco implementation of three-way handshake (default)";
          }
          enum "ietf" {
            tailf:info
              "IETF implementation of three-way handshake";
          }
        }
        default "cisco";
      }
      choice priority-choice {
        leaf priority {
          tailf:info
            "Set priority for Designated Router election";
          tailf:cli-full-command;
          type uint8 {
            tailf:info
              "<0-127>;;Priority value";
            range "0..127";
          }
        }
        container priority-level-1-2 {
          tailf:cli-drop-node-name;
          list priority {
            tailf:info
              "Set priority for Designated Router election";
            tailf:cli-suppress-mode;
            tailf:cli-delete-when-empty;
            tailf:cli-compact-syntax;
            tailf:cli-sequence-commands;
            key "level";
            leaf level {
              type enumeration {
                enum "level-1" {
                  tailf:info
                    "Specify priority for level-1 routing";
                }
                enum "level-2" {
                  tailf:info
                    "Specify priority for level-2 routing";
                }
              }
            }
            leaf priority {
              tailf:cli-drop-node-name;
              tailf:cli-prefix-key;
              type uint8 {
                tailf:info
                  "<0-127>;;Priority value";
                range "0..127";
              }
            }
          }
        }
      }
      container hello-multiplier {
        tailf:info
          "Set Hello multiplier";
        leaf seconds {
          tailf:cli-drop-node-name;
          type uint16 {
            tailf:info
              "<1-65535>;;Hello multiplier value";
            range "1..65535";
          }
        }
      }
      container hello-interval {
        tailf:info
          "Set Hello interval in seconds";
        choice hello-interval-choice {
          leaf seconds {
            tailf:cli-drop-node-name;
            type uint16 {
              tailf:info
                "<1-65535>;;Hello interval value";
              range "1..65535";
            }
          }
          leaf minimal {
            tailf:info
              "Holdtime 1 second, interval depends on multiplier";
            type empty;
          }
        }
      }
      choice csnp-interval-choice {
        leaf csnp-interval {
          tailf:info
            "Set CSNP interval in seconds";
          tailf:cli-full-command;
          type uint16 {
            tailf:info
              "<0-65535>;;CSNP interval value";
          }
        }
        container csnp-interval-level {
          tailf:cli-drop-node-name;
          list csnp-interval {
            tailf:cli-suppress-mode;
            tailf:cli-delete-when-empty;
            tailf:cli-compact-syntax;
            tailf:cli-sequence-commands;
            key "level";
            leaf level {
              type enumeration {
                enum "level-1" {
                  tailf:info
                    "Specify interval for level-1 CSNPs";
                }
                enum "level-2" {
                  tailf:info
                    "Specify interval for level-2 CSNPs";
                }
              }
            }
            leaf seconds {
              tailf:cli-drop-node-name;
              tailf:cli-prefix-key;
              type uint16 {
                tailf:info
                  "<0-65535>;;CSNP interval value";
              }
            }
          }
        }
      }
      choice password-choice {
        leaf password {
          tailf:info
            "Configure the authentication password for interface";
          tailf:cli-full-command;
          type string {
            tailf:info
              "WORD;;Password";
          }
        }
        container password-level-1-2 {
          tailf:cli-drop-node-name;
          list password {
            tailf:cli-sequence-commands;
            tailf:cli-compact-syntax;
            key "level";
            leaf password {
              tailf:cli-prefix-key;
              tailf:cli-drop-node-name;
              type string {
                tailf:info
                  "WORD;;Password";
              }
            }
            leaf level {
              type enumeration {
                enum "level-1" {
                  tailf:info
                    "Specify password for level-1 PDUs";
                }
                enum "level-2" {
                  tailf:info
                    "Specify password for level-2 PDUs";
                }
              }
            }
          }
        }
      }
    }
    choice vrf-choice {
      container ip-vrf {
        tailf:cli-drop-node-name;
        container ip {
          container vrf {
            leaf forwarding {
              tailf:info
                "Configure forwarding table";
              tailf:cli-diff-dependency "/ios:ip/vrf" {
                tailf:xpath-root 3;
              }
              // NCS drop tailf-common:non-strict-leafref statement
              type string {
                tailf:info
                  "WORD;;VRF name";
              }
            }
          }
        }
      }
      container vrf {
        tailf:info
          "VPN Routing/Forwarding parameters on the interface";
        leaf forwarding {
          tailf:info
            "Configure forwarding table";
          tailf:cli-diff-dependency "/ios:vrf/definition" {
            tailf:xpath-root 3;
          }
          // NCS drop tailf-common:non-strict-leafref statement
          type string {
            tailf:info
              "WORD;;VRF name";
          }
        }
      }
    }
    container pm-path {
      tailf:info
        "Global pm-path configuration";
      tailf:cli-compact-syntax;
      tailf:cli-sequence-commands {
        tailf:cli-reset-siblings;
      }
      tailf:cli-diff-dependency "/ios:pm-agent" {
        tailf:xpath-root 3;
      }
      leaf name {
        tailf:cli-drop-node-name;
        tailf:cli-incomplete-command;
        type string {
          tailf:info
            "WORD;;Path name";
        }
      }
      leaf interface-id {
        tailf:info
          "Specify the interface-id";
        type uint32 {
          tailf:info
            "<1-4294967295>;;Specify the interface-id value";
          range "1..4294967295";
        }
      }
    }
    container ip {
      tailf:info
        "Interface Internet Protocol config commands";
      list access-group {
        tailf:info
          "Specify access control for packets";
        tailf:cli-suppress-mode;
        tailf:cli-delete-when-empty;
        tailf:cli-compact-syntax;
        tailf:cli-sequence-commands;
        key "direction";
        leaf direction {
          type enumeration {
            enum "in" {
              tailf:code-name "access_group_direction_in";
              tailf:info
                "inbound packets";
            }
            enum "out" {
              tailf:code-name "access_group_direction_out";
              tailf:info
                "outbound packets";
            }
          }
        }
        leaf access-list {
          tailf:cli-diff-dependency "/ios:ip/access-list" {
            tailf:xpath-root 3;
          }
          tailf:cli-drop-node-name;
          tailf:cli-prefix-key;
          type exp-ip-acl-type;
        }
      }
      container authentication {
        tailf:info
          "authentication subcommands";
        container mode {
          tailf:info
            "mode";
          list eigrp {
            tailf:info
              "Enhanced Interior Gateway Routing Protocol (EIGRP)";
            tailf:cli-suppress-mode;
            tailf:cli-delete-when-empty;
            tailf:cli-incomplete-command;
            key "as-no";
            leaf as-no {
              type uint16 {
                tailf:info
                  "<1-65535>;;Autonomous system number";
                range "1..65535";
              }
            }
            leaf md5 {
              tailf:info
                "Keyed message digest";
              type empty;
            }
          }
        }
        container key-chain {
          tailf:info
            "key-chain";
          list eigrp {
            tailf:info
              "Enhanced Interior Gateway Routing Protocol (EIGRP)";
            tailf:cli-suppress-mode;
            tailf:cli-delete-when-empty;
            tailf:cli-incomplete-command;
            key "as-no";
            leaf as-no {
              type uint16 {
                tailf:info
                  "<1-65535>;;Autonomous system number";
                range "1..65535";
              }
            }
            leaf key-chain {
              tailf:cli-drop-node-name;
              // NCS drop tailf-common:non-strict-leafref statement
              type string {
                tailf:info
                  "WORD;;name of key-chain";
              }
            }
          }
        }
      }
      container accounting {
        tailf:info
          "Enable IP accounting on this interface";
        tailf:cli-delete-when-empty;
        presence "true";
        leaf output-packets {
          tailf:info
            "Account for IP packets output on this interface";
          tailf:cli-full-command;
          type empty;
        }
        container precedence {
          tailf:info
            "Count packets by IP precedence on this interface";
          leaf input {
            tailf:info
              "received packets";
            type empty;
          }
          leaf output {
            tailf:info
              "transmitted packets";
            type empty;
          }
        }
        leaf access-violations {
          tailf:info
            "Account for IP packets violating access lists on this interface";
          tailf:cli-full-command;
          type empty;
        }
      }
      container vrf {
        tailf:info
          "VPN Routing/Forwarding parameters on the interface";
        leaf receive {
          tailf:info
            "Add Interface Address into VRF Table";
          tailf:cli-full-command;
          type string {
            tailf:info
              "WORD;;Table name";
          }
        }
        leaf sitemap {
          tailf:info
            "Configure route-map for routesreceived from this site";
          tailf:cli-full-command;
          type string {
            tailf:info
              "WORD;;Name of the route-map";
          }
        }
      }
      container arp {
        tailf:info
          "Configure ARP features";
        container inspection {
          tailf:info
            "Arp Inspection configuration";
          leaf trust {
            tailf:info
              "Configure Trust state";
            type empty;
          }
          container limit {
            tailf:info
              "Configure Rate limit of incoming ARP packets";
            tailf:cli-compact-syntax;
            tailf:cli-sequence-commands {
              tailf:cli-reset-siblings;
            }
            choice limit-choice {
              leaf none {
                tailf:info
                  "No limit";
                type empty;
              }
              leaf rate {
                tailf:info
                  "Rate Limit";
                type uint16 {
                  tailf:info
                    "<0-10000>;;Packets per second";
                  range "0..10000";
                }
              }
            }
            container burst {
              tailf:info
                "Configure Burst parameters for ARP packets";
              tailf:cli-flatten-container;
              leaf interval {
                tailf:info
                  "Number of seconds to check the rate";
                type uint8 {
                  tailf:info
                    "<1-15>;;Burst interval in seconds";
                  range "1..15";
                }
              }
            }
          }
        }
      }
      choice address-choice {
        container unnumbered {
          tailf:info
            "Enable IP processing without an explicit address";
          uses ncs_rpc_notif_interface-name-grouping;
        }
        container no-address {
          tailf:cli-drop-node-name;
          leaf address {
            tailf:cli-boolean-no;
            tailf:cli-full-command;
            tailf:cli-full-no;
            type boolean;
            default "true";
          }
        }
        container address {
          tailf:info
            "Set the IP address of an interface";
          tailf:cli-incomplete-command;
          tailf:cli-incomplete-no;
          choice address-choice {
            case fixed-case {
              container primary {
                tailf:cli-drop-node-name;
                tailf:cli-compact-syntax;
                tailf:cli-sequence-commands;
                tailf:cli-incomplete-command;
                tailf:cli-incomplete-no;
                tailf:cli-diff-dependency "/ios:l2vpn-xconnect/l2vpn/xconnect/context" {
                  tailf:xpath-root 3;
                  tailf:cli-trigger-on-set;
                }
                leaf address {
                  tailf:cli-drop-node-name;
                  tailf:cli-incomplete-command;
                  tailf:cli-incomplete-no;
                  type inet:ipv4-address {
                    tailf:info
                      "A.B.C.D;;IP address";
                  }
                }
                leaf mask {
                  tailf:cli-drop-node-name;
                  type inet:ipv4-address {
                    tailf:info
                      "A.B.C.D;;IP subnet mask";
                  }
                }
              }
              list secondary {
                tailf:cli-drop-node-name;
                tailf:cli-suppress-mode;
                tailf:cli-delete-when-empty;
                tailf:cli-compact-syntax;
                tailf:cli-incomplete-command;
                tailf:cli-incomplete-no;
                tailf:cli-diff-dependency "../primary/address" {
                  tailf:xpath-root 3;
                }
                key "address mask";
                leaf address {
                  tailf:cli-incomplete-no;
                  type inet:ipv4-address {
                    tailf:info
                      "A.B.C.D;;IP address";
                  }
                }
                leaf mask {
                  type inet:ipv4-address {
                    tailf:info
                      "A.B.C.D;;IP subnet mask";
                  }
                }
                leaf secondary {
                  tailf:info
                    "Make this IP address a secondary address";
                  type empty;
                }
              }
            }
            case dhcp-case {
              container dhcp {
                tailf:info
                  "IP Address negotiated via DHCP";
                tailf:cli-compact-syntax;
                tailf:cli-sequence-commands;
                presence "true";
                container client-id {
                  tailf:info
                    "Specify client-id to use";
                  tailf:cli-optional-in-sequence;
                  tailf:cli-flatten-container;
                  tailf:cli-compact-syntax;
                  uses ncs_rpc_notif_interface-name-grouping;
                }
                leaf hostname {
                  tailf:info
                    "Specify value for hostname option";
                  type string {
                    tailf:info
                      "WORD;;hostname string";
                  }
                }
              }
            }
            case negotiated-case {
              container negotiated {
                tailf:info
                  "IP Address negotiated over PPP";
                tailf:cli-reset-container;
                tailf:cli-delete-when-empty;
                presence "true";
                leaf previous {
                  tailf:info
                    "IPCP attempts to negotiate previous address assigned";
                  type empty;
                }
              }
            }
          }
        }
      }
      container directed-broadcast {
        tailf:info
          "Enable forwarding of directed broadcasts";
        tailf:cli-delete-when-empty;
        presence "true";
        leaf access-list {
          tailf:cli-drop-node-name;
          type union {
            type uint16 {
              tailf:info
                "<1-199>;;A standard IP access list number";
              range "1..199";
            }
            type uint16 {
              tailf:info
                "<1300-2699>;;A standard IP expanded access list number";
              range "1300..2699";
            }
          }
        }
      }
      container split-horizon-eigrp {
        tailf:cli-drop-node-name;
        container split-horizon {
          tailf:info
            "Perform split horizon";
          tailf:cli-incomplete-command;
          tailf:cli-incomplete-no;
          container eigrp {
            tailf:info
              "Enhanced Interior Gateway Routing Protocol (EIGRP)";
            list no-list {
              tailf:info
                "'no ip split-horizon eigrp' entry";
              tailf:cli-suppress-mode;
              tailf:cli-delete-when-empty;
              key "as-no";
              leaf as-no {
                type uint16 {
                  tailf:info
                    "<1-65535>;;Autonomous System";
                  range "1..65535";
                }
              }
            }
          }
        }
      }
      leaf split-horizon {
        tailf:info
          "Perform split horizon";
        tailf:cli-boolean-no;
        tailf:cli-full-command;
        type boolean;
        default "true";
      }
      container router {
        tailf:info
          "IP router interface commands";
        container isis {
          tailf:info
            "IS-IS Routing for IP";
          tailf:cli-delete-when-empty;
          presence "true";
          leaf tag {
            tailf:cli-drop-node-name;
            type string {
              tailf:info
                "WORD;;Routing process tag";
            }
          }
        }
      }
      container flow {
        tailf:info
          "NetFlow related commands";
        leaf ingress {
          tailf:info
            "Enable inbound NetFlow";
          type empty;
        }
        leaf egress {
          tailf:info
            "Enable outbound NetFlow";
          type empty;
        }
        list monitor {
          tailf:info
            "Apply a Flow Monitor";
          tailf:cli-suppress-mode;
          tailf:cli-delete-when-empty;
          tailf:cli-compact-syntax;
          tailf:cli-sequence-commands {
            tailf:cli-reset-siblings;
          }
          key "direction";
          leaf direction {
            type enumeration {
              enum "input" {
                tailf:info
                  "Apply Flow Monitor on input traffic";
              }
              enum "output" {
                tailf:info
                  "Apply Flow Monitor on output traffic";
              }
            }
          }
          leaf name {
            tailf:cli-prefix-key;
            tailf:cli-drop-node-name;
            // NCS drop tailf-common:non-strict-leafref statement
            type string {
              tailf:info
                "WORD;;Flow Monitor name";
            }
          }
        }
      }
      container helper-address {
        tailf:info
          "Specify a destination address for UDP broadcasts";
        list helper-address-list {
          tailf:cli-drop-node-name;
          tailf:cli-suppress-mode;
          tailf:cli-delete-when-empty;
          tailf:cli-show-long-obu-diffs;
          ordered-by user;
          key "address";
          leaf address {
            type inet:ipv4-address {
              tailf:info
                "A.B.C.D;;IP destination address";
            }
          }
        }
        list vrf {
          tailf:cli-suppress-mode;
          tailf:cli-delete-when-empty;
          tailf:cli-show-long-obu-diffs;
          ordered-by user;
          key "vrf address";
          leaf vrf {
            type string {
              tailf:info
                "VRF name for helper-address";
            }
          }
          leaf address {
            type inet:ipv4-address {
              tailf:info
                "A.B.C.D;;IP destination address";
            }
          }
        }
      }
      container summary-address {
        tailf:info
          "Perform address summarization";
        list eigrp {
          tailf:info
            "Enhanced Interior Gateway Routing Protocol (EIGRP)";
          tailf:cli-delete-when-empty;
          tailf:cli-suppress-mode;
          key "as-no ip-address wildcard-mask";
          leaf as-no {
            type uint16 {
              tailf:info
                "<1-65535>;;Autonomous system number";
              range "1..65535";
            }
          }
          leaf ip-address {
            type inet:ipv4-address {
              tailf:info
                "A.B.C.D;;IP summary address";
            }
          }
          leaf wildcard-mask {
            type inet:ipv4-address {
              tailf:info
                "A.B.C.D;;Summary mask";
            }
          }
          leaf distance {
            tailf:cli-drop-node-name;
            type uint8 {
              tailf:info
                "<1-255>;;Administrative distance";
              range "1..255";
            }
          }
        }
      }
      container ospf {
        tailf:info
          "OSPF interface commands";
        list process-id {
          tailf:cli-drop-node-name;
          tailf:cli-suppress-mode;
          tailf:cli-delete-when-empty;
          tailf:cli-compact-syntax;
          tailf:cli-sequence-commands {
            tailf:cli-reset-siblings;
          }
          tailf:cli-incomplete-command;
          key "id";
          leaf id {
            tailf:cli-suppress-range;
            type uint16 {
              tailf:info
                "<1-65535>;;Process ID";
              range "1..65535";
            }
          }
          leaf area {
            tailf:info
              "Set the OSPF area ID";
            type union {
              type uint32 {
                tailf:info
                  "<0-4294967295>;;OSPF area ID as a decimal value";
              }
              type inet:ipv4-address {
                tailf:info
                  "A.B.C.D;;OSPF area ID in IP address format";
              }
            }
          }
          leaf secondaries {
            tailf:info
              "Include or exclude secondary IP addresses";
            type empty;
          }
          leaf none {
            tailf:info
              "Do not include secondary IP addresses";
            type empty;
          }
        }
        container authentication {
          tailf:info
            "Enable authentication";
          tailf:cli-delete-when-empty;
          presence "true";
          choice authentication-choice {
            leaf message-digest {
              tailf:info
                "Use message-digest authentication";
              type empty;
            }
            leaf null {
              tailf:info
                "Use no authentication";
              type empty;
            }
            leaf key-chain {
              tailf:info
                "Use a key-chain for cryptographic authentication keys";
              type string {
                tailf:info
                  "WORD;;Key-chain name";
              }
            }
          }
        }
        container authentication-key {
          tailf:info
            "Authentication password (key)";
          tailf:cli-compact-syntax;
          tailf:cli-sequence-commands;
          uses ncs_rpc_notif_password-grouping;
        }
        list message-digest-key {
          tailf:info
            "Message digest authentication password (key)";
          tailf:cli-suppress-mode;
          tailf:cli-delete-when-empty;
          tailf:cli-compact-syntax;
          tailf:cli-sequence-commands;
          tailf:cli-remove-before-change;
          key "id";
          leaf id {
            type uint8 {
              tailf:info
                "<1-255>;;Key ID";
              range "1..255";
            }
          }
          container md5 {
            tailf:info
              "Use MD5 algorithm";
            tailf:cli-flatten-container;
            tailf:cli-compact-syntax;
            tailf:cli-sequence-commands;
            uses ncs_rpc_notif_password-grouping;
          }
        }
        leaf-list network {
          tailf:info
            "Network type";
          tailf:cli-flat-list-syntax {
            tailf:cli-replace-all;
          }
          tailf:cli-full-command;
          max-elements 2;
          type enumeration {
            enum "point-to-multipoint" {
              tailf:info
                "Specify OSPF point-to-multipoint network";
            }
            enum "point-to-point" {
              tailf:info
                "Specify OSPF point-to-point network";
            }
            enum "broadcast" {
              tailf:info
                "Specify OSPF broadcast multi-access network";
            }
            enum "non-broadcast" {
              tailf:info
                "Specify OSPF NBMA network";
            }
          }
        }
        leaf hello-interval {
          tailf:info
            "Time between HELLO packets";
          type uint16 {
            tailf:info
              "<1-65535>;;Seconds";
            range "1..65535";
          }
        }
        container dead-interval {
          tailf:info
            "Interval after which a neighbor is declared dead";
          tailf:cli-compact-syntax;
          tailf:cli-sequence-commands {
            tailf:cli-reset-siblings;
          }
          choice dead-interva-choice {
            leaf seconds {
              tailf:cli-drop-node-name;
              type uint16 {
                tailf:info
                  "<1-65535>;;Seconds";
                range "1..65535";
              }
            }
            case minimal {
              leaf minimal {
                tailf:info
                  "Set to 1 second";
                type empty;
              }
              leaf hello-multiplier {
                tailf:info
                  "Set multiplier for Hellos";
                type uint8 {
                  tailf:info
                    "<3-20>;;Number of Hellos sent within 1 second";
                  range "3..20";
                }
              }
            }
          }
        }
        container bfd {
          tailf:info
            "BFD interface configuration commands";
          presence "true";
          leaf enable {
            tailf:cli-full-command;
            tailf:cli-drop-node-name;
            type enumeration {
              enum "disable" {
                tailf:info
                  "Disable BFD for this interface";
              }
            }
          }
        }
        leaf mtu-ignore {
          tailf:info
            "Ignores the MTU in DBD packets";
          tailf:cli-full-command;
          type empty;
        }
        leaf cost {
          tailf:info
            "Interface cost";
          tailf:cli-full-command;
          type uint16 {
            tailf:info
              "<1-65535>;;Cost";
            range "1..65535";
          }
        }
        container ttl-security {
          tailf:info
            "TTL security check";
          tailf:cli-delete-when-empty;
          presence "true";
          leaf hops {
            tailf:info
              "IP hops";
            type uint8 {
              tailf:info
                "<1-254>;;maximum number of hops allowed";
              range "1..254";
            }
          }
        }
        leaf priority {
          tailf:info
            "Router priority";
          tailf:cli-full-command;
          type uint8 {
            tailf:info
              "<0-255>;;Priority";
          }
        }
        container lls {
          tailf:info
            "Link-local Signaling (LLS) support";
          tailf:cli-delete-when-empty;
          presence "true";
          leaf disable {
            tailf:info
              "disable LLS";
            type empty;
          }
        }
        container database-filter {
          tailf:info
            "Filter OSPF LSA during synchronization and flooding";
          container all {
            tailf:info
              "Filter all LSA";
            leaf out {
              tailf:info
                "Outgoing LSA";
              type empty;
            }
          }
        }
      }
      container pim {
        tailf:info
          "PIM interface commands";
        leaf query-interval {
          tailf:info
            "PIM router query interval";
          type uint16 {
            tailf:info
              "<1-65535>;;Query interval in seconds or milliseconds";
            range "1..65535";
          }
          default "30";
        }
        leaf nbma-mode {
          tailf:info
            "Use Non-Broadcast Multi-Access (NBMA) mode on interface";
          type empty;
        }
        leaf mode {
          tailf:cli-drop-node-name;
          type enumeration {
            enum "sparse-mode" {
              tailf:info
                "Enable PIM sparse-mode operation";
            }
            enum "sparse-dense-mode" {
              tailf:info
                "Enable PIM sparse-dense-mode operation";
            }
          }
        }
        leaf dr-priority {
          tailf:info
            "PIM router DR priority";
          type uint32 {
            tailf:info
              "<0-4294967294>;;DR priority, preference given to larger value";
          }
        }
        leaf snooping {
          tailf:info
            "PIM Snooping enable for Catalyst Vlan";
          type empty;
        }
        leaf passive {
          tailf:info
            "Enable PIM passive interface operation";
          tailf:cli-full-command;
          type empty;
        }
      }
      container multicast {
        tailf:info
          "IP multicast interface commands";
        container boundary {
          tailf:info
            "Boundary for administratively scoped multicast addresses";
          tailf:cli-compact-syntax;
          tailf:cli-sequence-commands {
            tailf:cli-reset-siblings;
          }
          leaf access-list {
            tailf:cli-drop-node-name;
            type string {
              tailf:info
                "WORD;;ACL name or number";
            }
          }
          leaf filter-autorp {
            tailf:info
              "Filter AutoRP packet contents.";
            type empty;
          }
        }
        container limit {
          tailf:info
            "Limit multicast mroute state";
          list access-lists {
            tailf:cli-drop-node-name;
            tailf:cli-suppress-mode;
            tailf:cli-delete-when-empty;
            tailf:cli-incomplete-command;
            key "access-list";
            leaf access-list {
              tailf:cli-suppress-range;
              type ip-acl-type;
            }
            leaf allowed-state {
              tailf:cli-drop-node-name;
              type uint32 {
                tailf:info
                  "<0-2147483647>;;Max Allowed State on this interface";
                range "0..2147483647";
              }
            }
          }
          list connected {
            tailf:info
              "Limit connected incoming state";
            tailf:cli-suppress-mode;
            tailf:cli-delete-when-empty;
            tailf:cli-incomplete-command;
            key "access-list";
            leaf access-list {
              tailf:cli-suppress-range;
              type ip-acl-type;
            }
            leaf allowed-state {
              tailf:cli-drop-node-name;
              type uint32 {
                tailf:info
                  "<0-2147483647>;;Max Allowed State on this interface";
                range "0..2147483647";
              }
            }
          }
          list out {
            tailf:info
              "Limit outgoing state";
            tailf:cli-suppress-mode;
            tailf:cli-delete-when-empty;
            tailf:cli-incomplete-command;
            key "access-list";
            leaf access-list {
              tailf:cli-suppress-range;
              type ip-acl-type;
            }
            leaf allowed-state {
              tailf:cli-drop-node-name;
              type uint32 {
                tailf:info
                  "<0-2147483647>;;Max Allowed State on this interface";
                range "0..2147483647";
              }
            }
          }
          list rpf {
            tailf:info
              "Limit incoming state";
            tailf:cli-suppress-mode;
            tailf:cli-delete-when-empty;
            tailf:cli-incomplete-command;
            key "access-list";
            leaf access-list {
              tailf:cli-suppress-range;
              type ip-acl-type;
            }
            leaf allowed-state {
              tailf:cli-drop-node-name;
              type uint32 {
                tailf:info
                  "<0-2147483647>;;Max Allowed State on this interface";
                range "0..2147483647";
              }
            }
          }
        }
      }
      container policy {
        tailf:info
          "Enable policy routing";
        leaf route-map {
          tailf:info
            "Policy route-map";
          type string {
            tailf:info
              "WORD;;Route map name";
          }
        }
      }
      leaf unreachables {
        tailf:info
          "Enable sending ICMP Unreachable messages";
        tailf:cli-boolean-no;
        type boolean;
        default "true";
      }
      leaf proxy-arp {
        tailf:info
          "Enable proxy ARP";
        tailf:cli-boolean-no;
        type boolean;
        default "true";
      }
      container route-cache-conf {
        tailf:cli-drop-node-name;
        leaf route-cache {
          tailf:cli-boolean-no;
          tailf:cli-full-command;
          type boolean;
          default "true";
        }
      }
      container route-cache {
        tailf:info
          "Enable fast-switching cache for outgoing packets";
        tailf:cli-incomplete-no;
        tailf:cli-incomplete-command;
        leaf cef {
          tailf:info
            "Enable Cisco Express Forwarding";
          tailf:cli-boolean-no;
          type boolean;
          default "true";
        }
        leaf flow {
          tailf:info
            "Enable Flow fast-switching cache";
          tailf:cli-boolean-no;
          type boolean;
          default "false";
        }
        leaf policy {
          tailf:info
            "Enable fast-switching policy cache for outgoing packets";
          tailf:cli-boolean-no;
          type boolean;
          default "false";
        }
        leaf same-interface {
          tailf:info
            "Enable fast-switching on the same interface";
          tailf:cli-boolean-no;
          type boolean;
          default "false";
        }
      }
      leaf mroute-cache {
        tailf:info
          "Enable switching cache for incoming multicast packets";
        tailf:cli-boolean-no;
        tailf:cli-full-command;
        type boolean;
        default "true";
      }
      container igmp {
        tailf:info
          "IGMP interface commands";
        container max-groups {
          tailf:info
            "set maximum number of IGMP groups that can be joined";
          leaf number {
            tailf:cli-drop-node-name;
            tailf:cli-full-command;
            type uint32 {
              tailf:info
                "<0-4294967294>;;maximum # of groups";
            }
          }
          leaf action {
            tailf:info
              "action taken on exceeding the limit";
            tailf:cli-full-command;
            type enumeration {
              enum "deny" {
                tailf:info
                  "do not allow any more groups";
              }
              enum "replace" {
                tailf:info
                  "replace existing group with new";
              }
            }
            default "deny";
          }
        }
        leaf filter {
          tailf:info
            "set IGMP filter profile number";
          type uint32 {
            tailf:info
              "<1-4294967295>;;IGMP profile number";
            range "1..4294967295";
          }
        }
        list join-group {
          tailf:info
            "IGMP join multicast group";
          tailf:cli-suppress-mode;
          tailf:cli-delete-when-empty;
          tailf:cli-compact-syntax;
          key "address";
          leaf address {
            type inet:ipv4-address {
              tailf:info
                "A.B.C.D;;IP group address";
            }
          }
          leaf source {
            tailf:info
              "Include SSM source";
            type inet:ipv4-address {
              tailf:info
                "A.B.C.D;;IP source address";
            }
          }
        }
        container static-group {
          tailf:info
            "IGMP static multicast group";
          list groups {
            tailf:cli-drop-node-name;
            tailf:cli-suppress-mode;
            tailf:cli-delete-when-empty;
            key "name";
            leaf name {
              tailf:cli-suppress-range;
              type union {
                type inet:ipv4-address {
                  tailf:info
                    "A.B.C.D;;IP group address";
                }
                type enumeration {
                  enum "*" {
                    tailf:info
                      "Populated for all groups";
                  }
                }
              }
            }
          }
          list class-map {
            tailf:info
              "Class map of type multicast-flows";
            tailf:cli-suppress-mode;
            tailf:cli-delete-when-empty;
            key "id";
            leaf id {
              // NCS drop tailf-common:non-strict-leafref statement
              type string {
                tailf:info
                  "WORD;;Name of class-map of type multicast-flows";
              }
            }
          }
        }
        leaf version {
          tailf:info
            "IGMP version";
          type uint8 {
            tailf:info
              "<1-3>;;version number";
            range "1..3";
          }
        }
        leaf access-group {
          tailf:info
            "IGMP group access group";
          type exp-ip-acl-type;
        }
      }
      leaf redirects {
        tailf:info
          "Enable sending ICMP Redirect messages";
        tailf:cli-boolean-no;
        tailf:cli-full-command;
        type boolean;
        default "true";
      }
      container hello-interval {
        tailf:info
          "Configures EIGRP-IPv4 hello interval";
        list eigrp {
          tailf:info
            "Enhanced Interior Gateway Routing Protocol (EIGRP)";
          tailf:cli-suppress-mode;
          tailf:cli-delete-when-empty;
          tailf:cli-incomplete-command;
          key "as-number";
          leaf as-number {
            type uint16 {
              tailf:info
                "<1-65535>;;AS number";
            }
          }
          leaf seconds {
            tailf:cli-drop-node-name;
            type uint16 {
              tailf:info
                "<1-65535>;;Seconds between hello transmissions";
              range "1..65535";
            }
          }
        }
      }
      container hold-time {
        tailf:info
          "Configures EIGRP-IPv4 hold time";
        list eigrp {
          tailf:info
            "Enhanced Interior Gateway Routing Protocol (EIGRP)";
          tailf:cli-suppress-mode;
          tailf:cli-delete-when-empty;
          tailf:cli-incomplete-command;
          key "as-number";
          leaf as-number {
            type uint16 {
              tailf:info
                "<1-65535>;;AS number";
            }
          }
          leaf seconds {
            tailf:cli-drop-node-name;
            type uint16 {
              tailf:info
                "<1-65535>;;Seconds before neighbor is considered down";
              range "1..65535";
            }
          }
        }
      }
      container nbar {
        tailf:info
          "Network-Based Application Recognition";
        leaf protocol-discovery {
          tailf:info
            "Enable protocol discovery for both ipv4 and ipv6";
          type empty;
        }
      }
      container nhrp {
        tailf:info
          "NHRP interface subcommands";
        leaf authentication {
          tailf:info
            "Authentication string";
          type string {
            tailf:info
              "WORD;;authentication string";
          }
        }
        leaf group {
          tailf:info
            "NHRP group name";
          type string {
            tailf:info
              "WORD;;group name string";
          }
        }
        container map {
          tailf:info
            "Map dest IP addresses to NBMA addresses";
          list map-list {
            tailf:cli-drop-node-name;
            tailf:cli-suppress-mode;
            tailf:cli-delete-when-empty;
            key "ip-address";
            leaf ip-address {
              type inet:ipv4-address {
                tailf:info
                  "A.B.C.D;;IP address of destination";
              }
            }
            leaf nbma-address {
              tailf:cli-drop-node-name;
              type union {
                type inet:ipv4-address {
                  tailf:info
                    "A.B.C.D;;IP NBMA address";
                }
                type inet:ipv6-address {
                  tailf:info
                    "X:X:X:X::X;;IPv6 NBMA address";
                }
              }
            }
          }
          container multicast {
            tailf:info
              "Use this NBMA mapping for broadcasts/multicasts";
            leaf dynamic {
              tailf:info
                "Dynamically learn destinations from client registrations on hub";
              type empty;
            }
            list multicast-list {
              tailf:cli-drop-node-name;
              tailf:cli-suppress-mode;
              tailf:cli-delete-when-empty;
              key "nbma-address";
              leaf nbma-address {
                type union {
                  type inet:ipv4-address {
                    tailf:info
                      "A.B.C.D;;IP NBMA address";
                  }
                  type inet:ipv6-address {
                    tailf:info
                      "X:X:X:X::X;;IPv6 NBMA address";
                  }
                }
              }
            }
          }
          list group {
            tailf:info
              "NHRP group mapping";
            tailf:cli-suppress-mode;
            tailf:cli-delete-when-empty;
            tailf:cli-incomplete-command;
            key "name";
            leaf name {
              type string {
                tailf:info
                  "WORD;;NHRP group name";
              }
            }
            container service-policy {
              tailf:info
                "QoS service-policy";
              leaf output {
                tailf:info
                  "apply QoS service policy in the output direction";
                // NCS drop tailf-common:non-strict-leafref statement
                type string {
                  tailf:info
                    "WORD;;QoS policy-map name";
                }
              }
            }
          }
        }
        leaf network-id {
          tailf:info
            "NBMA network identifier";
          type union {
            type uint32 {
              tailf:info
                "<1-4294967295>;;Network identifier";
            }
            type inet:ipv4-address {
              tailf:info
                "A.B.C.D;;IP address";
            }
          }
        }
        leaf holdtime {
          tailf:info
            "Advertised holdtime";
          type uint16 {
            tailf:info
              "<1-65535>;;Number of seconds";
            range "1..65535";
          }
        }
        container nhs {
          tailf:info
            "Specify a next hop server";
          list nhs-list {
            tailf:cli-drop-node-name;
            tailf:cli-suppress-mode;
            tailf:cli-delete-when-empty;
            tailf:cli-compact-syntax;
            key "nhs-address";
            leaf nhs-address {
              type inet:ipv4-address {
                tailf:info
                  "A.B.C.D;;Protocol IP address of NHS";
              }
            }
            leaf nbma {
              tailf:info
                "NBMA of NHS";
              type union {
                type inet:ipv4-address {
                  tailf:info
                    "A.B.C.D;;IPv4 address";
                }
                type inet:ipv6-address {
                  tailf:info
                    "X:X:X:X::X;;IPv6 address";
                }
                type string {
                  tailf:info
                    "WORD;;NHS FQDN string";
                }
              }
            }
            leaf multicast {
              when "../nbma" {
                tailf:xpath-root 3;
                tailf:dependency "../nbma";
              }
              tailf:info
                "Use this NBMA mapping for broadcasts/multicasts";
              type empty;
            }
          }
        }
        container server-only {
          tailf:info
            "Disable NHRP requests";
          tailf:cli-reset-container;
          tailf:cli-delete-when-empty;
          presence "true";
          leaf non-caching {
            tailf:info
              "Do not create NHRP cache entries";
            type empty;
          }
        }
        container registration {
          tailf:info
            "Settings for registration packets.";
          leaf no-unique {
            tailf:info
              "Do not set the 'Unique' flag in registration requests.";
            type empty;
          }
          leaf timeout {
            tailf:info
              "Time between periodic Registration messages";
            type uint16 {
              tailf:info
                "<1-65535>;;Number of seconds";
              range "1..65535";
            }
          }
        }
        container shortcut {
          tailf:info
            "Enable shortcut switching";
          tailf:cli-delete-when-empty;
          presence "true";
          leaf virtual-template {
            tailf:info
              "Virtual template interface number";
            type uint16 {
              tailf:info
                "<1-200>;;Virtual template number";
            }
          }
        }
        container redirect {
          tailf:info
            "Enable NHRP redirect traffic indication";
          tailf:cli-delete-when-empty;
          presence "true";
          leaf timeout {
            tailf:info
              "Specify interval over which to throttle";
            type uint8 {
              tailf:info
                "<2-30>;;Interval in seconds";
              range "2..30";
            }
          }
        }
      }
      container tcp {
        tailf:info
          "TCP header compression and other parameters";
        leaf adjust-mss {
          tailf:info
            "Adjust the mss of transit packets";
          type uint16 {
            tailf:info
              "<500-1460>;;Maximum segment size in bytes";
            range "500..1460";
          }
        }
        container header-compression {
          tailf:info
            "Enable TCP header compression";
          tailf:cli-delete-when-empty;
          presence "true";
          leaf type {
            tailf:cli-drop-node-name;
            type enumeration {
              enum "ietf-format" {
                tailf:info
                  "Compressing using IETF format";
              }
              enum "iphc-format" {
                tailf:info
                  "Using PPP  IPHC compression for TCP/UDP/RTP";
              }
              enum "passive" {
                tailf:info
                  "Compress only for destinations which send compressed headers";
              }
            }
          }
        }
        leaf compression-connections {
          tailf:info
            "Maximum number of compressed connections";
          type uint16 {
            tailf:info
              "<1-256>;;Number of connections";
            range "1..256";
          }
        }
      }
      container rtp {
        tailf:info
          "RTP parameters";
        container header-compression {
          tailf:info
            "Enable RTP header compression";
          tailf:cli-compact-syntax;
          tailf:cli-sequence-commands {
            tailf:cli-reset-siblings;
          }
          leaf type {
            tailf:cli-drop-node-name;
            tailf:cli-optional-in-sequence;
            type enumeration {
              enum "ietf-format" {
                tailf:info
                  "Compressing using IETF format";
              }
              enum "iphc-format" {
                tailf:info
                  "Compress using IPHC format";
              }
              enum "passive" {
                tailf:info
                  "Compress only for destinations which send compressed headers";
              }
            }
          }
          leaf periodic-refresh {
            tailf:info
              "Periodic context refresh";
            type empty;
          }
        }
        leaf compression-connections {
          tailf:info
            "Maximum number of compressed connections";
          type uint16 {
            tailf:info
              "<1-1000>;;Number of connections";
            range "1..1000";
          }
        }
      }
      container header-compression {
        tailf:info
          "IPHC options";
        leaf max-header {
          tailf:info
            "Maximim compressible header";
          type uint8 {
            tailf:info
              "<20-168>;;Maximim compressible header";
            range "20..168";
          }
        }
      }
      container mobile {
        tailf:info
          "Mobile IP support";
        container router-service {
          tailf:info
            "Mobile router support";
          container roam {
            tailf:info
              "Roaming interface";
            presence "true";
            leaf priority {
              tailf:info
                "Priority level";
              type uint8 {
                tailf:info
                  "<0-255>;;Priority level";
              }
            }
          }
          leaf description {
            tailf:info
              "roaming interface description";
            tailf:cli-multi-value;
            tailf:cli-preformatted;
            tailf:cli-full-command;
            type string {
              tailf:info
                "LINE;;roaming interface description";
            }
          }
          leaf link-type {
            tailf:info
              "Link type of the roaming interface";
            type string;
          }
          container tunnel {
            tailf:info
              "Tunnel parameters";
            leaf mode {
              tailf:info
                "Tunnel encapsulation mode";
              type enumeration {
                enum "gre" {
                  tailf:info
                    "Generic Routing Encapsulation";
                }
                enum "ipip" {
                  tailf:info
                    "IP-in-IP Encapsulation";
                }
              }
            }
          }
          container collocated {
            tailf:info
              "Collocated care-of address options";
            tailf:cli-compact-syntax;
            tailf:cli-sequence-commands;
            leaf gateway {
              tailf:info
                "Default gateway for static collocated care-of address";
              tailf:cli-optional-in-sequence;
              type inet:ipv4-address {
                tailf:info
                  "A.B.C.D;;IP address to use as the default gateway";
              }
            }
            leaf ccoa-only {
              tailf:info
                "Only register a collocated CoA";
              tailf:cli-optional-in-sequence;
              type empty;
            }
            container registration {
              tailf:info
                "Registration options";
              tailf:cli-break-sequence-commands;
              leaf retry {
                tailf:info
                  "Retry interval in seconds (1-65535)";
                type uint16 {
                  tailf:info
                    "<1-65535>;;Seconds (default 60; 65535 = never)";
                  range "1..65535";
                }
                default "60";
              }
              container nat {
                tailf:info
                  "NAT traversal settings";
                container traversal {
                  tailf:info
                    "Enable NAT traversal support";
                  tailf:cli-compact-syntax;
                  presence "true";
                  leaf keepalive {
                    tailf:info
                      "Keepalive message frequency (sec)";
                    type uint16 {
                      tailf:info
                        "<0-65535>;;keepalive value";
                    }
                  }
                  leaf force {
                    tailf:info
                      "Force home agent to use UDP encapsulation for the tunnel";
                    type empty;
                  }
                }
              }
            }
            leaf encapsulation {
              type enumeration {
                enum "slip";
                enum "ppp";
              }
            }
          }
        }
      }
      list inspect {
        tailf:cli-suppress-mode;
        tailf:cli-delete-when-empty;
        tailf:cli-compact-syntax;
        tailf:cli-sequence-commands {
          tailf:cli-reset-siblings;
        }
        key "direction";
        leaf direction {
          type enumeration {
            enum "in" {
              tailf:info
                "Inbound inspection";
            }
            enum "out" {
              tailf:info
                "Outbound inspection";
            }
          }
        }
        leaf name {
          tailf:cli-prefix-key;
          tailf:cli-drop-node-name;
          // NCS drop tailf-common:non-strict-leafref statement
          type string {
            tailf:info
              "WORD;;Name of inspection defined";
          }
        }
      }
      container virtual-reassembly {
        tailf:info
          "Enable Virtual Fragment Reassembly";
        tailf:cli-delete-when-empty;
        presence "true";
        leaf in {
          tailf:info
            "Enable VFR on Ingress";
          tailf:cli-full-command;
          type empty;
        }
        leaf out {
          tailf:info
            "Enable VFR on Egress";
          tailf:cli-full-command;
          type empty;
        }
        container conf {
          tailf:cli-drop-node-name;
          tailf:cli-compact-syntax;
          leaf drop-fragments {
            tailf:info
              "Drop all the incoming fragments";
            type empty;
          }
          leaf max-fragments {
            tailf:info
              "Specify max number of fragments per reassembly (datagram)";
            type uint8 {
              tailf:info
                "<1-64>;;Number of fragments per datagram";
              range "1..64";
            }
          }
          leaf max-reassemblies {
            tailf:info
              "Specify max number of concurrent reassemblies";
            type uint16 {
              tailf:info
                "<1-1024>;;Number of datagrams that can be reassembled at a time";
              range "1..1024";
            }
          }
          leaf timeout {
            tailf:info
              "Specify timeout value of the datagram being reassembled";
            type uint8 {
              tailf:info
                "<1-60>;;Timeout value of the datagram being reassembled";
            }
          }
          leaf percentage {
            tailf:info
              "Reserved Reassembly capacity for high priority packets";
            type uint8 {
              tailf:info
                "<1-100>;;Reserved Reassembly capacity percentage";
              range "1..100";
            }
          }
          leaf-list dscp {
            tailf:info
              "DSCP value";
            tailf:cli-flat-list-syntax;
            tailf:cli-full-command;
            type dscp-type;
          }
          leaf-list precedence {
            tailf:info
              "IP precedence";
            tailf:cli-flat-list-syntax;
            tailf:cli-full-command;
            type precedence-type;
          }
        }
      }
      container dns {
        tailf:info
          "Configure DNS server";
        leaf view-group {
          tailf:info
            "Configure a DNS view-list for use on this interface";
          // NCS drop tailf-common:non-strict-leafref statement
          type string {
            tailf:info
              "WORD;;View-list name";
          }
        }
      }
      container dhcp {
        tailf:info
          "Configure DHCP parameters for this interface";
        container relay {
          tailf:info
            "DHCP relay configuration parameters";
          container information {
            tailf:info
              "DHCP relay information option";
            container check-reply {
              tailf:info
                "Validate relay information in BOOTREPLY";
              presence "true";
              leaf none {
                tailf:info
                  "Set to none";
                type empty;
              }
            }
            container option {
              tailf:info
                "DHCP relay information option";
              leaf subscriber-id {
                tailf:info
                  "Subscriber identifier sub option";
                type string {
                  tailf:info
                    "WORD;;Subscriber identifier string";
                }
              }
            }
            container option-insert {
              tailf:info
                "Insert relay information in BOOTREQUEST";
              presence "true";
              leaf none {
                tailf:info
                  "Set to none";
                type empty;
              }
            }
            leaf policy-action {
              tailf:info
                "Define reforwarding policy";
              type enumeration {
                enum "drop" {
                  tailf:info
                    "Do not forward BOOTREQUEST message";
                }
                enum "encapsulate" {
                  tailf:info
                    "Encapsulate existing information";
                }
                enum "keep" {
                  tailf:info
                    "Leave existing information alone";
                }
                enum "replace" {
                  tailf:info
                    "Replace existing information";
                }
              }
            }
            leaf trusted {
              tailf:info
                "Received DHCP packet may contain relay info option with zero giaddr";
              type empty;
            }
          }
        }
        container snooping {
          tailf:info
            "DHCP Snooping";
          container limit {
            tailf:info
              "DHCP Snooping limit";
            leaf rate {
              tailf:info
                "DHCP Snooping limit";
              type uint16 {
                tailf:info
                  "<1-2048>;;DHCP snooping rate limit";
                range "1..2048";
              }
            }
          }
          leaf trust {
            tailf:info
              "DHCP Snooping trust config";
            type empty;
          }
          list vlan {
            tailf:info
              "DHCP Snooping vlan";
            tailf:cli-suppress-mode;
            tailf:cli-delete-when-empty;
            tailf:cli-compact-syntax;
            key "id";
            leaf id {
              type uint16 {
                tailf:info
                  "<1-4094>;;DHCP Snooping vlan";
                range "1..4094";
              }
            }
            container information {
              tailf:info
                "DHCP Snooping information";
              tailf:cli-flatten-container;
              container option {
                tailf:info
                  "DHCP Snooping information option";
                container format-type {
                  tailf:info
                    "Option 82 information format";
                  container circuit-id {
                    tailf:info
                      "Circuit id option 82 format";
                    leaf string {
                      tailf:info
                        "User defined string for circuit id";
                      type string {
                        tailf:info
                          "WORD;;Use string for circuit id (3-63 chars)";
                        length "3..63";
                      }
                    }
                  }
                }
              }
            }
          }
          list bridge-domain {
            tailf:info
              "DHCP Snooping bridge-domain";
            tailf:cli-suppress-mode;
            tailf:cli-delete-when-empty;
            tailf:cli-compact-syntax;
            key "id";
            leaf id {
              type uint16 {
                tailf:info
                  "<1-4094>;;DHCP Snooping bridge-domain number";
                range "1..4094";
              }
            }
            container information {
              tailf:info
                "DHCP Snooping information";
              tailf:cli-flatten-container;
              container option {
                tailf:info
                  "DHCP Snooping information option";
                container format-type {
                  tailf:info
                    "Option 82 information format";
                  container circuit-id {
                    tailf:info
                      "Circuit id option 82 format";
                    leaf string {
                      tailf:info
                        "User defined string for circuit id";
                      type string {
                        tailf:info
                          "WORD;;Use string for circuit id";
                      }
                    }
                  }
                }
              }
            }
          }
        }
      }
      leaf mtu {
        tailf:info
          "Set IP Maximum Transmission Unit";
        type uint16 {
          tailf:info
            "<68-9216>;;MTU (bytes)";
          range "68..9216";
        }
      }
      container nat {
        tailf:info
          "NAT interface commands";
        leaf allow-static-host {
          tailf:info
            "Allow static-ip clients";
          type empty;
        }
        leaf enable {
          tailf:info
            "Enable Address Translation (NVI)";
          type empty;
        }
        choice nat-choice {
          leaf inside {
            tailf:info
              "Inside interface for address translation";
            type empty;
          }
          leaf outside {
            tailf:info
              "Outside interface for address translation";
            type empty;
          }
        }
      }
      container rsvp {
        tailf:info
          "RSVP Interface Commands";
        container bandwidth {
          tailf:info
            "RSVP Reservable Bandwidth (kbps)";
          tailf:cli-compact-syntax;
          tailf:cli-sequence-commands {
            tailf:cli-reset-siblings;
          }
          tailf:cli-delete-when-empty;
          presence "true";
          leaf interface-bandwidth {
            tailf:cli-drop-node-name;
            type uint32 {
              tailf:info
                "<1-10000000>;;Reservable Bandwidth (kbps)";
              range "1..10000000";
            }
          }
          leaf single-flow-bandwidth {
            tailf:cli-drop-node-name;
            type uint32 {
              tailf:info
                "<1-10000000>;;Largest Reservable Flow (kbps)";
              range "1..10000000";
            }
          }
        }
        container signalling {
          tailf:info
            "RSVP signalling";
          container hello {
            tailf:info
              "Enable neighbor-down detection";
            presence "true";
            container graceful-restart {
              tailf:info
                "Configure RSVP Graceful Restart";
              presence "true";
            }
          }
        }
        container resource-provider {
          tailf:info
            "RSVP resource provider";
          choice resource-provider-choice {
            leaf none {
              tailf:info
                "Associates NO resources with reservations";
              type empty;
            }
            leaf wfq {
              tailf:info
                "Associates WFQ resources with reservations";
              type enumeration {
                enum "interface" {
                  tailf:info
                    "Associates WFQ queues and bandwidth at the interface level with reservations";
                }
                enum "pvc" {
                  tailf:info
                    "Associates WFQ queues and bandwidth at the PVC level with reservations";
                }
              }
            }
          }
        }
      }
      container verify {
        tailf:info
          "Enable per packet validation";
        container unicast {
          tailf:info
            "Enable per packet validation for unicast";
          container reverse-path {
            tailf:info
              "Reverse path validation of source address (old command format)";
            presence "true";
          }
          container source {
            tailf:info
              "Validation of source address";
            tailf:cli-compact-syntax;
            tailf:cli-sequence-commands {
              tailf:cli-reset-all-siblings;
            }
            leaf reachable-via {
              tailf:info
                "Specify reachability check to apply to the source address";
              type enumeration {
                enum "any" {
                  tailf:info
                    "Source is reachable via any interface";
                }
                enum "rx" {
                  tailf:info
                    "Source is reachable via interface on which packet was received";
                }
              }
            }
            leaf allow-self-ping {
              tailf:cli-break-sequence-commands;
              tailf:info
                "Allow router to ping itself (opens vulnerability in verification)";
              type empty;
            }
            leaf allow-default {
              tailf:info
                "Allow default route to match when checking source address";
              type empty;
            }
            leaf access-list {
              tailf:cli-drop-node-name;
              tailf:cli-disallow-value "allow-self-ping|allow-default";
              type exp-ip-acl-type;
            }
          }
        }
        container source {
          tailf:info
            "source address";
          tailf:cli-delete-when-empty;
          presence "true";
          container vlan {
            tailf:info
              "vlan specification";
            container dhcp-snooping {
              tailf:info
                "snooping enable vlan";
              tailf:cli-reset-container;
              tailf:cli-delete-when-empty;
              presence "true";
              leaf port-security {
                tailf:info
                  "port security";
                type empty;
              }
            }
          }
        }
      }
      container rip {
        tailf:info
          "Router Information Protocol";
        container send {
          tailf:info
            "advertisement transmission";
          leaf version {
            tailf:info
              "version control";
            type enumeration {
              enum "1" {
                tailf:info
                  "RIP version 1";
              }
              enum "2" {
                tailf:info
                  "RIP version 2";
              }
            }
          }
        }
        container receive {
          tailf:info
            "advertisement reception";
          leaf version {
            tailf:info
              "version control";
            type enumeration {
              enum "1" {
                tailf:info
                  "RIP version 1";
              }
              enum "2" {
                tailf:info
                  "RIP version 2";
              }
            }
          }
        }
        container authentication {
          tailf:info
            "Authentication control";
          leaf mode {
            tailf:info
              "Authentication mode";
            type enumeration {
              enum "md5" {
                tailf:info
                  "Keyed message digest";
              }
              enum "text" {
                tailf:info
                  "Clear text authentication";
              }
            }
          }
          leaf key-chain {
            tailf:info
              "Authentication key-chain";
            // NCS drop tailf-common:non-strict-leafref statement
            type string {
              tailf:info
                "LINE;;name of key-chain";
            }
          }
        }
      }
      leaf mask-reply {
        tailf:info
          "Enable sending ICMP Mask Reply messages";
        tailf:cli-full-command;
        type empty;
      }
      container bandwidth-percent {
        tailf:info
          "Set EIGRP bandwidth limit";
        list eigrp {
          tailf:info
            "Enhanced Interior Gateway Routing Protocol (EIGRP)";
          tailf:cli-suppress-mode;
          tailf:cli-delete-when-empty;
          tailf:cli-incomplete-command;
          key "as-number";
          leaf as-number {
            type uint16 {
              tailf:info
                "<1-65535>;;AS number";
            }
          }
          leaf percent {
            tailf:cli-drop-node-name;
            type uint32 {
              tailf:info
                "<1-999999>;;Maximum bandwidth percentage that EIGRP may use";
              range "1..999999";
            }
          }
        }
      }
      container next-hop-self {
        tailf:info
          "Configures EIGRP-IPv4 next-hop-self";
        container eigrp {
          tailf:info
            "Enhanced Interior Gateway Routing Protocol (EIGRP)";
          list no-list {
            tailf:info
              "'no ip next-hop-self eigrp' entry";
            tailf:cli-suppress-mode;
            tailf:cli-delete-when-empty;
            key "as-number";
            leaf as-number {
              type uint16 {
                tailf:info
                  "<1-65535>;;AS number";
                range "1..65535";
              }
            }
          }
        }
      }
      container lisp {
        tailf:info
          "Locator/ID Separation Protocol";
        container source-locator {
          tailf:info
            "Choose IP source address for LISP packets egressing this interface";
          uses ncs_rpc_notif_interface-name-grouping;
        }
      }
      container wccp {
        tailf:info
          "WCCP IPv4 interface commands";
        tailf:cli-diff-dependency "/ios:ip/wccp" {
          tailf:xpath-root 3;
        }
        uses ncs_rpc_notif_interface-ip-wccp-grouping;
        list vrf {
          tailf:info
            "Configure WCCP for a VRF";
          tailf:cli-suppress-mode;
          tailf:cli-delete-when-empty;
          tailf:cli-compact-syntax;
          tailf:cli-incomplete-command;
          key "name";
          leaf name {
            tailf:cli-diff-dependency "/ios:vrf/definition" {
              tailf:xpath-root 3;
            }
            type string {
              tailf:info
                "WORD;;VRF name";
            }
          }
          uses ncs_rpc_notif_interface-ip-wccp-grouping;
        }
      }
    }
    container ipv6 {
      tailf:info
        "IPv6 interface subcommands";
      container address {
        tailf:info
          "Configure IPv6 address on interface";
        choice address-choice {
          case autoconfig-case {
            container autoconfig {
              tailf:info
                "Obtain address using autoconfiguration";
              presence "true";
              leaf default {
                tailf:info
                  "Insert default route";
                type empty;
              }
            }
          }
          case dhcp-case {
            container dhcp {
              tailf:info
                "Obtain a ipv6 address using dhcp";
              tailf:cli-reset-container;
              tailf:cli-delete-when-empty;
              presence "true";
              leaf rapid-commit {
                tailf:info
                  "Enable Rapid-Commit";
                type empty;
              }
            }
          }
          case manual-case {
            list prefix-list {
              tailf:cli-drop-node-name;
              tailf:cli-suppress-mode;
              tailf:cli-delete-when-empty;
              key "prefix";
              leaf prefix {
                type union {
                  type ios:ipv6-prefix {
                    tailf:info
                      "X:X:X:X::X/<0-128>;;IPv6 prefix";
                  }
                  type inet:ipv6-address {
                    tailf:info
                      "X:X:X:X::X;;IPv6 link-local address";
                  }
                }
              }
              leaf link-local {
                tailf:info
                  "Use link-local address";
                tailf:cli-full-command;
                type empty;
              }
              leaf anycast {
                tailf:info
                  "Configure as an anycast";
                tailf:cli-full-command;
                type empty;
              }
              leaf eui-64 {
                tailf:info
                  "Use eui-64 interface identifier";
                tailf:cli-full-command;
                type empty;
              }
            }
          }
        }
      }
      leaf enable {
        tailf:info
          "Enable IPv6 on interface";
        type empty;
      }
      container unnumbered {
        tailf:info
          "Preferred interface for source address selection";
        uses ncs_rpc_notif_interface-name-grouping;
      }
      list traffic-filter {
        tailf:info
          "Access control list for packets";
        tailf:cli-suppress-mode;
        tailf:cli-delete-when-empty;
        tailf:cli-compact-syntax;
        tailf:cli-sequence-commands;
        key "direction";
        leaf direction {
          type enumeration {
            enum "in" {
              tailf:info
                "inbound packets";
            }
            enum "out" {
              tailf:info
                "outbound packets";
            }
          }
        }
        leaf access-list {
          tailf:cli-drop-node-name;
          tailf:cli-prefix-key;
          type string {
            tailf:info
              "WORD;;Access-list name";
          }
        }
      }
      container nd {
        tailf:info
          "IPv6 interface Neighbor Discovery subcommands";
        container dad {
          tailf:info
            "Duplicate Address Detection";
          leaf attempts {
            tailf:info
              "Set IPv6 Duplicate Address Detection Transmits";
            type uint16 {
              tailf:info
                "<0-600>;;Number of attempts";
              range "0..600";
            }
          }
        }
        leaf reachable-time {
          tailf:info
            "Set advertised reachability time";
          type uint32 {
            tailf:info
              "<0-3600000>;;Reachability time in milliseconds";
            range "0..3600000";
          }
        }
        container prefix {
          tailf:info
            "Configure IPv6 Routing Prefix Advertisement";
          list prefix-list {
            tailf:cli-drop-node-name;
            tailf:cli-suppress-mode;
            tailf:cli-delete-when-empty;
            tailf:cli-compact-syntax;
            tailf:cli-sequence-commands {
              tailf:cli-reset-all-siblings;
            }
            tailf:cli-incomplete-command;
            key "ipv6-prefix";
            leaf ipv6-prefix {
              type union {
                type ipv6-prefix {
                  tailf:info
                    "X:X:X:X::X/<0-128>;;IPv6 prefix x:x::y/<z>";
                }
                type enumeration {
                  enum "default" {
                    tailf:info
                      "Specify prefix default parameters";
                  }
                }
              }
            }
            choice advertise-choice {
              case no-advertise {
                leaf no-advertise {
                  tailf:info
                    "Do not advertise prefix";
                  tailf:cli-full-command;
                  type empty;
                }
              }
              case advertise {
                leaf valid-lifetime {
                  tailf:cli-drop-node-name;
                  tailf:cli-incomplete-command;
                  type union {
                    type enumeration {
                      enum "infinite" {
                        tailf:info
                          "Infinite Valid Lifetime";
                      }
                    }
                    type uint32 {
                      tailf:info
                        "<0-4294967295>;;Valid Lifetime (secs)";
                    }
                  }
                }
                leaf preferred-lifetime {
                  tailf:cli-drop-node-name;
                  type union {
                    type enumeration {
                      enum "infinite" {
                        tailf:info
                          "Infinite Preferred Lifetime";
                      }
                    }
                    type uint32 {
                      tailf:info
                        "<0-4294967295>;;Preferred Lifetime (secs)";
                    }
                  }
                }
                leaf off-link {
                  tailf:cli-break-sequence-commands;
                  tailf:info
                    "Prefix is offlink";
                  type empty;
                }
                leaf no-autoconfig {
                  tailf:info
                    "Do not use prefix for autoconfiguration";
                  type empty;
                }
                leaf no-rtr-address {
                  tailf:info
                    "Do not send full router address in prefix advert";
                  type empty;
                }
                leaf no-onlink {
                  tailf:info
                    "Do not use prefix for onlink determination";
                  type empty;
                }
              }
            }
          }
        }
        leaf managed-config-flag {
          tailf:info
            "Hosts should use DHCP for address config";
          type empty;
        }
        leaf other-config-flag {
          tailf:info
            "Hosts should use DHCP for non-address config";
          type empty;
        }
        container ra {
          tailf:info
            "Router Advertisement control";
          container suppress {
            tailf:info
              "Suppress IPv6 Router Advertisements";
            tailf:cli-delete-when-empty;
            presence "true";
            leaf all {
              tailf:info
                "Suppress all ipv6 Router advertisements";
              type empty;
            }
          }
          container interval {
            choice interval-choice {
              leaf seconds {
                tailf:cli-drop-node-name;
                type uint16 {
                  tailf:info
                    "<4-1800>;;RA Interval (sec)";
                  range "4..1800";
                }
              }
              leaf msec {
                tailf:info
                  "Interval in milliseconds";
                type uint32 {
                  tailf:info
                    "<70-1800000>;;RA Interval (msec)";
                  range "70..1800000";
                }
              }
            }
          }
          leaf lifetime {
            tailf:info
              "Set IPv6 Router Advertisement Lifetime";
            tailf:cli-full-command;
            type uint16 {
              tailf:info
                "<0-9000>;;RA Lifetime (seconds)";
              range "0..9000";
            }
          }
        }
        container raguard {
          tailf:info
            "apply the router advertisements (RA) guard feature";
          presence "true";
        }
        container autoconfig {
          tailf:info
            "Automatic Configuration";
          leaf prefix {
            tailf:info
              "Prefix";
            tailf:cli-full-command;
            type empty;
          }
          leaf default-route {
            tailf:info
              "Default Route";
            tailf:cli-full-command;
            type empty;
          }
        }
      }
      container mld {
        tailf:info
          "interface commands";
        leaf access-group {
          tailf:info
            "source, group membership access";
          type string {
            tailf:info
              "WORD;;Named access list specifying access group range";
          }
        }
      }
      leaf redirects {
        tailf:info
          "Enable sending of ICMP Redirect messages";
        tailf:cli-boolean-no;
        tailf:cli-full-command;
        type boolean;
        default "true";
      }
      leaf unreachables {
        tailf:info
          "Enable sending of ICMP Unreachable messages";
        tailf:cli-boolean-no;
        tailf:cli-full-command;
        type boolean;
        default "true";
      }
      container tcp {
        tailf:info
          "TCP interface commands";
        leaf adjust-mss {
          tailf:info
            "Adjust the mss of IPV6 transit packets";
          type uint16 {
            tailf:info
              "<40-1454>;;Maximum segment size in bytes";
            range "40..1454";
          }
        }
      }
      container router {
        tailf:info
          "IPv6 Router interface commands";
        container isis {
          tailf:info
            "isis  IS-IS Routing for IPv6";
          tailf:cli-delete-when-empty;
          presence "true";
          leaf tag {
            tailf:cli-drop-node-name;
            type string {
              tailf:info
                "WORD;;Routing process tag";
            }
          }
        }
      }
      container ospf {
        tailf:info
          "OSPF interface commands";
        leaf network {
          tailf:info
            "Network type";
          tailf:cli-full-command;
          type enumeration {
            enum "broadcast" {
              tailf:info
                "Specify OSPF broadcast multi-access network";
            }
            enum "non-broadcast" {
              tailf:info
                "Specify OSPF NBMA network";
            }
            enum "point-to-multipoint" {
              tailf:info
                "Specify OSPF point-to-multipoint network";
            }
            enum "point-to-point" {
              tailf:info
                "Specify OSPF point-to-point network";
            }
          }
        }
        list process {
          tailf:cli-drop-node-name;
          tailf:cli-suppress-mode;
          tailf:cli-delete-when-empty;
          tailf:cli-compact-syntax;
          tailf:cli-sequence-commands {
            tailf:cli-reset-siblings;
          }
          key "id";
          leaf id {
            type uint16 {
              tailf:info
                "<1-65535>;;Process ID";
              range "1..65535";
            }
          }
          leaf area {
            tailf:info
              "Set the OSPF area ID";
            type union {
              type uint32 {
                tailf:info
                  "<0-4294967295>;;OSPF area ID as a decimal value";
                range "0..4294967295";
              }
              type inet:ipv4-address {
                tailf:info
                  "A.B.C.D;;OSPF area ID in IP address format";
              }
            }
          }
          leaf instance {
            tailf:info
              "Set the OSPF instance";
            type union {
              type uint8 {
                tailf:info
                  "<0-31>;;Instance ID";
                range "0..31";
              }
              type uint8 {
                tailf:info
                  "<32-255>;;Instance ID (DEPRECATED!)";
                range "32..255";
              }
            }
          }
        }
        container bfd {
          tailf:info
            "Enable BFD on this interface";
          presence "true";
          leaf disable {
            tailf:info
              "Disable BFD on this interface";
            type empty;
          }
        }
        leaf cost {
          tailf:info
            "Route cost of this interface";
          type uint16 {
            tailf:info
              "<1-65535>;;Route cost of this interface";
            range "1..65535";
          }
        }
        container database-filter {
          tailf:info
            "Filter OSPF LSA during synchronization and flooding";
          choice database {
            leaf all {
              tailf:info
                "Filter all LSA";
              type enumeration {
                enum "out" {
                  tailf:info
                    "Outgoing LSA";
                }
              }
            }
            leaf disable {
              tailf:info
                "Disable LSA Filter on this interface";
              type empty;
            }
          }
        }
        leaf dead-interval {
          tailf:info
            "Interval after which a neighbor is declared dead";
          type uint16 {
            tailf:info
              "<1-65535>;;Seconds";
            range "1..65535";
          }
        }
        container demand-circuit {
          tailf:info
            "OSPF demand circuit";
          presence "true";
          leaf disable {
            tailf:info
              "Disable demand circuit on this interface";
            type empty;
          }
        }
        container flood-reduction {
          tailf:info
            "OSPF Flood Reduction";
          presence "true";
          leaf disable {
            tailf:info
              "Disable Flood Reduction on this interface";
            type empty;
          }
        }
        leaf hello-interval {
          tailf:info
            "Time between HELLO packets";
          type uint16 {
            tailf:info
              "<1-65535>;;Seconds";
            range "1..65535";
          }
        }
        container mtu-ignore {
          tailf:info
            "Ignores the MTU in DBD packets";
          presence "true";
          leaf disable {
            tailf:info
              "Disable Ingore MTU on this interface";
            type empty;
          }
        }
        leaf priority {
          tailf:info
            "Router priority";
          type uint16 {
            tailf:info
              "<0-255>;;Priority";
            range "0..255";
          }
        }
        leaf retransmit-interval {
          tailf:info
            "Time between retransmitting lost link state advertisements";
          type uint16 {
            tailf:info
              "<1-65535>;;Seconds";
            range "1..65535";
          }
        }
        leaf transmit-delay {
          tailf:info
            "Link state transmit delay";
          type uint16 {
            tailf:info
              "<1-65535>;;Seconds";
            range "1..65535";
          }
        }
      }
      leaf-list eigrp {
        tailf:cli-list-syntax;
        tailf:cli-full-command;
        type uint16 {
          tailf:info
            "<1-65535>;;AS number";
          range "1..65535";
        }
      }
      leaf mtu {
        tailf:info
          "Set IPv6 Maximum Transmission Unit";
        type uint16 {
          tailf:info
            "<1280-9198>;;MTU (bytes)";
          range "1280..9198";
        }
      }
      container crypto {
        tailf:info
          "Encryption/Decryption commands";
        container map {
          tailf:info
            "Assign a Crypto Map";
          tailf:cli-compact-syntax;
          tailf:cli-sequence-commands {
            tailf:cli-reset-siblings;
          }
          tailf:cli-diff-dependency "/ios:crypto/map" {
            tailf:xpath-root 3;
          }
          leaf map-name {
            tailf:cli-drop-node-name;
            // NCS drop tailf-common:non-strict-leafref statement
            type string {
              tailf:info
                "WORD;;Crypto Map tag";
            }
          }
          leaf redundancy {
            tailf:info
              "enable redundancy";
            type string {
              tailf:info
                "WORD;;Name of IP Redundancy Group";
            }
          }
          leaf stateful {
            tailf:info
              "enable stateful failover";
            when "../redundancy" {
              tailf:xpath-root 3;
              tailf:dependency "../redundancy";
            }
            type empty;
          }
        }
      }
      container hold-time {
        tailf:info
          "Configures EIGRP-IPv6 hold time";
        list eigrp {
          tailf:info
            "Enhanced Interior Gateway Routing Protocol (EIGRP)";
          tailf:cli-suppress-mode;
          tailf:cli-delete-when-empty;
          key "as-no";
          leaf as-no {
            type uint16 {
              tailf:info
                "<1-65535>;;AS number";
              range "1..65535";
            }
          }
          leaf seconds {
            tailf:cli-drop-node-name;
            type uint16 {
              tailf:info
                "<1-65535>;;Seconds before neighbor is considered down";
              range "1..65535";
            }
          }
        }
      }
      container hello-interval {
        tailf:info
          "Configures EIGRP-IPv6 hello interval";
        list eigrp {
          tailf:info
            "Enhanced Interior Gateway Routing Protocol (EIGRP)";
          tailf:cli-suppress-mode;
          tailf:cli-delete-when-empty;
          key "as-no";
          leaf as-no {
            type uint16 {
              tailf:info
                "<1-65535>;;AS number";
              range "1..65535";
            }
          }
          leaf seconds {
            tailf:cli-drop-node-name;
            type uint16 {
              tailf:info
                "<1-65535>;;Seconds between hello transmission";
              range "1..65535";
            }
          }
        }
      }
      container verify {
        tailf:info
          "Enable per packet validation";
        container unicast {
          tailf:info
            "Enable per packet validation for unicast";
          container source {
            tailf:info
              "Validation of source address";
            leaf reachable-via {
              tailf:info
                "Specify reachability check to apply to the source address";
              type enumeration {
                enum "any" {
                  tailf:info
                    "Source is reachable via any interface";
                }
                enum "rx" {
                  tailf:info
                    "Source is reachable via interface on which packet was received";
                }
              }
            }
          }
          container reverse-path {
            tailf:info
              "Reverse path validation of source address (old command format)";
            tailf:cli-delete-when-empty;
            presence "true";
            leaf access-list {
              tailf:cli-drop-node-name;
              type string {
                tailf:info
                  "WORD;;Access-list name";
              }
            }
          }
        }
      }
      container dhcp {
        tailf:info
          "IPv6 DHCP interface subcommands";
        container relay {
          tailf:info
            "Act as an IPv6 DHCP relay agent";
          list destination {
            tailf:info
              "Configure relay destination";
            tailf:cli-suppress-mode;
            tailf:cli-delete-when-empty;
            tailf:cli-compact-syntax;
            tailf:cli-sequence-commands {
              tailf:cli-reset-siblings;
            }
            key "ipv6-address";
            leaf ipv6-address {
              type inet:ipv6-address {
                tailf:info
                  "X:X:X:X::X;;IPv6 address";
              }
            }
            leaf source-address {
              tailf:info
                "Configure source address to use for relay-forward";
              type inet:ipv6-address {
                tailf:info
                  "X:X:X:X::X;;IPv6 src address";
              }
            }
            leaf link-address {
              tailf:info
                "Configure link-address to use for relay-forward";
              type inet:ipv6-address {
                tailf:info
                  "X:X:X:X::X;;IPv6 link address";
              }
            }
          }
          container source-interface {
            tailf:info
              "Set source interface for relayed messages";
            uses ncs_rpc_notif_interface-name-grouping;
          }
        }
        container client {
          tailf:info
            "Act as an IPv6 DHCP client";
          container information {
            tailf:info
              "Configure information refresh option";
            container refresh {
              tailf:info
                "Configure information refresh parameters";
              leaf minimum {
                tailf:info
                  "Minimum information refresh time";
                type uint16 {
                  tailf:info
                    "<60-3600>;;Seconds";
                  range "60..3600";
                }
              }
            }
          }
        }
      }
      container nhrp {
        tailf:info
          "NHRP interface subcommands";
        container map {
          tailf:info
            "Map dest IPv6 address to NBMA address";
          list map-list {
            tailf:cli-drop-node-name;
            tailf:cli-suppress-mode;
            tailf:cli-delete-when-empty;
            tailf:cli-incomplete-command;
            key "ipv6-address";
            leaf ipv6-address {
              tailf:cli-drop-node-name;
              type ipv6-prefix {
                tailf:info
                  "X:X:X:X::X/<0-128>;;IPv6 address/mask of destination";
              }
            }
            leaf nbma-address {
              tailf:cli-drop-node-name;
              type union {
                type inet:ipv4-address {
                  tailf:info
                    "A.B.C.D;;IP NBMA address";
                }
                type inet:ipv6-address {
                  tailf:info
                    "X:X:X:X::X;;IPv6 NBMA address";
                }
              }
            }
          }
          container multicast {
            tailf:info
              "Use this NBMA mapping for broadcasts/multicasts";
            leaf dynamic {
              tailf:info
                "Dynamically learn destinations from client registrations on hub";
              type empty;
            }
            list multicast-list {
              tailf:cli-drop-node-name;
              tailf:cli-suppress-mode;
              tailf:cli-delete-when-empty;
              key "nbma-address";
              leaf nbma-address {
                type union {
                  type inet:ipv4-address {
                    tailf:info
                      "A.B.C.D;;IP NBMA address";
                  }
                  type inet:ipv6-address {
                    tailf:info
                      "X:X:X:X::X;;IPv6 NBMA address";
                  }
                }
              }
            }
          }
        }
        leaf network-id {
          tailf:info
            "NBMA network identifier";
          type uint32 {
            tailf:info
              "<1-4294967295>;;Network identifier";
            range "1..4294967295";
          }
        }
        leaf holdtime {
          tailf:info
            "Advertised holdtime";
          type uint16 {
            tailf:info
              "<1-65535>;;Number of seconds";
            range "1..65535";
          }
        }
        container nhs {
          tailf:info
            "Specify a next hop server";
          list nhs-list {
            tailf:cli-drop-node-name;
            tailf:cli-suppress-mode;
            tailf:cli-delete-when-empty;
            tailf:cli-compact-syntax;
            key "nhs-address";
            leaf nhs-address {
              type inet:ipv6-address {
                tailf:info
                  "X:X:X:X::X;;Protocol IPv6 address of NHS";
              }
            }
            leaf nbma {
              tailf:info
                "NBMA of NHS";
              type union {
                type inet:ipv4-address {
                  tailf:info
                    "A.B.C.D;;IPv4 address";
                }
                type inet:ipv6-address {
                  tailf:info
                    "X:X:X:X::X;;IPv6 address";
                }
                type string {
                  tailf:info
                    "WORD;;NHS FQDN string";
                }
              }
            }
            leaf multicast {
              when "../nbma" {
                tailf:xpath-root 3;
                tailf:dependency "../nbma";
              }
              tailf:info
                "Use this NBMA mapping for broadcasts/multicasts";
              type empty;
            }
          }
        }
        container server-only {
          tailf:info
            "Disable NHRP requests";
          tailf:cli-reset-container;
          tailf:cli-delete-when-empty;
          presence "true";
          leaf non-caching {
            tailf:info
              "Do not create NHRP cache entries";
            type empty;
          }
        }
        container registration {
          tailf:info
            "Settings for registration packets.";
          leaf no-unique {
            tailf:info
              "Do not set the 'Unique' flag in registration requests.";
            type empty;
          }
          leaf timeout {
            tailf:info
              "Time between periodic Registration messages";
            type uint16 {
              tailf:info
                "<1-65535>;;Number of seconds";
              range "1..65535";
            }
          }
        }
        container shortcut {
          tailf:info
            "Enable shortcut switching";
          presence "true";
        }
        container redirect {
          tailf:info
            "Enable NHRP redirect traffic indication";
          tailf:cli-delete-when-empty;
          presence "true";
          leaf timeout {
            tailf:info
              "Specify interval over which to throttle";
            type uint8 {
              tailf:info
                "<2-30>;;Interval in seconds";
              range "2..30";
            }
          }
        }
      }
      container summary-address {
        tailf:info
          "Perform address summarization";
        tailf:cli-diff-dependency "/ios:ipv6/unicast-routing" {
          tailf:xpath-root 3;
        }
        list eigrp {
          tailf:info
            "Enhanced Interior Gateway Routing Protocol (EIGRP)";
          tailf:cli-delete-when-empty;
          tailf:cli-suppress-mode;
          key "as-no ipv6-address";
          leaf as-no {
            type uint16 {
              tailf:info
                "<1-65535>;;Autonomous system number";
              range "1..65535";
            }
          }
          leaf ipv6-address {
            type ios:ipv6-prefix {
              tailf:info
                "X:X:X:X::X/<0-128>;;IPv6 prefix";
            }
          }
          leaf distance {
            tailf:cli-drop-node-name;
            type uint8 {
              tailf:info
                "<0-255>;;Administrative distance";
              range "0..255";
            }
          }
        }
      }
      list rip {
        tailf:info
          "Configure RIP routing protocol";
        tailf:cli-suppress-mode;
        tailf:cli-delete-when-empty;
        tailf:cli-incomplete-command;
        key "id";
        leaf id {
          type string {
            tailf:info
              "WORD;;User selected string identifying this RIP process";
          }
        }
        leaf enable {
          tailf:info
            "Enable/disable RIP routing";
          type empty;
        }
        container default-information {
          tailf:info
            "Configure handling of default route";
          tailf:cli-compact-syntax;
          tailf:cli-sequence-commands;
          leaf default-route {
            tailf:cli-drop-node-name;
            tailf:cli-reset-container;
            type enumeration {
              enum "only" {
                tailf:info
                  "Advertise only the default route";
              }
              enum "originate" {
                tailf:info
                  "Originate the default route";
              }
            }
          }
          leaf metric {
            tailf:info
              "Default route metric";
            type uint8 {
              tailf:info
                "<1-15>;;Metric value";
              range "1..15";
            }
          }
        }
      }
      container wccp {
        tailf:info
          "WCCP IPv4 interface commands";
        tailf:cli-diff-dependency "/ios:ipv6/wccp" {
          tailf:xpath-root 3;
        }
        uses ncs_rpc_notif_interface-ip-wccp-grouping;
        list vrf {
          tailf:info
            "Configure WCCP for a VRF";
          tailf:cli-suppress-mode;
          tailf:cli-delete-when-empty;
          tailf:cli-compact-syntax;
          tailf:cli-incomplete-command;
          key "name";
          leaf name {
            tailf:cli-diff-dependency "/ios:vrf/definition" {
              tailf:xpath-root 3;
            }
            type string {
              tailf:info
                "WORD;;VRF name";
            }
          }
          uses ncs_rpc_notif_interface-ip-wccp-grouping;
        }
      }
      container policy {
        tailf:info
          "Enable IPv6 policy routing";
        leaf route-map {
          tailf:info
            "IPv6 policy-based-routing routemap";
          type string {
            tailf:info
              "WORD;;Route-map name";
          }
        }
      }
    }
    container ospfv3 {
      tailf:info
        "OSPFv3 interface commands";
      tailf:cli-diff-dependency "/ios:ipv6/unicast-routing" {
        tailf:xpath-root 3;
      }
      uses ncs_rpc_notif_interface-ospfv3-grouping;
      list ospfv3-list {
        tailf:cli-drop-node-name;
        tailf:cli-suppress-mode;
        tailf:cli-delete-when-empty;
        tailf:cli-incomplete-command;
        key "id";
        leaf id {
          tailf:cli-suppress-range;
          type uint16 {
            tailf:info
              "<1-65535>;;Process ID";
            range "1..65535";
          }
        }
        uses ncs_rpc_notif_interface-ospfv3-grouping;
        container ipv4 {
          tailf:info
            "Specify parameters for IPv4";
          uses ncs_rpc_notif_interface-ospfv3-grouping;
        }
        container ipv6 {
          tailf:info
            "Specify parameters for IPv6";
          uses ncs_rpc_notif_interface-ospfv3-grouping;
        }
      }
    }
    container nhrp {
      tailf:info
        "NHRP Interface commands";
      leaf group {
        tailf:info
          "NHRP group name";
        tailf:cli-full-command;
        type string {
          tailf:info
            "WORD;;group name string";
        }
      }
      leaf route-watch {
        tailf:cli-boolean-no;
        tailf:cli-full-command;
        tailf:cli-diff-dependency "../../ip/nhrp" {
          tailf:xpath-root 3;
        }
        type boolean;
        default "true";
      }
    }
    container if-state {
      tailf:info
        "Allow applications to control interface state";
      leaf nhrp {
        tailf:info
          "Allow NHRP to control interface state";
        type empty;
      }
    }
    leaf delay {
      tailf:info
        "Specify interface throughput delay";
      type uint32 {
        tailf:info
          "<1-16777215>;;Throughput delay (tens of microseconds)";
      }
    }
    leaf load-interval {
      tailf:info
        "Specify interval for load calculation for an interface";
      type uint16 {
        tailf:info
          "<30-600>;;Load interval delay in seconds";
        range "0..600";
      }
    }
    container logging {
      tailf:info
        "Configure logging for interface";
      container event {
        tailf:info
          "Interface events";
        leaf link-status {
          tailf:info
            "UPDOWN and CHANGE messages";
          tailf:cli-boolean-no;
          type boolean;
          default "true";
        }
        leaf trunk-status {
          tailf:info
            "TRUNK status messages";
          tailf:cli-full-command;
          type empty;
        }
        leaf bundle-status {
          tailf:info
            "BUNDLE/UNBUNDLE messages";
          tailf:cli-full-command;
          type empty;
        }
        leaf subif-link-status {
          tailf:info
            "Sub-interface UPDOWN and CHANGE messages";
          tailf:cli-full-command;
          type empty;
        }
        container spanning-tree {
          tailf:info
            "Spanning-tree Interface events";
          leaf status {
            tailf:info
              "Spanning-tree state change messages";
            type empty;
          }
        }
        leaf nfas-status {
          tailf:info
            "NFAS D-channel status messages";
          tailf:cli-full-command;
          type empty;
        }
      }
    }
    leaf max-reserved-bandwidth {
      tailf:info
        "Maximum Reservable Bandwidth on an Interface";
      tailf:cli-full-command;
      type uint8 {
        tailf:info
          "<1-100>;;Max. reservable bandwidth as percent of interface bandwidth";
        range "1..100";
      }
    }
    container mls {
      tailf:info
        "mls sub/interface commands";
      container netflow {
        tailf:info
          "netflow command keyword";
        leaf sampling {
          tailf:info
            "sampling keyword";
          type empty;
        }
      }
      container qos {
        tailf:info
          "qos command keyword";
        container cos {
          tailf:info
            "Configure interface COS parameters";
          leaf cos-value {
            tailf:cli-drop-node-name;
            type uint8 {
              tailf:info
                "<0-7>;;Class of service value between 0 and 7";
              range "0..7";
            }
          }
          leaf override {
            tailf:info
              "Force default COS on all packets";
            type empty;
          }
        }
        leaf channel-consistency {
          tailf:info
            "enable or disable qos consistency checks";
          tailf:cli-boolean-no;
          tailf:cli-full-command;
          type boolean;
          default "true";
        }
        container trust {
          tailf:info
            "Configure trust state of interface";
          container device {
            tailf:info
              "trusted device class";
            leaf cisco-phone {
              tailf:info
                "Cisco IP Phone";
              type empty;
            }
          }
          choice trust-choice {
            container cos {
              tailf:info
                "Classify by packet COS";
              tailf:cli-reset-container;
              tailf:cli-delete-when-empty;
              tailf:cli-diff-dependency "../../vlan-based" {
                tailf:xpath-root 3;
                tailf:cli-trigger-on-set;
              }
              presence "true";
              container pass-through {
                tailf:info
                  "cos pass-through mode";
                leaf dscp {
                  tailf:info
                    "transmit without dscp modification";
                  type empty;
                }
              }
            }
            container dscp {
              tailf:info
                "Classify by packet DSCP";
              tailf:cli-diff-dependency "../../vlan-based" {
                tailf:xpath-root 3;
                tailf:cli-trigger-on-set;
              }
              presence "true";
              container pass-through {
                tailf:info
                  "dscp pass-through mode";
                leaf cos {
                  tailf:info
                    "transmit without cos modification";
                  type empty;
                }
              }
            }
            container ip-precedence {
              tailf:info
                "Classify by packet IP precedence";
              tailf:cli-diff-dependency "../../vlan-based" {
                tailf:xpath-root 3;
                tailf:cli-trigger-on-set;
              }
              presence "true";
            }
          }
        }
        container monitor {
          tailf:info
            "Collect QoS statistics";
          leaf-list dscp {
            tailf:info
              "Collect DSCP statistics";
            tailf:cli-flat-list-syntax;
            tailf:meta-data "max-values" {
              tailf:meta-value "4 :: 8";
            }
            max-elements 15;
            type uint8 {
              tailf:info
                "<0-63>;;dscp (up to 15 values total)";
              range "0..63";
            }
          }
        }
        leaf vlan-based {
          tailf:info
            "vlan-based keyword";
          tailf:cli-full-command;
          tailf:cli-diff-dependency "../../../service-policy/input" {
            tailf:xpath-root 3;
            tailf:cli-trigger-on-set;
          }
          tailf:cli-diff-dependency "../../../service-policy/output" {
            tailf:xpath-root 3;
            tailf:cli-trigger-on-set;
          }
          type empty;
        }
        leaf bridged {
          tailf:info
            "bridged keyword";
          tailf:cli-full-command;
          type empty;
        }
      }
    }
    container auto {
      tailf:info
        "Configure Automation";
      container qos {
        tailf:info
          "Configure AutoQoS";
        container voip {
          tailf:info
            "Configure AutoQoS for VoIP";
          leaf cisco-phone {
            tailf:info
              "Trust the QoS marking of Cisco IP Phone";
            type empty;
          }
          leaf trust {
            tailf:info
              "Trust the COS marking";
            type empty;
          }
        }
      }
    }
    leaf mtu {
      tailf:info
        "Set the interface Maximum Transmission Unit (MTU)";
      tailf:cli-full-command;
      type uint16 {
        tailf:info
          "<64-18000>;;MTU size in bytes";
        range "64..18000";
      }
    }
    container ntp {
      tailf:info
        "Configure NTP";
      container broadcast {
        tailf:info
          "Configure NTP broadcast service";
        presence "true";
        container client {
          tailf:info
            "Listen to NTP broadcasts";
          tailf:cli-full-command;
          presence "true";
        }
        list destination {
          tailf:info
            "Configure broadcast destination address";
          tailf:cli-suppress-mode;
          tailf:cli-delete-when-empty;
          tailf:cli-compact-syntax;
          tailf:cli-reset-container;
          key "address";
          leaf version {
            tailf:info
              "Configure NTP version";
            type uint8 {
              tailf:info
                "<1-4>;;NTP version number";
              range "1..4";
            }
          }
          leaf key {
            tailf:info
              "Configure broadcast authentication key";
            type uint32 {
              tailf:info
                "<0-4294967295>;;Broadcast key number";
            }
          }
          leaf address {
            type inet:ipv4-address {
              tailf:info
                "A.B.C.D;;Destination broadcast IP address";
            }
          }
        }
        container version-key {
          tailf:cli-drop-node-name;
          tailf:cli-compact-syntax;
          tailf:cli-reset-container;
          leaf version {
            tailf:info
              "Configure NTP version";
            type uint8 {
              tailf:info
                "<1-4>;;NTP version number";
              range "1..4";
            }
          }
          leaf key {
            tailf:info
              "Configure broadcast authentication key";
            type uint32 {
              tailf:info
                "<0-4294967295>;;Broadcast key number";
            }
          }
        }
      }
      leaf disable {
        tailf:info
          "Disable NTP traffic (both IP and IPv6)";
        tailf:cli-full-command;
        type empty;
      }
      container multicast {
        tailf:info
          "Configure NTP multicast service";
        tailf:cli-display-separated;
        tailf:cli-compact-syntax;
        presence "true";
        list address-list {
          tailf:cli-drop-node-name;
          tailf:cli-suppress-mode;
          tailf:cli-delete-when-empty;
          tailf:cli-compact-syntax;
          key "group-address";
          leaf group-address {
            type union {
              type inet:ipv4-address {
                tailf:info
                  "A.B.C.D;;Multicast group IP address";
              }
              type inet:ipv6-address {
                tailf:info
                  "X:X:X:X::X;;Multicast group IPv6 address";
              }
            }
          }
          leaf version {
            tailf:info
              "Configure NTP version";
            type uint8 {
              tailf:info
                "<1-4>;;NTP version number";
              range "1..4";
            }
          }
          leaf key {
            tailf:info
              "Configure multicast authentication key";
            type uint32 {
              tailf:info
                "<0-4294967295>;;Multicast key number";
            }
          }
          leaf ttl {
            tailf:info
              "TTL of the multicast packet";
            type uint8 {
              tailf:info
                "<1-255>;;TTL";
              range "1..255";
            }
          }
        }
        leaf version {
          tailf:info
            "Configure NTP version";
          type uint8 {
            tailf:info
              "<1-4>;;NTP version number";
            range "1..4";
          }
        }
        leaf key {
          tailf:info
            "Configure multicast authentication key";
          type uint32 {
            tailf:info
              "<0-4294967295>;;Multicast key number";
          }
        }
        leaf ttl {
          tailf:info
            "TTL of the multicast packet";
          type uint8 {
            tailf:info
              "<1-255>;;TTL";
            range "1..255";
          }
        }
        container client-list {
          tailf:cli-drop-node-name;
          leaf-list client {
            tailf:info
              "Listen to NTP multicasts";
            tailf:cli-list-syntax;
            tailf:cli-suppress-list-no;
            tailf:cli-incomplete-no;
            type union {
              type inet:ipv4-address {
                tailf:info
                  "A.B.C.D;;Multicast client IP address";
              }
              type inet:ipv6-address {
                tailf:info
                  "X:X:X:X::X;;Multicast client IPv6 address";
              }
            }
          }
        }
        leaf client {
          tailf:info
            "Listen to NTP multicasts";
          tailf:cli-full-command;
          type empty;
        }
      }
    }
    container power {
      tailf:info
        "Power configuration";
      container inline {
        tailf:info
          "Inline power configuration";
        tailf:cli-compact-syntax;
        tailf:cli-sequence-commands {
          tailf:cli-reset-siblings;
        }
        leaf consumption {
          tailf:info
            "Configure the inline device consumption";
          tailf:cli-optional-in-sequence;
          tailf:cli-full-command;
          type uint16 {
            tailf:info
              "<4000-15400>;;milli-watts";
            range "4000..15400";
          }
        }
        leaf mode {
          tailf:cli-drop-node-name;
          type enumeration {
            enum "auto" {
              tailf:info
                "Automatically detect and power inline devices";
            }
            enum "never" {
              tailf:info
                "Never apply inline power";
            }
            enum "static" {
              tailf:info
                "High priority inline power interface";
            }
          }
          default "auto";
        }
        leaf max {
          tailf:info
            "Maximum power allowed on this interface";
          when "../mode != 'never'" {
            tailf:xpath-root 3;
            tailf:dependency "../mode";
          }
          type uint16 {
            tailf:info
              "<4000-15400>;;milli-watts";
            range "4000..15400";
          }
        }
      }
      container client {
        tailf:info
          "Client radio requested maximum transmitter power level";
        leaf local {
          tailf:info
            "Set power to Access Point local power";
          type empty;
        }
      }
    }
    list rate-limit {
      tailf:info
        "Rate Limit";
      tailf:cli-suppress-mode;
      tailf:cli-delete-when-empty;
      tailf:cli-compact-syntax;
      key "dir bps bc be conform-action exceed-action";
      leaf dir {
        type enumeration {
          enum "input" {
            tailf:info
              "Rate limit on input";
          }
          enum "output" {
            tailf:info
              "Rate limit on output";
          }
        }
      }
      leaf dscp {
        tailf:info
          "Match dscp value";
        type uint8 {
          tailf:info
            "<0-63>;;dscp";
          range "0..63";
        }
      }
      leaf bps {
        tailf:info
          "<8000-2000000000>;;Bits per second";
        type police-bps-type;
      }
      leaf bc {
        type uint32 {
          tailf:info
            "<1000-512000000>;;Normal burst bytes";
          range "1000..512000000";
        }
      }
      leaf be {
        type uint32 {
          tailf:info
            "<2000-1024000000>;;Maximum burst bytes";
          range "2000..1024000000";
        }
      }
      leaf conform-action {
        tailf:cli-expose-key-name;
        type enumeration {
          enum "transmit";
        }
      }
      leaf exceed-action {
        tailf:cli-expose-key-name;
        type enumeration {
          enum "drop";
        }
      }
    }
    container service-policy {
      tailf:info
        "Configure QoS Service Policy";
      leaf history {
        tailf:cli-full-command;
        tailf:info
          "Keep history of QoS metrics";
        type empty;
      }
      uses ncs_rpc_notif_service-policy-grouping;
      container type {
        tailf:info
          "Configure CPL Service Policy";
        container control {
          tailf:info
            "Apply a control policy to the interface";
          leaf subscriber {
            tailf:info
              "Apply a subscriber control policy to the interfac";
            // NCS drop tailf-common:non-strict-leafref statement
            type string {
              tailf:info
                "WORD;;policy-map name";
            }
          }
        }
        container performance-monitor {
          tailf:info
            "Configure media monitor service-policy type";
          uses ncs_rpc_notif_service-policy-grouping;
        }
      }
    }
    container service-insertion {
      tailf:info
        "Service-insertion AppNav Controller";
      leaf waas {
        tailf:info
          "Enable Service-insertion";
        type empty;
      }
    }
    container service-module {
      tailf:info
        "Configure service module";
      container t1 {
        tailf:info
          "Configure Serial T1 parameters";
        tailf:cli-compact-syntax;
        tailf:cli-sequence-commands;
        leaf-list timeslots {
          tailf:info
            "List of timeslots in the T1 group";
          tailf:cli-range-list-syntax;
          tailf:cli-replace-all;
          type uint8 {
            tailf:info
              "<1-24>;List of timeslots";
            range "1..24";
          }
        }
        leaf speed {
          type enumeration {
            enum "56";
            enum "64";
          }
        }
      }
    }
    leaf group {
      tailf:info
        "Add this subinterface to a group";
      tailf:cli-full-command;
      tailf:cli-diff-dependency "/ios:service-group" {
        tailf:xpath-root 3;
      }
      type uint16 {
        tailf:info
          "<1-65532>;;Group number";
        range "1..65532";
      }
    }
    leaf shutdown {
      tailf:info
        "Shutdown the selected interface";
      tailf:cli-show-no;
      tailf:cli-full-command;
      type empty;
    }
    container standby {
      tailf:info
        "HSRP interface configuration commands";
      leaf version {
        tailf:info
          "HSRP version";
        tailf:cli-full-command;
        type enumeration {
          tailf:info
            "<1-2>;;Version number";
          enum "1";
          enum "2";
        }
      }
      leaf bfd {
        tailf:info
          "Enable HSRP BFD";
        tailf:cli-boolean-no;
        tailf:cli-full-command;
        type boolean;
        default "true";
      }
      container delay {
        tailf:info
          "HSRP initialisation delay";
        tailf:cli-compact-syntax;
        leaf minimum {
          tailf:info
            "Minimum delay";
          type uint16 {
            tailf:info
              "<0-10000>;;Delay in seconds";
            range "0..10000";
          }
        }
        leaf reload {
          tailf:info
            "Delay after reload";
          type uint16 {
            tailf:info
              "<0-10000>;;Delay in seconds";
            range "0..10000";
          }
        }
      }
      leaf mac-refresh {
        tailf:info
          "Refresh MAC cache on switch by periodically sending packet from virtual mac address";
        type uint8 {
          tailf:info
            "<0-255>;;Interval to refresh MAC cache";
          range "0..255";
        }
      }
      container use-bia {
        tailf:info
          "HSRP uses interface's burned in address";
        presence "true";
        container scope {
          tailf:info
            "Specify the scope of use-bia";
          leaf interface {
            tailf:info
              "Use-bia applies to all groups on this interface or sub-interface";
            type empty;
          }
        }
      }
      list standby-list {
        tailf:cli-drop-node-name;
        tailf:cli-suppress-mode;
        tailf:cli-delete-when-empty;
        tailf:cli-incomplete-command;
        tailf:cli-diff-dependency "../version" {
          tailf:xpath-root 3;
        }
        key "group-number";
        leaf group-number {
          tailf:key-default "0";
          tailf:cli-suppress-range;
          type uint16 {
            tailf:info
              "<0-4095>;;group number";
          }
        }
        container authentication {
          tailf:info
            "Authentication";
          choice auth {
            leaf word {
              tailf:cli-drop-node-name;
              tailf:cli-disallow-value "md5|text";
              type string {
                tailf:info
                  "WORD;;Plain text authentication string (8 chars max)";
              }
            }
            container md5 {
              tailf:info
                "Use MD5 authentication";
              leaf key-chain {
                tailf:info
                  "Set key chain";
                type string {
                  tailf:info
                    "WORD;;Name of key-chain";
                }
              }
              container key-string {
                tailf:info
                  "Set key string";
                tailf:cli-flatten-container;
                tailf:cli-compact-syntax;
                tailf:cli-sequence-commands;
                uses ncs_rpc_notif_password-grouping;
                leaf timeout {
                  tailf:info
                    "Set timeout";
                  type uint16 {
                    tailf:info
                      "<0-32767>;;Timeout until only accepting new key (seconds)";
                    range "0..32767";
                  }
                }
              }
            }
            leaf text {
              tailf:info
                "Plain text authentication";
              type string {
                tailf:info
                  "WORD;;Plain text authentication string (8 chars max)";
              }
            }
          }
        }
        leaf follow {
          tailf:info
            "Name of HSRP group to follow";
          type string {
            tailf:info
              "WORD;;name string (25 chars. max)";
          }
        }
        container ip {
          tailf:info
            "Enable HSRP and set the virtual IP address";
          tailf:cli-compact-syntax;
          tailf:cli-sequence-commands;
          tailf:cli-delete-when-empty;
          presence "true";
          leaf address {
            tailf:cli-drop-node-name;
            tailf:cli-diff-dependency "../../../../ip-vrf/ip/vrf/forwarding" {
              tailf:xpath-root 3;
              tailf:cli-trigger-on-set;
            }
            type inet:ipv4-address {
              tailf:info
                "A.B.C.D;;Virtual IP address";
            }
          }
          leaf secondary {
            tailf:info
              "Make this IP address a secondary virtual IP address";
            type empty;
          }
        }
        leaf ipv6 {
          tailf:info
            "Enable HSRP IPv6";
          type union {
            type inet:ipv6-address {
              tailf:info
                "X:X:X:X::X;;IPv6 link-local address";
            }
            type ios:ipv6-prefix;
            type enumeration {
              enum "autoconfig" {
                tailf:info
                  "Obtain address using autoconfiguration";
              }
            }
          }
        }
        leaf mac-address {
          tailf:info
            "Virtual MAC address";
          type string {
            tailf:info
              "H.H.H;;MAC address";
          }
        }
        leaf name {
          tailf:info
            "Redundancy name string";
          tailf:cli-full-command;
          type string {
            tailf:info
              "WORD;;name string";
          }
        }
        container redirect {
          tailf:info
            "Configure sending of ICMP Redirect messages with an HSRP virtual IP address as the gateway IP address";
          container advertisement {
            tailf:info
              "Redirect advertisement messages";
            container authentication {
              tailf:info
                "Authentication";
              container md5 {
                tailf:info
                  "Use MD5 authentication";
                leaf key-chain {
                  tailf:info
                    "Set key chain";
                  type string {
                    tailf:info
                      "WORD;;Name of key-chain";
                  }
                }
                container key-string {
                  tailf:info
                    "Set key string";
                  tailf:cli-flatten-container;
                  tailf:cli-compact-syntax;
                  tailf:cli-sequence-commands;
                  uses ncs_rpc_notif_password-grouping;
                  leaf timeout {
                    tailf:info
                      "Set timeout";
                    type uint16 {
                      tailf:info
                        "<0-32767>;;Timeout until only accepting new key (seconds)";
                      range "0..32767";
                    }
                  }
                }
              }
            }
          }
          container timers {
            tailf:info
              "Adjust redirect timers";
            tailf:cli-compact-syntax;
            tailf:cli-sequence-commands {
              tailf:cli-reset-siblings;
            }
            leaf advertisement {
              tailf:cli-drop-node-name;
              type uint16 {
                tailf:info
                  "<10-180>;;Passive router advertisement interval in seconds";
                range "10..180";
              }
            }
            leaf holddown {
              tailf:cli-drop-node-name;
              type uint16 {
                tailf:info
                  "<30-3600>;;Passive router holddown interval in seconds";
                range "30..3600";
              }
            }
          }
          leaf unknown {
            tailf:info
              "Redirect to non-HSRP routers";
            type empty;
          }
        }
        container timers {
          tailf:info
            "Hello and hold timers";
          tailf:cli-compact-syntax;
          tailf:cli-sequence-commands {
            tailf:cli-reset-siblings;
          }
          container hello-interval {
            tailf:cli-drop-node-name;
            tailf:cli-flatten-container;
            tailf:cli-compact-syntax;
            choice hello-interval-choice {
              leaf seconds {
                tailf:cli-drop-node-name;
                tailf:cli-incomplete-command;
                type uint8 {
                  tailf:info
                    "<1-254>;;Hello interval in seconds";
                  range "1..254";
                }
              }
              leaf msec {
                tailf:info
                  "Specify hello interval in milliseconds";
                tailf:cli-incomplete-command;
                type uint16 {
                  tailf:info
                    "<15-999>;;Hello interval in milliseconds";
                  range "15..999";
                }
              }
            }
          }
          container hold-time {
            tailf:cli-drop-node-name;
            tailf:cli-flatten-container;
            tailf:cli-compact-syntax;
            choice hold-time-choice {
              leaf seconds {
                tailf:cli-drop-node-name;
                type uint8 {
                  tailf:info
                    "<1-255>;;Hold time in seconds";
                  range "1..255";
                }
              }
              leaf msec {
                tailf:info
                  "Specify hold time in milliseconds";
                type uint16 {
                  tailf:info
                    "<50-3000>;;Hello interval in milliseconds";
                  range "50..3000";
                }
              }
            }
          }
        }
        leaf priority {
          tailf:info
            "Priority level";
          tailf:cli-full-command;
          type uint8 {
            tailf:info
              "<0-255>;;Priority value";
          }
        }
        container preempt {
          tailf:info
            "Overthrow lower priority Active routers";
          tailf:cli-compact-syntax;
          tailf:meta-data "trim-delete-when-empty" {
            tailf:meta-value "( preempt)";
          }
          tailf:ned-data "." {
            tailf:xpath-root 3;
            tailf:transaction to;
          }
          presence "true";
          container delay {
            tailf:info
              "Wait before preempting";
            tailf:cli-compact-syntax;
            leaf minimum {
              tailf:info
                "Delay at least this long";
              type uint16 {
                tailf:info
                  "<0-3600>;;Number of seconds for minimum delay";
                range "0..3600";
              }
            }
            leaf reload {
              tailf:info
                "Delay after reload";
              type uint16 {
                tailf:info
                  "<0-3600>;;Number of seconds for reload delay";
                range "0..3600";
              }
            }
            leaf sync {
              tailf:info
                "Wait for IP redundancy client";
              type uint16 {
                tailf:info
                  "<0-3600>;;Number of seconds for sync delay";
                range "0..3600";
              }
            }
          }
        }
        list track {
          tailf:info
            "Priority tracking";
          tailf:cli-suppress-mode;
          tailf:cli-delete-when-empty;
          tailf:cli-incomplete-command;
          tailf:cli-compact-syntax;
          key "name";
          leaf name {
            tailf:cli-suppress-range;
            type union {
              type uint16 {
                tailf:info
                  "<0-1000>;;Tracked object number";
              }
              type string {
                tailf:info
                  "WORD;;Interface name";
              }
            }
          }
          choice options {
            case interface {
              leaf priority-decrement {
                tailf:cli-drop-node-name;
                type uint16 {
                  tailf:info
                    "<1-255>;;Decrement value";
                }
              }
            }
            case group-number {
              leaf decrement {
                tailf:info
                  "Priority decrement";
                tailf:cli-full-command;
                type uint16 {
                  tailf:info
                    "<1-255>;;Decrement value";
                }
              }
              leaf shutdown {
                tailf:info
                  "Shutdown group";
                tailf:cli-full-command;
                type empty;
              }
            }
          }
        }
      }
    }
    container storm-control {
      tailf:info
        "storm configuration";
      container action {
        tailf:info
          "Action to take for storm-control";
        leaf shutdown {
          tailf:info
            "Shutdown this interface if a storm occurs";
          tailf:cli-full-command;
          type empty;
        }
        leaf trap {
          tailf:info
            "Send SNMP trap if a storm occurs";
          tailf:cli-full-command;
          type empty;
        }
        leaf level {
          tailf:info
            "Set storm suppression level on this interface";
          tailf:cli-full-command;
          type decimal64 {
            fraction-digits 2;
            tailf:info
              "<0-100>;;Enter Integer part of level as percentage of bandwidth";
            range "0..100";
          }
        }
      }
      container broadcast {
        tailf:info
          "Broadcast address storm control";
        leaf level {
          tailf:info
            "Set storm suppression level on this interface";
          type decimal64 {
            fraction-digits 2;
            tailf:info
              "<0-100>;;Enter Integer part of level as percentage of bandwidth";
            range "0..100";
          }
        }
        uses ncs_rpc_notif_storm-control-level-bps-pps-grouping;
        container include {
          tailf:info
            "include other traffic types";
          leaf multicast {
            tailf:info
              "Suppress broadcast and multicast traffic";
            type empty;
          }
        }
      }
      container multicast {
        tailf:info
          "Multicast address storm control";
        leaf level {
          tailf:info
            "Set storm suppression level on this interface";
          type decimal64 {
            fraction-digits 2;
            tailf:info
              "<0-100>;;Enter Integer part of level as percentage of bandwidth";
            range "0..100";
          }
        }
        uses ncs_rpc_notif_storm-control-level-bps-pps-grouping;
      }
      container unicast {
        tailf:info
          "Unicast address storm control";
        leaf level {
          tailf:info
            "Set storm suppression level on this interface";
          type decimal64 {
            fraction-digits 2;
            tailf:info
              "<0-100>;;Enter Integer part of level as percentage of bandwidth";
            range "0..100";
          }
        }
        uses ncs_rpc_notif_storm-control-level-bps-pps-grouping;
      }
    }
    container wrr-queue {
      tailf:info
        "Configure weighted round-robin xmt queues";
      container bandwidth {
        tailf:info
          "Configure WRR minimum bandwidth with weights or percentages";
        tailf:cli-compact-syntax;
        tailf:cli-sequence-commands {
          tailf:cli-reset-siblings;
        }
        choice bandwidth-choice {
          case a {
            leaf weight-1 {
              tailf:cli-drop-node-name;
              type uint8 {
                tailf:info
                  "<0-255>;;enter bandwidth weight";
                range "0..255";
              }
            }
            leaf weight-2 {
              tailf:cli-drop-node-name;
              type uint8 {
                tailf:info
                  "<0-255>;;enter bandwidth weight";
                range "0..255";
              }
            }
            leaf weight-3 {
              tailf:cli-drop-node-name;
              type uint8 {
                tailf:info
                  "<0-255>;;enter bandwidth weight";
                range "0..255";
              }
            }
            leaf weight-4 {
              tailf:cli-drop-node-name;
              type uint8 {
                tailf:info
                  "<0-255>;;enter bandwidth weight";
                range "0..255";
              }
            }
            leaf weight-5 {
              tailf:cli-drop-node-name;
              type uint8 {
                tailf:info
                  "<0-255>;;enter bandwidth weight";
                range "0..255";
              }
            }
            leaf weight-6 {
              tailf:cli-drop-node-name;
              type uint8 {
                tailf:info
                  "<0-255>;;enter bandwidth weight";
                range "0..255";
              }
            }
            leaf weight-7 {
              tailf:cli-drop-node-name;
              type uint8 {
                tailf:info
                  "<0-255>;;enter bandwidth weight";
                range "0..255";
              }
            }
          }
          case b {
            container percent {
              tailf:cli-compact-syntax;
              tailf:cli-sequence-commands {
                tailf:cli-reset-siblings;
              }
              leaf percent-1 {
                tailf:cli-drop-node-name;
                type uint8 {
                  tailf:info
                    "<0-100>;;enter bandwidth percent";
                  range "0..100";
                }
              }
              leaf percent-2 {
                tailf:cli-drop-node-name;
                type uint8 {
                  tailf:info
                    "<0-100>;;enter bandwidth percent";
                  range "0..100";
                }
              }
              leaf percent-3 {
                tailf:cli-drop-node-name;
                type uint8 {
                  tailf:info
                    "<0-100>;;enter bandwidth percent";
                  range "0..100";
                }
              }
              leaf percent-4 {
                tailf:cli-drop-node-name;
                type uint8 {
                  tailf:info
                    "<0-100>;;enter bandwidth percent";
                  range "0..100";
                }
              }
              leaf percent-5 {
                tailf:cli-drop-node-name;
                type uint8 {
                  tailf:info
                    "<0-100>;;enter bandwidth percent";
                  range "0..100";
                }
              }
              leaf percent-6 {
                tailf:cli-drop-node-name;
                type uint8 {
                  tailf:info
                    "<0-100>;;enter bandwidth percent";
                  range "0..100";
                }
              }
              leaf percent-7 {
                tailf:cli-drop-node-name;
                type uint8 {
                  tailf:info
                    "<0-100>;;enter bandwidth percent";
                  range "0..100";
                }
              }
            }
          }
        }
      }
      list dscp-map {
        tailf:info
          "Configure dscp-map for a queue threshold";
        tailf:cli-suppress-mode;
        tailf:cli-delete-when-empty;
        tailf:cli-compact-syntax;
        key "queue threshold";
        leaf queue {
          type uint8 {
            tailf:info
              "<1-7>;;enter dscp-map queue id";
          }
        }
        leaf threshold {
          type uint8 {
            tailf:info
              "<1-4>;;enter dscp-map threshold id";
          }
        }
        list values {
          tailf:cli-drop-node-name;
          tailf:cli-suppress-mode;
          tailf:cli-delete-when-empty;
          tailf:cli-show-long-obu-diffs;
          ordered-by user;
          key "value";
          leaf value {
            tailf:cli-multi-word-key;
            type string;
          }
        }
      }
      list cos-map {
        tailf:info
          "Configure cos-map for a queue threshold";
        tailf:cli-suppress-mode;
        tailf:cli-delete-when-empty;
        tailf:cli-compact-syntax;
        tailf:cli-sequence-commands {
          tailf:cli-reset-siblings;
        }
        key "queue-id threshold-id";
        leaf queue-id {
          type uint8 {
            tailf:info
              "<1-4>;;enter cos-map queue id";
            range "1..4";
          }
        }
        leaf threshold-id {
          type uint8 {
            tailf:info
              "<1-8>;;enter cos-map threshhold id";
            range "0..8";
          }
        }
        leaf-list cos-values {
          tailf:cli-drop-node-name;
          tailf:cli-flat-list-syntax;
          tailf:meta-data "max-values-copy-meta" {
            tailf:meta-value "4 :: 1";
          }
          tailf:meta-data "default-value" {
            tailf:meta-value "$1 $2<NL> <DEFAULT><NL>exit<NL> :: MAP=WRR-QUEUE-COSMAP";
          }
          max-elements 8;
          type uint8 {
            tailf:info
              "<0-7>;;cos values separated by spaces (up to 8 values total)";
            range "0..7";
          }
        }
      }
      container queue-limit {
        tailf:info
          "Configure queue-limit";
        tailf:cli-compact-syntax;
        tailf:cli-sequence-commands {
          tailf:cli-reset-siblings;
        }
        leaf weight-a {
          tailf:cli-drop-node-name;
          type uint8 {
            tailf:info
              "<0-100>;;enter queue size weight";
            range "0..100";
          }
        }
        leaf weight-b {
          tailf:cli-drop-node-name;
          type uint8 {
            tailf:info
              "<0-100>;;enter queue size weight";
            range "0..100";
          }
        }
        leaf weight-c {
          tailf:cli-drop-node-name;
          type uint8 {
            tailf:info
              "<0-100>;;enter queue size weight";
            range "0..100";
          }
        }
        leaf weight-d {
          tailf:cli-drop-node-name;
          type uint8 {
            tailf:info
              "<0-100>;;enter queue size weight";
            range "0..100";
          }
        }
        leaf weight-e {
          tailf:cli-drop-node-name;
          type uint8 {
            tailf:info
              "<0-100>;;enter queue size weight";
            range "0..100";
          }
        }
        leaf weight-f {
          tailf:cli-drop-node-name;
          type uint8 {
            tailf:info
              "<0-100>;;enter queue size weight";
            range "0..100";
          }
        }
        leaf weight-g {
          tailf:cli-drop-node-name;
          type uint8 {
            tailf:info
              "<0-100>;;enter queue size weight";
            range "0..100";
          }
        }
      }
      container random-detect {
        tailf:info
          "Configure random-detect";
        list max-threshold {
          tailf:info
            "Max threshold for WRED";
          tailf:cli-suppress-mode;
          tailf:cli-delete-when-empty;
          tailf:cli-compact-syntax;
          tailf:cli-sequence-commands {
            tailf:cli-reset-siblings;
          }
          key "id";
          leaf id {
            type uint8 {
              tailf:info
                "<1-3>;;enter queue id";
              range "1..3";
            }
          }
          uses ncs_rpc_notif_queue-size-grouping;
        }
        list min-threshold {
          tailf:info
            "Min threshold for WRED";
          tailf:cli-suppress-mode;
          tailf:cli-delete-when-empty;
          tailf:cli-compact-syntax;
          tailf:cli-sequence-commands {
            tailf:cli-reset-siblings;
          }
          key "id";
          leaf id {
            type uint8 {
              tailf:info
                "<1-3>;;enter queue id";
              range "1..3";
            }
          }
          uses ncs_rpc_notif_queue-size-grouping;
        }
      }
      list threshold {
        tailf:info
          "Configure queue tail-drop thresholds";
        tailf:cli-suppress-mode;
        tailf:cli-delete-when-empty;
        tailf:cli-compact-syntax;
        tailf:cli-sequence-commands {
          tailf:cli-reset-siblings;
        }
        key "id";
        leaf id {
          type uint8 {
            tailf:info
              "<1-3>;;enter queue id";
            range "1..3";
          }
        }
        uses ncs_rpc_notif_queue-size-grouping;
      }
      list min-reserve {
        tailf:info
          "Configure min-reserve level";
        tailf:cli-suppress-mode;
        tailf:cli-delete-when-empty;
        tailf:cli-incomplete-command;
        key "id";
        leaf id {
          type uint8 {
            tailf:info
              "<1-4>;;queue id";
            range "1..4";
          }
        }
        leaf level {
          tailf:cli-drop-node-name;
          type uint8 {
            tailf:info
              "<1-8>;;min-reserve level";
            range "1..8";
          }
        }
      }
    }
    container no-list {
      tailf:info
        "no wrr-queue random-detect entry";
      container wrr-queue {
        tailf:info
          "Configure weighted round-robin xmt queues";
        list random-detect {
          tailf:info
            "Configure random-detect";
          tailf:cli-suppress-mode;
          tailf:cli-delete-when-empty;
          key "id";
          leaf id {
            type uint32;
          }
        }
      }
    }
    container priority-queue {
      tailf:info
        "Configure priority scheduling";
      leaf queue-limit {
        tailf:info
          "configure priority queue limit";
        tailf:cli-full-command;
        type uint8 {
          tailf:info
            "<0-100>;;enter queue size weight";
          range "0..100";
        }
      }
      list dscp-map {
        tailf:info
          "Configure dscp-map for a queue threshold";
        tailf:cli-suppress-mode;
        tailf:cli-delete-when-empty;
        tailf:cli-compact-syntax;
        tailf:cli-incomplete-command;
        key "id";
        leaf id {
          type uint8 {
            tailf:info
              "<1-1>;;enter priority queue id";
            range "1";
          }
        }
        list values {
          tailf:cli-drop-node-name;
          tailf:cli-suppress-mode;
          tailf:cli-delete-when-empty;
          tailf:cli-show-long-obu-diffs;
          ordered-by user;
          key "value";
          leaf value {
            tailf:cli-multi-word-key;
            type string;
          }
        }
      }
      container cos-map {
        tailf:info
          "Configure cos-map for a queue";
        tailf:cli-compact-syntax;
        tailf:cli-sequence-commands;
        leaf id {
          tailf:cli-drop-node-name;
          tailf:cli-incomplete-command;
          type uint8 {
            tailf:info
              "<1-1>;;enter cos-map queue id";
            range "1";
          }
        }
        leaf-list cos-values {
          tailf:cli-drop-node-name;
          tailf:cli-flat-list-syntax;
          tailf:meta-data "default-value" {
            tailf:meta-value "$1 $2<NL> <DEFAULT><NL>exit<NL> :: priority-queue cos-map 1 5";
          }
          max-elements 8;
          type uint8 {
            tailf:info
              "<0-7>;;cos values separated by spaces (up to 8 values total)";
            range "0..7";
          }
        }
      }
      leaf out {
        tailf:info
          "egress priority queue";
        tailf:cli-full-command;
        type empty;
      }
    }
    container rep {
      tailf:info
        "Resilient Ethernet Protocol characteristics";
      container block {
        tailf:info
          "Block port & VLANs for VLAN Load-balancing";
        container port {
          tailf:info
            "Specify port for VLAN Load-balancing";
          tailf:cli-sequence-commands {
            tailf:cli-reset-siblings;
          }
          tailf:cli-compact-syntax;
          choice port-choice {
            leaf neighbor-offset {
              tailf:cli-drop-node-name;
              type int16 {
                tailf:info
                  "<-256 - 256>;;Neighbor offset";
                range "-256..256";
              }
            }
            leaf id {
              tailf:info
                "REP port ID";
              type string {
                tailf:info
                  "WORD;;REP port ID (16 digit hexadecimal number)";
              }
            }
            leaf preferred {
              tailf:info
                "Preferred flag";
              type empty;
            }
          }
          leaf vlan {
            tailf:info
              "VLANs to block";
            type union {
              type string {
                tailf:info
                  "WORD;;VLAN list (1-4094) ex: 1-65,72,300-320";
              }
              type enumeration {
                enum "all" {
                  tailf:info
                    "All VLANs";
                }
              }
            }
          }
        }
      }
      container preempt {
        tailf:info
          "Preemption options";
        leaf delay {
          tailf:info
            "Delay timer in seconds";
          type uint16 {
            tailf:info
              "<15-300>;;number of seconds before automatic preemption takes place";
            range "15..300";
          }
        }
      }
      container segment {
        tailf:info
          "REP segment ID";
        tailf:cli-compact-syntax;
        tailf:cli-sequence-commands {
          tailf:cli-reset-siblings;
        }
        leaf id {
          tailf:cli-drop-node-name;
          type uint16 {
            tailf:info
              "<1-1024>;;Between 1 and 1024";
            range "1..1024";
          }
        }
        leaf edge {
          tailf:info
            "Edge Port";
          tailf:cli-optional-in-sequence;
          type empty;
        }
        leaf no-neighbor {
          tailf:info
            "No-Neighbor Edge Port";
          tailf:cli-optional-in-sequence;
          type empty;
        }
        leaf primary {
          tailf:info
            "Primary Edge Port";
          tailf:cli-optional-in-sequence;
          when "../edge" {
            tailf:xpath-root 3;
            tailf:dependency "../edge";
          }
          type empty;
        }
        leaf preferred {
          tailf:info
            "Preferred Alternate Port";
          type empty;
        }
      }
      container stcn {
        tailf:info
          "Segment Topology Change Notification";
        leaf segment {
          tailf:info
            "for REP segment";
          type string {
            tailf:info
              "WORD;;segment ID list (1-1024) ex: 1-3,6-9";
          }
        }
        leaf stp {
          tailf:info
            "for STP network";
          type empty;
        }
      }
    }
    container rcv-queue {
      tailf:info
        "Configure receive queue(s)";
      list cos-map {
        tailf:info
          "Configure cos-map for a queue threshold";
        tailf:cli-suppress-mode;
        tailf:cli-delete-when-empty;
        tailf:cli-compact-syntax;
        tailf:cli-sequence-commands {
          tailf:cli-reset-siblings;
        }
        key "queue-id threshold-id";
        leaf queue-id {
          type uint8 {
            tailf:info
              "<1-3>;;enter cos-map queue id";
            range "1..3";
          }
        }
        leaf threshold-id {
          type uint8 {
            tailf:info
              "<1-8>;;enter cos-map threshhold id";
            range "1..8";
          }
        }
        leaf-list cos-values {
          tailf:cli-drop-node-name;
          tailf:cli-flat-list-syntax;
          max-elements 8;
          type uint8 {
            tailf:info
              "<0-7>;;cos values separated by spaces (up to 8 values total)";
            range "0..7";
          }
        }
      }
    }
    container udld {
      tailf:info
        "Configure UDLD enabled or disabled and ignore global UDLD setting";
      container port {
        tailf:info
          "Enable UDLD protocol on this interface despite global UDLD setting";
        tailf:cli-delete-when-empty;
        presence "true";
        choice port-choice {
          leaf aggressive {
            tailf:info
              "Enable UDLD protocol in aggressive mode on this interface despite global UDLD setting";
            type empty;
          }
          leaf disable {
            tailf:info
              "Disable UDLD protocol on this interface despite global UDLD setting";
            type empty;
          }
        }
      }
    }
    container peer {
      tailf:info
        "Peer parameters for point to point interfaces";
      leaf neighbor-route {
        tailf:info
          "Create neighbor route to peer if needed";
        tailf:cli-boolean-no;
        tailf:cli-full-command;
        type boolean;
        default "true";
      }
      container default {
        tailf:info
          "Specify default parameters";
        container ip {
          tailf:info
            "Specify default IP parameters";
          container address {
            tailf:info
              "Specify default IP address";
            choice address-choice {
              leaf dhcp {
                tailf:info
                  "Use DHCP proxy client mechanism to allocate a peer IP address";
                type empty;
              }
              container dhcp-pool {
                tailf:info
                  "Use local DHCP pools to allocate a peer IP address";
                presence "true";
                leaf pools {
                  tailf:cli-drop-node-name;
                  tailf:cli-multi-value;
                  type string {
                    tailf:info
                      "LINE;;List of one or more DHCP address pools";
                  }
                }
              }
              container pool {
                tailf:info
                  "Use IP pool mechanism to allocate a peer IP address";
                presence "true";
                leaf pools {
                  tailf:cli-drop-node-name;
                  tailf:cli-multi-value;
                  type string {
                    tailf:info
                      "LINE;;List of one or more DHCP address pools";
                  }
                }
              }
            }
          }
        }
      }
    }
    container clns {
      tailf:info
        "CLNS interface subcommands";
      leaf mtu {
        tailf:info
          "Set MTU packet size for interface";
        type uint32 {
          tailf:info
            "<512-4294967295>;;CLNS MTU packet size for interface";
        }
      }
      container router {
        tailf:info
          "Enable CLNS routing protocol on interface";
        container isis {
          tailf:info
            "ISO IS-IS routing protocol";
          tailf:cli-delete-when-empty;
          presence "true";
          leaf tag {
            tailf:cli-drop-node-name;
            type string {
              tailf:info
                "WORD;;Routing process tag";
            }
          }
        }
      }
      leaf route-cache {
        tailf:info
          "Enable fast switching through the cache";
        tailf:cli-boolean-no;
        tailf:cli-full-command;
        type boolean;
        default "true";
      }
    }
    container dsu {
      leaf bandwidth {
        tailf:cli-full-command;
        type uint32;
      }
      leaf mode {
        tailf:cli-full-command;
        type enumeration {
          enum "1" {
            tailf:info
              "DSU mode 1";
          }
          enum "2" {
            tailf:info
              "DSU mode 2";
          }
        }
      }
    }
    leaf framing {
      tailf:info
        "Framing interface subcommands";
      tailf:cli-full-command;
      type enumeration {
        enum "bypass";
        enum "g751" {
          tailf:info
            "G.751 framing";
        }
        enum "c-bit";
        enum "m13";
      }
    }
    leaf cablelength {
      tailf:cli-full-command;
      type uint32;
    }
    container isdn {
      tailf:info
        "ISDN Interface configuration commands";
      leaf switch-type {
        tailf:info
          "Select the Interface ISDN switch type";
        tailf:cli-full-command;
        type string {
          tailf:info
            "WORD;;Switch type";
        }
      }
      leaf protocol-emulate {
        tailf:info
          "Protocol (L2/L3) emulation network/user side";
        tailf:cli-full-command;
        type enumeration {
          enum "network" {
            tailf:info
              "ISDN protocol emulation network side";
          }
          enum "user" {
            tailf:info
              "ISDN protocol emulation user side (default)";
          }
        }
      }
      container incoming-voice {
        tailf:info
          "Specify options for incoming calls.";
        choice incoming-voice-choice {
          leaf voice {
            tailf:info
              "Incoming voice calls will be handled as voice.";
            type empty;
          }
          container data {
            tailf:info
              "Incoming voice calls will be handled as data.";
            tailf:cli-delete-when-empty;
            presence "true";
            leaf kbps {
              tailf:cli-drop-node-name;
              type enumeration {
                enum "56" {
                  tailf:info
                    "B Channel Bandwidth of 56Kb/s";
                }
                enum "64" {
                  tailf:info
                    "B Channel Bandwidth of 64Kb/s";
                }
              }
            }
          }
          container modem {
            tailf:info
              "Incoming voice calls will be handled as modems.";
            tailf:cli-delete-when-empty;
            presence "true";
            leaf kbps {
              tailf:cli-drop-node-name;
              type enumeration {
                enum "56" {
                  tailf:info
                    "56  B Channel Bandwidth of 56Kb/s  ";
                }
                enum "64" {
                  tailf:info
                    "64  B Channel Bandwidth of 64Kb/s";
                }
              }
            }
          }
        }
      }
      container supp-service {
        tailf:info
          "Specify the subscribed supplementary service";
        container name {
          tailf:info
            "Specify the subscribed name service";
          container calling {
            tailf:info
              "calling name service";
            tailf:cli-delete-when-empty;
            presence "true";
          }
        }
      }
      container termination {
        tailf:info
          "To connect the TR pair and to in turn enable internal termination";
        leaf multidrop {
          tailf:info
            "Enable multidrop Internal termination";
          type empty;
        }
      }
      leaf point-to-point-setup {
        tailf:info
          "Bri send point-to-point SETUP";
        tailf:cli-full-command;
        type empty;
      }
    }
    leaf scramble {
      tailf:cli-full-command;
      type empty;
    }
    container clock {
      tailf:info
        "Configure interface clock source";
      leaf source {
        type enumeration {
          enum "internal" {
            tailf:info
              "Internal clock source";
          }
          enum "external" {
            tailf:info
              "External clock source";
          }
          enum "line" {
            tailf:info
              "Line clock source";
          }
        }
      }
      leaf rate {
        tailf:info
          "Clock rate";
        type uint32 {
          tailf:info
            "NUM;;Clock rate, round of to the nearest supported value by device. Please set exact to avoid diff.";
        }
      }
    }
    leaf down-when-looped {
      tailf:info
        "Force looped serial interface down";
      tailf:cli-full-command;
      type empty;
    }
    leaf crc {
      tailf:info
        "CRC interface subcommands";
      tailf:cli-full-command;
      type enumeration {
        enum "16" {
          tailf:info
            "Setting CRC-16";
        }
        enum "32" {
          tailf:info
            "Setting CRC-32";
        }
      }
    }
    container carrier-delay {
      tailf:info
        "Specify delay for interface transitions";
      uses ncs_rpc_notif_carrier-delay-grouping;
      container up {
        tailf:info
          "Carrier Up Transitions";
        uses ncs_rpc_notif_carrier-delay-grouping;
      }
      container down {
        tailf:info
          "Carrier Down Transitions";
        uses ncs_rpc_notif_carrier-delay-grouping;
      }
    }
    leaf trunk-group {
      tailf:info
        "Configure interface to be in a trunk group";
      // NCS drop tailf-common:non-strict-leafref statement
      type string {
        tailf:info
          "WORD;;Trunk group label";
      }
    }
    container crypto {
      tailf:info
        "Encryption/Decryption commands";
      container engine {
        tailf:info
          "";
        tailf:cli-compact-syntax;
        tailf:cli-sequence-commands {
          tailf:cli-reset-all-siblings;
        }
        leaf slot {
          tailf:info
            "WORD;;<integer>/<integer>";
          type string;
        }
        leaf location {
          tailf:info
            "";
          tailf:cli-drop-node-name;
          type enumeration {
            enum "inside";
            enum "outside";
          }
        }
      }
      container map {
        tailf:info
          "Assign a Crypto Map";
        container ipv4 {
          tailf:cli-drop-node-name;
          tailf:cli-compact-syntax;
          tailf:cli-sequence-commands {
            tailf:cli-reset-siblings;
          }
          leaf map-name {
            tailf:cli-drop-node-name;
            tailf:cli-disallow-value "ipv6";
            // NCS drop tailf-common:non-strict-leafref statement
            type string {
              tailf:info
                "WORD;;Crypto Map tag";
            }
          }
          leaf redundancy {
            tailf:info
              "enable redundancy";
            type string {
              tailf:info
                "WORD;;Name of IP Redundancy Group";
            }
          }
          leaf stateful {
            tailf:info
              "enable stateful failover";
            when "../redundancy" {
              tailf:xpath-root 3;
              tailf:dependency "../redundancy";
            }
            type empty;
          }
        }
        container ipv6 {
          tailf:cli-compact-syntax;
          tailf:cli-sequence-commands {
            tailf:cli-reset-siblings;
          }
          leaf map-name {
            tailf:cli-drop-node-name;
            // NCS drop tailf-common:non-strict-leafref statement
            type string {
              tailf:info
                "WORD;;Crypto Map tag";
            }
          }
          leaf redundancy {
            tailf:info
              "enable redundancy";
            type string {
              tailf:info
                "WORD;;Name of IP Redundancy Group";
            }
          }
          leaf stateful {
            tailf:info
              "enable stateful failover";
            when "../redundancy" {
              tailf:xpath-root 3;
              tailf:dependency "../redundancy";
            }
            type empty;
          }
        }
      }
    }
    container routing {
      tailf:info
        "Per-interface routing configuration";
      leaf dynamic {
        tailf:info
          "participates in routing protocols";
        tailf:cli-boolean-no;
        tailf:cli-full-command;
        type boolean;
        default "true";
      }
    }
    container autonomic {
      tailf:info
        "Autonomic Networking";
      leaf connect {
        tailf:info
          "Connect to External Device";
        type empty;
      }
    }
    container performance {
      tailf:info
        "Global performance monitor configuration";
      container monitor {
        tailf:info
          "monitor";
        leaf context {
          tailf:info
            "Select ezPM context";
          tailf:cli-diff-dependency "/ios:performance/monitor/context[name=current()]/exporter/destination" {
            tailf:xpath-root 3;
          }
          // NCS drop tailf-common:non-strict-leafref statement
          type string {
            tailf:info
              "WORD;;User defined ezPM context";
          }
        }
      }
    }
    container qos {
      tailf:info
        "QoS configuration";
      container trust {
        tailf:info
          "Trust state of the interface";
        choice trust-choice {
          leaf dscp {
            tailf:info
              "Trust DSCP";
            type empty;
          }
          leaf cos {
            tailf:info
              "Trust CoS";
            type empty;
          }
          leaf device {
            tailf:info
              "trusted device class";
            type enumeration {
              enum "cisco-phone" {
                tailf:info
                  "Cisco IP Phone";
              }
            }
          }
        }
      }
      leaf pre-classify {
        tailf:info
          "Enable QOS classification before packets are tunnel encapsulated";
        type empty;
      }
    }
    list tx-queue {
      tailf:info
        "Configure interface transmit queue";
      tailf:cli-mode-name "config-if-tx-queue";
      key "id";
      leaf id {
        type uint8 {
          tailf:info
            "<1-4>;;Transmit queue number";
          range "1..4";
        }
      }
      container bandwidth {
        tailf:info
          "Bandwidth for this queue";
        tailf:cli-compact-syntax;
        tailf:cli-sequence-commands {
          tailf:cli-reset-siblings;
        }
        choice bandwidth-choice {
          case numeric {
            leaf value {
              tailf:cli-drop-node-name;
              type string {
                tailf:info
                  "<16000-1000000000>;;Bandwidth (Sharing rate) (postfix k, m, g optional; decimal point allowed)";
              }
            }
            leaf unit {
              tailf:cli-drop-node-name;
              type string {
                tailf:info
                  "UNIT;;kbps | mbps | gbps";
              }
            }
          }
          leaf percent {
            tailf:info
              "% of the link bandwidth";
            type uint8 {
              tailf:info
                "<1-100>;;percent";
              range "1..100";
            }
          }
        }
      }
      leaf priority {
        tailf:info
          "Priority of this queue";
        type enumeration {
          enum "high" {
            tailf:info
              "High priority queue";
          }
        }
      }
    }
    container link {
      tailf:info
        "Configure Link";
      container state {
        tailf:info
          "Configure link state";
        container group {
          tailf:info
            "Configure link state group";
          tailf:cli-compact-syntax;
          tailf:cli-sequence-commands {
            tailf:cli-reset-siblings;
          }
          leaf number {
            tailf:cli-drop-node-name;
            tailf:cli-incomplete-command;
            type uint8 {
              tailf:info
                "<1-10>;;Link state group number";
              range "1..10";
            }
          }
          leaf direction {
            tailf:cli-drop-node-name;
            type enumeration {
              enum "downstream" {
                tailf:info
                  "Downstream interface";
              }
              enum "upstream" {
                tailf:info
                  "Upstream interface";
              }
            }
          }
        }
      }
    }
    container source {
      tailf:info
        "Get config from another source";
      leaf template {
        tailf:info
          "Get config from a template";
        // NCS drop tailf-common:non-strict-leafref statement
        type string {
          tailf:info
            "WORD;;Template name";
        }
      }
    }
    container l2protocol {
      tailf:info
        "Configure l2 control protocol processing";
      container peer {
        tailf:info
          "peer L2 control protocol packets as data";
        tailf:cli-delete-when-empty;
        presence "true";
        leaf-list protocol {
          tailf:cli-drop-node-name;
          tailf:cli-flat-list-syntax;
          type l2protocol-type;
        }
      }
      container forward {
        tailf:info
          "forward L2 control protocol packets as data";
        tailf:cli-delete-when-empty;
        presence "true";
        leaf-list protocol {
          tailf:cli-drop-node-name;
          tailf:cli-flat-list-syntax;
          type l2protocol-type;
        }
      }
    }
    container zone-member {
      tailf:info
        "Apply zone name";
      leaf security {
        tailf:info
          "Security zone";
        tailf:cli-diff-dependency "../../vrf/forwarding" {
          tailf:xpath-root 3;
        }
        // NCS drop tailf-common:non-strict-leafref statement
        type string {
          tailf:info
            "WORD;;Zone";
        }
      }
    }
  }

  grouping ncs_rpc_notif_interface-common-grouping {
    uses ncs_rpc_notif_interface-common-grouping0 {
      refine "ip/helper-address/vrf/vrf" {
        tailf:cli-diff-dependency "../../../../../../ip/vrf" {
          tailf:xpath-root 3;
        }
        tailf:cli-diff-dependency "../../../../../../vrf/definition" {
          tailf:xpath-root 3;
        }
      }
      refine "crypto/map/ipv4/map-name" {
        tailf:cli-diff-dependency "../../../../../../crypto/map" {
          tailf:xpath-root 3;
        }
      }
      refine "crypto/map/ipv6/map-name" {
        tailf:cli-diff-dependency "../../../../../../crypto/map" {
          tailf:xpath-root 3;
        }
      }
      refine "ip/mobile/router-service/roam" {
        tailf:cli-diff-dependency "../../../../../../router/mobile" {
          tailf:xpath-root 3;
        }
      }
      refine "ip/pim/mode" {
        tailf:cli-diff-dependency "../../../../../ip/multicast-routing" {
          tailf:xpath-root 3;
        }
      }
    }
  }

  grouping ncs_rpc_notif_sub-interface-common-grouping {
    uses ncs_rpc_notif_interface-common-grouping0 {
      refine "ip/helper-address/vrf/vrf" {
        tailf:cli-diff-dependency "../../../../../../../ip/vrf" {
          tailf:xpath-root 3;
        }
        tailf:cli-diff-dependency "../../../../../../../vrf/definition" {
          tailf:xpath-root 3;
        }
      }
      refine "crypto/map/ipv4/map-name" {
        tailf:cli-diff-dependency "../../../../../../../crypto/map" {
          tailf:xpath-root 3;
        }
      }
      refine "crypto/map/ipv6/map-name" {
        tailf:cli-diff-dependency "../../../../../../../crypto/map" {
          tailf:xpath-root 3;
        }
      }
      refine "ip/mobile/router-service/roam" {
        tailf:cli-diff-dependency "../../../../../../../router/mobile" {
          tailf:xpath-root 3;
        }
      }
      refine "ip/pim/mode" {
        tailf:cli-diff-dependency "../../../../../../ip/multicast-routing" {
          tailf:xpath-root 3;
        }
      }
    }
  }

  grouping ncs_rpc_notif_interface-common-switch-grouping {
    uses ncs_rpc_notif_interface-common-grouping {
      refine "ip/dhcp/snooping" {
        tailf:cli-diff-dependency "../../../switchport" {
          tailf:xpath-root 3;
        }
      }
      refine "ip/verify" {
        tailf:cli-diff-dependency "../../switchport" {
          tailf:xpath-root 3;
        }
      }
      refine "ip/igmp" {
        tailf:cli-diff-dependency "../../switchport" {
          tailf:xpath-root 3;
          tailf:cli-trigger-on-set;
        }
        tailf:cli-diff-dependency "../../switchport" {
          tailf:xpath-root 3;
        }
      }
      refine "ip/ospf" {
        tailf:cli-diff-dependency "../../switchport" {
          tailf:xpath-root 3;
          tailf:cli-trigger-on-set;
        }
      }
      refine "ip/redirects" {
        tailf:cli-diff-dependency "../../switchport" {
          tailf:xpath-root 3;
          tailf:cli-trigger-on-set;
        }
      }
      refine "standby" {
        tailf:cli-diff-dependency "../switchport" {
          tailf:xpath-root 3;
          tailf:cli-trigger-on-set;
        }
      }
      refine "service-policy/input" {
        tailf:cli-diff-dependency "../../switchport" {
          tailf:xpath-root 3;
          tailf:cli-trigger-on-set;
        }
      }
      refine "service-policy/output" {
        tailf:cli-diff-dependency "../../switchport" {
          tailf:xpath-root 3;
          tailf:cli-trigger-on-set;
        }
      }
      refine "udld" {
        tailf:cli-diff-dependency "../switchport" {
          tailf:xpath-root 3;
          tailf:cli-trigger-on-set;
        }
      }
    }
  }

  grouping ncs_rpc_notif_sub-interface-common-switch-grouping {
    uses ncs_rpc_notif_sub-interface-common-grouping {
      refine "ip/dhcp/snooping" {
        tailf:cli-diff-dependency "../../../switchport" {
          tailf:xpath-root 3;
        }
      }
      refine "ip/verify" {
        tailf:cli-diff-dependency "../../switchport" {
          tailf:xpath-root 3;
        }
      }
      refine "ip/igmp" {
        tailf:cli-diff-dependency "../../switchport" {
          tailf:xpath-root 3;
          tailf:cli-trigger-on-set;
        }
        tailf:cli-diff-dependency "../../switchport" {
          tailf:xpath-root 3;
        }
      }
      refine "ip/ospf" {
        tailf:cli-diff-dependency "../../switchport" {
          tailf:xpath-root 3;
          tailf:cli-trigger-on-set;
        }
      }
      refine "ip/redirects" {
        tailf:cli-diff-dependency "../../switchport" {
          tailf:xpath-root 3;
          tailf:cli-trigger-on-set;
        }
      }
      refine "standby" {
        tailf:cli-diff-dependency "../switchport" {
          tailf:xpath-root 3;
          tailf:cli-trigger-on-set;
        }
      }
      refine "service-policy/input" {
        tailf:cli-diff-dependency "../../switchport" {
          tailf:xpath-root 3;
          tailf:cli-trigger-on-set;
        }
      }
      refine "service-policy/output" {
        tailf:cli-diff-dependency "../../switchport" {
          tailf:xpath-root 3;
          tailf:cli-trigger-on-set;
        }
      }
      refine "udld" {
        tailf:cli-diff-dependency "../switchport" {
          tailf:xpath-root 3;
          tailf:cli-trigger-on-set;
        }
      }
    }
  }

  grouping ncs_rpc_notif_interface-tunnel-grouping {
    container tunnel {
      tailf:info
        "protocol-over-protocol tunneling";
      leaf source {
        tailf:info
          "source of tunnel packets";
        type string;
      }
      leaf destination {
        tailf:info
          "destination of tunnel";
        type inet:host {
          tailf:info
            "Hostname, A.B.C.D or X:X:X:X::X;;Destination address";
        }
      }
      container mode {
        tailf:info
          "tunnel encapsulation method";
        choice mode-choice {
          container ipsec {
            tailf:info
              "IPSec tunnel encapsulation";
            container ipv4 {
              tailf:info
                "over IPv4";
              tailf:cli-delete-when-empty;
              presence "true";
            }
          }
          container mpls {
            tailf:info
              "MPLS encapsulations";
            container traffic-eng {
              tailf:info
                "Traffic engineering tunnels";
              tailf:cli-delete-when-empty;
              presence "true";
              leaf gre-ip {
                type empty;
              }
              leaf point-to-multipoint {
                tailf:info
                  "point-to-multipoint tunnel mode";
                tailf:cli-full-command;
                type empty;
              }
            }
          }
          container gre {
            tailf:info
              "generic route encapsulation protocol";
            choice gre-choice {
              container multipoint {
                tailf:info
                  "over IPv4 (multipoint)";
                presence "true";
                leaf ipv6 {
                  tailf:info
                    "over IPv6";
                  type empty;
                }
              }
              leaf ip {
                tailf:info
                  "over IP";
                type empty;
              }
              leaf ipv6 {
                tailf:info
                  "over IPv6";
                type empty;
              }
              default "ip";
            }
          }
          leaf eon {
            tailf:info
              "EON compatible CLNS tunnel";
            type empty;
          }
          leaf ipv6 {
            tailf:info
              "Generic packet tunneling in IPv6";
            type empty;
          }
        }
      }
      leaf key {
        tailf:info
          "security or selector key";
        type uint32 {
          tailf:info
            "<0-4294967295>;;key";
          range "0..4294967295";
        }
      }
      leaf vrf {
        tailf:info
          "set tunnel vrf membership";
        tailf:cli-diff-dependency "../../../../ip/vrf" {
          tailf:xpath-root 3;
        }
        tailf:cli-diff-dependency "../../../../vrf/definition" {
          tailf:xpath-root 3;
        }
        type string {
          tailf:info
            "WORD;;vrf table name";
        }
      }
      container path-mtu-discovery {
        tailf:info
          "Enable Path MTU Discovery on tunnel";
        presence "true";
      }
      container protection {
        tailf:info
          "Enable tunnel protection";
        container ipsec {
          tailf:info
            "Use ipsec to protect this tunnel interface";
          tailf:cli-compact-syntax;
          tailf:cli-sequence-commands {
            tailf:cli-reset-all-siblings;
          }
          leaf profile {
            tailf:info
              "Determine the ipsec policy profile to use.";
            tailf:non-strict-leafref {
              path "../../../../../../crypto/ipsec/profile/name";
            }
            type string {
              tailf:info
                "WORD;;IPSec policy profile";
            }
          }
          choice profile-choice {
            leaf isakmp-profile {
              tailf:info
                "Specify isakmp profile for the crypto connection.";
              tailf:non-strict-leafref {
                path "../../../../../../crypto/isakmp/profile/name";
              }
              type string {
                tailf:info
                  "WORD;;Profile name.";
              }
            }
            leaf ikev2-profile {
              tailf:info
                "Specify ikev2 profile for the crypto connection.";
              tailf:non-strict-leafref {
                path "../../../../../../crypto/ikev2/profile/name";
              }
              type string {
                tailf:info
                  "WORD;;Profile name.";
              }
            }
            leaf shared {
              tailf:info
                "Use a shared socket for the crypto connection.";
              type empty;
            }
          }
        }
      }
      container mpls {
        tailf:info
          "MPLS tunnel commands";
        container traffic-eng {
          tailf:info
            "Configure traffic engineering tunnel parameters";
          tailf:cli-diff-dependency "../../mode/mpls/traffic-eng" {
            tailf:xpath-root 3;
          }
          leaf name {
            tailf:info
              "specify a name describing the TE tunnel";
            tailf:cli-full-command;
            type string {
              tailf:info
                "WORD;;Name of tunnel (max of 63 characters)";
            }
          }
          container affinity {
            tailf:info
              "desired link attributes for links comprising tunnel";
            tailf:cli-compact-syntax;
            tailf:cli-sequence-commands {
              tailf:cli-reset-siblings;
            }
            leaf attributes {
              tailf:cli-drop-node-name;
              type string {
                tailf:info
                  "<0x0-0xFFFFFFFF>;;affinity value";
              }
            }
            leaf mask {
              tailf:info
                "mask on desired link attributes";
              type string {
                tailf:info
                  "<0x0-0xFFFFFFFF>;;affinity mask value";
              }
            }
          }
          container autoroute {
            tailf:info
              "parameters for routing over tunnel";
            leaf announce {
              tailf:info
                "announce tunnel to IGP";
              tailf:cli-full-command;
              type empty;
            }
          }
          container priority {
            tailf:info
              "tunnel priority";
            tailf:cli-sequence-commands {
              tailf:cli-reset-siblings;
            }
            tailf:cli-compact-syntax;
            leaf setup-priority {
              tailf:cli-drop-node-name;
              type uint8 {
                tailf:info
                  "<0-7>;;setup priority";
                range "0..7";
              }
            }
            leaf hold-priority {
              tailf:cli-drop-node-name;
              type uint8 {
                tailf:info
                  "<0-7>;;hold priority";
                range "0..7";
              }
            }
          }
          container bandwidth {
            tailf:info
              "tunnel bandwidth requirement";
            leaf requirement {
              tailf:cli-drop-node-name;
              type uint32 {
                tailf:info
                  "<0-4294967295>;;bandwidth requirement in kbps";
              }
            }
          }
          list path-option {
            tailf:info
              "a primary or fallback path setup option";
            tailf:cli-suppress-mode;
            tailf:cli-delete-when-empty;
            tailf:cli-compact-syntax;
            tailf:cli-sequence-commands {
              tailf:cli-reset-siblings;
            }
            tailf:cli-incomplete-command;
            key "id";
            leaf id {
              tailf:cli-suppress-range;
              type uint16 {
                tailf:info
                  "<1-1000>;;preference for this path option";
              }
            }
            leaf protect {
              tailf:info
                "a path protection setup option";
              tailf:cli-optional-in-sequence;
              tailf:cli-prefix-key;
              type empty;
            }
            choice path-option-choice {
              container dynamic {
                tailf:info
                  "setup based on dynamically calculcated path";
                presence "true";
              }
              container explicit {
                tailf:info
                  "setup based on preconfigured path";
                tailf:cli-flatten-container;
                tailf:cli-compact-syntax;
                choice explicit-choice {
                  leaf name {
                    tailf:info
                      "Specify an IP explicit path by name";
                    type string {
                      tailf:info
                        "WORD;;Name of ip explicit path";
                    }
                  }
                  leaf identifier {
                    tailf:info
                      "Specify an IP explicit path by number";
                    type uint16 {
                      tailf:info
                        "<1-65535>;;Number of ip explicit path";
                    }
                  }
                }
              }
            }
            leaf lockdown {
              tailf:info
                "not a candidate for reoptimization";
              tailf:cli-optional-in-sequence;
              type empty;
            }
            leaf verbatim {
              type empty;
            }
          }
          container auto-bw {
            tailf:info
              "Specify mpls tunnel should automatically change bw";
            presence "true";
          }
          container fast-reroute {
            tailf:info
              "Specify mpls tunnel can be fast-rerouted";
            presence "true";
          }
        }
      }
    }
    container domain {
      tailf:info
        "Specify a domain";
      tailf:cli-compact-syntax;
      tailf:cli-sequence-commands {
        tailf:cli-reset-all-siblings;
      }
      leaf domain-name {
        tailf:cli-drop-node-name;
        tailf:cli-optional-in-sequence;
        // NCS drop tailf-common:non-strict-leafref statement
        type string {
          tailf:info
            "WORD;;Domain name";
        }
      }
      leaf path {
        tailf:info
          "Specify a service provider for this interface";
        type string {
          tailf:info
            "WORD;;Specify the color of service provider";
        }
      }
      leaf path-id {
        tailf:cli-break-sequence-commands;
        tailf:info
          "Specify Path ID";
        type uint8 {
          tailf:info
            "<1-62>;;Path ID";
          range "1..62";
        }
      }
      leaf internet-bound {
        tailf:info
          "Specify Internet-bound interface";
        tailf:cli-full-command;
        type empty;
      }
      leaf zero-sla {
        tailf:info
          "Specify if you want this interface to be a 0-sla interface";
        tailf:cli-full-command;
        type empty;
      }
      leaf path-last-resort {
        tailf:info
          "Specify if you want this interface to be a path of last resort";
        tailf:cli-full-command;
        type empty;
      }
    }
  }

  grouping ncs_rpc_notif_interface-ethernet-pre-grouping {
    leaf port-type {
      tailf:info
        "Set port type";
      type enumeration {
        enum "eni" {
          tailf:info
            "Set port-type to ENI";
        }
        enum "nni" {
          tailf:info
            "Set port-type to NNI";
        }
        enum "uni" {
          tailf:info
            "Set port-type to UNI";
        }
      }
    }
    container platform {
      tailf:info
        "Configure platform";
      container ring {
        tailf:info
          "Configure ring entries commands";
        leaf rx {
          tailf:info
            "Configure receiver ring entries";
          type uint16 {
            tailf:info
              "<1-4096>;;Number of ring entries for the Rx ring";
            range "1..4096";
          }
        }
        leaf tx {
          tailf:info
            "Configure transmit ring entries";
          type uint16 {
            tailf:info
              "<1-4096>;;Number of ring entries for the Tx ring";
            range "1..4096";
          }
        }
      }
    }
    container encapsulation {
      tailf:info
        "Set encapsulation type for an interface";
      container dot1Q {
        tailf:info
          "IEEE 802.1Q Virtual LAN";
        tailf:cli-compact-syntax;
        tailf:cli-sequence-commands;
        leaf vlan-id {
          tailf:cli-drop-node-name;
          type uint16 {
            tailf:info
              "<1-4094>;;IEEE 802.1Q VLAN ID required";
            range "1..4094";
          }
        }
        leaf second-dot1q {
          tailf:info
            "Configure this subinterface as a 1Q-in-1Q subinterface";
          tailf:cli-optional-in-sequence;
          tailf:cli-full-command;
          type union {
            type enumeration {
              enum "any" {
                tailf:info
                  "All Inner VLAN IDs not configured on another subinterface";
              }
            }
            type string {
              tailf:info
                "Second (inner) VLAN IDs e.g. 100,200-300,400,500-600";
            }
          }
        }
        leaf native {
          tailf:info
            "Make this as native vlan";
          type empty;
        }
      }
    }
  }

  grouping ncs_rpc_notif_interface-ethernet-grouping0 {
    container mac {
      tailf:info
        "MAC interface commands";
      list access-group {
        tailf:info
          "MAC access-group configuration commands";
        tailf:cli-suppress-mode;
        tailf:cli-delete-when-empty;
        tailf:cli-compact-syntax;
        tailf:cli-sequence-commands;
        key "direction";
        leaf direction {
          type enumeration {
            enum "in" {
              tailf:info
                "Apply to Ingress";
            }
            enum "out" {
              tailf:info
                "Apply to Egress";
            }
          }
        }
        leaf access-list {
          tailf:cli-drop-node-name;
          tailf:cli-prefix-key;
          // NCS drop tailf-common:non-strict-leafref statement
          type string {
            tailf:info
              "WORD;;ACL name";
          }
        }
      }
    }
    container spanning-tree {
      tailf:info
        "Spanning Tree Subsystem";
      leaf bpdufilter {
        tailf:info
          "Don't send or receive BPDUs on this interface";
        type enumeration {
          enum "disable" {
            tailf:info
              "Disable BPDU filtering for this interface";
          }
          enum "enable" {
            tailf:info
              "Enable BPDU filtering for this interface";
          }
        }
      }
      container bpduguard {
        tailf:info
          "Don't accept BPDUs on this interface";
        choice bpduguard-choice {
          leaf disable {
            tailf:info
              "Disable BPDU guard for this interface";
            type empty;
          }
          leaf enable {
            type empty;
            tailf:info
              "Enable BPDU guard for this interface";
          }
        }
      }
      leaf cost {
        tailf:info
          "To set the path cost of the interface";
        tailf:cli-full-command;
        type uint32 {
          range "1..200000000";
        }
      }
      leaf guard {
        tailf:info
          "Change an interface's spanning tree guard mode";
        tailf:cli-full-command;
        type enumeration {
          enum "loop" {
            tailf:info
              "Set guard mode to loop guard on interface";
          }
          enum "none" {
            tailf:info
              "Set guard mode to none";
          }
          enum "root" {
            tailf:info
              "Set guard mode to root guard on interface";
          }
        }
      }
      leaf link-type {
        tailf:info
          "Specify a link type for spanning tree tree protocol use";
        tailf:cli-full-command;
        type enumeration {
          enum "auto" {
            tailf:code-name "link_type_auto";
            tailf:info
              "Determine link type based on media duplex of this interface";
          }
          enum "none" {
            tailf:info
              "Consider the interface as point-to-point";
          }
          enum "point-to-point" {
            tailf:info
              "Consider the interface as point-to-point";
          }
          enum "root" {
            tailf:info
              "Consider the interface as shared";
          }
        }
      }
      container mst {
        tailf:info
          "Multiple spanning tree";
        choice mst-choice {
          list instance-range {
            tailf:cli-drop-node-name;
            tailf:cli-suppress-mode;
            tailf:cli-delete-when-empty;
            tailf:cli-compact-syntax;
            tailf:cli-range-list-syntax;
            key "id";
            leaf id {
              type uint16 {
                tailf:info
                  "MST instance list, example 0,2-4,6,8-12";
              }
            }
            leaf cost {
              tailf:info
                "Change the interface spanning tree path cost for an instance";
              type uint32 {
                tailf:info
                  "<1-200000000>;;Change the interface spanning tree path cost for an instance";
                range "1..200000000";
              }
            }
            leaf port-priority {
              tailf:info
                "Change the spanning tree port priority for an instance";
              type uint16 {
                tailf:info
                  "<0-240>;;port priority in increments of 16";
                range "0..240" {
                  tailf:step "16";
                }
              }
            }
          }
          leaf pre-standard {
            tailf:info
              "Force pre-standard MST BPDU transmission on port";
            type empty;
          }
        }
      }
      container portfast {
        tailf:info
          "Spanning tree portfast options";
        tailf:cli-compact-syntax;
        tailf:cli-delete-when-empty;
        presence "true";
        choice portfast-choice {
          leaf disable {
            tailf:info
              "Disable portfast for this interface";
            type empty;
          }
          leaf network {
            tailf:info
              "Enable portfast network on the interface";
            type empty;
          }
          case trunk-mode {
            leaf edge {
              tailf:info
                "Enable portfast edge on the interface";
              type empty;
            }
            leaf trunk {
              tailf:info
                "Enable portfast edge on the interface even in trunk mode";
              type empty;
            }
          }
        }
      }
      container loopguard {
        tailf:info
          "Spanning tree loopguard options";
        leaf default {
          tailf:info
            "Enable loopguard by default on all ports";
          type empty;
        }
      }
    }
    container srr-queue {
      tailf:info
        "Configure shaped round-robin transmit queues";
      container bandwidth {
        tailf:info
          "Configure shared bandwidth";
        leaf limit {
          tailf:info
            "Configure bandwidth-limit for this interface";
          type uint8 {
            tailf:info
              "<10-90>;;enter bandwidth limit for interface as percentage";
            range "10..90";
          }
        }
        container shape {
          tailf:info
            "Configure shaping on transmit queues";
          tailf:cli-compact-syntax;
          tailf:cli-sequence-commands;
          tailf:cli-reset-container;
          leaf weight1 {
            tailf:cli-drop-node-name;
            tailf:cli-incomplete-command;
            type uint16 {
              tailf:info
                "<0-65535>;;enter bandwidth weight for queue id 1";
            }
          }
          leaf weight2 {
            tailf:cli-drop-node-name;
            tailf:cli-incomplete-command;
            type uint16 {
              tailf:info
                "<0-65535>;;enter bandwidth weight for queue id 2";
            }
          }
          leaf weight3 {
            tailf:cli-drop-node-name;
            tailf:cli-incomplete-command;
            type uint16 {
              tailf:info
                "<0-65535>;;enter bandwidth weight for queue id 3";
            }
          }
          leaf weight4 {
            tailf:cli-drop-node-name;
            type uint16 {
              tailf:info
                "<0-65535>;;enter bandwidth weight for queue id 4";
            }
          }
        }
        container share {
          tailf:info
            "Configure shared bandwidth";
          tailf:cli-compact-syntax;
          tailf:cli-sequence-commands;
          tailf:cli-reset-container;
          leaf weight1 {
            tailf:cli-drop-node-name;
            tailf:cli-incomplete-command;
            type uint8 {
              tailf:info
                "<1-255>;;enter bandwidth weight for queue id 1";
              range "1..255";
            }
          }
          leaf weight2 {
            tailf:cli-drop-node-name;
            tailf:cli-incomplete-command;
            type uint8 {
              tailf:info
                "<1-255>;;enter bandwidth weight for queue id 2";
              range "1..255";
            }
          }
          leaf weight3 {
            tailf:cli-drop-node-name;
            tailf:cli-incomplete-command;
            type uint8 {
              tailf:info
                "<1-255>;;enter bandwidth weight for queue id 3";
              range "1..255";
            }
          }
          leaf weight4 {
            tailf:cli-drop-node-name;
            type uint8 {
              tailf:info
                "<1-255>;;enter bandwidth weight for queue id 4";
              range "1..255";
            }
          }
        }
      }
    }
    leaf queue-set {
      tailf:info
        "Choose a queue set for this queue";
      type uint8 {
        tailf:info
          "<1-2>;;the qset to which this port is mapped";
      }
    }
    container dot1x {
      tailf:info
        "Interface Config Commands for IEEE 802.1X";
      container pae {
        tailf:info
          "Set 802.1x interface pae type";
        leaf authenticator {
          tailf:info
            "Set pae type as Authenticator";
          type empty;
        }
      }
      container timeout {
        tailf:info
          "Various Timeouts";
        leaf quiet-period {
          tailf:info
            "QuietPeriod in Seconds";
          type uint16 {
            tailf:info
              "<1-65535>;;Enter a value between 1 and 65535";
            range "1..65535";
          }
        }
        leaf tx-period {
          tailf:info
            "Timeout for supplicant retries";
          type uint16 {
            tailf:info
              "<1-65535>;;Enter a value between 1 and 65535";
            range "1..65535";
          }
        }
        leaf supp-period {
          tailf:info
            "Timeout for supplicant reply";
          type uint16 {
            tailf:info
              "<1-65535>;;Enter a value between 1 and 65535";
            range "1..65535";
          }
        }
        leaf ratelimit-period {
          tailf:info
            "Ratelimit Period in seconds";
          type uint16 {
            tailf:info
              "<1-65535>;;Enter a value between 1 and 65535";
            range "1..65535";
          }
        }
        leaf held-period {
          tailf:info
            "Timeout for authentication retries";
          type uint16 {
            tailf:info
              "<1-65535>;;Enter a value between 1 and 65535";
            range "1..65535";
          }
        }
      }
    }
    leaf media-type {
      tailf:info
        "Media type";
      tailf:cli-full-command;
      tailf:meta-data "inject-interface-config-duplex" {
        tailf:meta-value "duplex :: duplex :: after :: create";
      }
      tailf:meta-data "inject-interface-config-speed" {
        tailf:meta-value "speed :: speed :: after :: create";
      }
      tailf:ned-data "../duplex" {
        tailf:xpath-root 3;
        tailf:transaction to;
      }
      tailf:ned-data "../speed" {
        tailf:xpath-root 3;
        tailf:transaction to;
      }
      type enumeration {
        enum "rj45" {
          tailf:info
            "Copper";
        }
        enum "sfp" {
          tailf:info
            "Fiber";
        }
        enum "auto-select" {
          tailf:info
            "Auto Select";
        }
        enum "gbic";
      }
      default "auto-select";
    }
    container mdix {
      tailf:info
        "Set Media Dependent Interface with Crossover";
      leaf auto {
        tailf:info
          "Enable automatic MDI crossover detection on this interface";
        tailf:cli-boolean-no;
        type boolean;
        default "true";
      }
    }
    leaf channel-protocol {
      tailf:info
        "Select the channel protocol (LACP, PAgP)";
      type enumeration {
        enum "lacp" {
          tailf:info
            "Prepare interface for LACP protocol";
        }
        enum "pagp" {
          tailf:info
            "Prepare interface for PAgP protocol";
        }
      }
    }
    container lacp {
      tailf:info
        "LACP interface subcommands";
      leaf rate {
        tailf:info
          "Rate at which the LACP packets are requested to be ingressed to this interface";
        type enumeration {
          enum "fast" {
            tailf:info
              "Request LACP packets to be ingressed at the 1 second rate for this interface";
          }
          enum "normal" {
            tailf:info
              "Request LACP packets to be ingressed at the 30 second rate once the link is established";
          }
        }
        default "normal";
      }
      leaf fast-switchover {
        tailf:info
          "Enable LACP fast switchover on this port channel";
        type empty;
      }
      leaf min-bundle {
        tailf:info
          "LACP minimum number of ports to bundle in this port channel";
        type uint8 {
          tailf:info
            "<1-8>;;Minimum number of ports to bundle in this Port Channel";
          range "1..8";
        }
      }
      leaf max-bundle {
        tailf:info
          "LACP maximum number of ports to bundle in this port channel";
        type uint8 {
          tailf:info
            "<1-8>;;Max number of ports to bundle in this Port Channel";
          range "1..8";
        }
      }
    }
    container ethernet {
      tailf:info
        "Ethernet interface parameters";
      container oam-conf {
        tailf:cli-drop-node-name;
        container oam {
          tailf:info
            "To enable Ethernet Link OAM";
          leaf max-rate {
            tailf:info
              "Maximum transmission rate(number of OAMPDUs per second)";
            type uint8 {
              tailf:info
                "<1-10>;;Set the rate in number of packets per second";
              range "1..10";
            }
          }
          leaf min-rate {
            tailf:info
              "Minimum transmission rate(one OAMPDU per number of seconds)";
            type uint8 {
              tailf:info
                "<1-10>;;Set the rate in number of seconds";
              range "1..10";
            }
          }
          leaf mode {
            tailf:info
              "Ethernet OAM client mode";
            type enumeration {
              enum "active" {
                tailf:info
                  "Active mode";
              }
              enum "passive" {
                tailf:info
                  "Passive mode";
              }
            }
          }
          container remote-loopback {
            tailf:info
              "Ethernet OAM Remote Loopback";
            leaf supported {
              tailf:info
                "Support remote loopback functionality";
              type empty;
            }
          }
          leaf timeout {
            tailf:info
              "Ethernet OAM client link timeout setting";
            type uint8 {
              tailf:info
                "<2-30>;;Set timeout value in number of seconds";
              range "2..30";
            }
            default "5";
          }
          container link-monitor {
            tailf:info
              "Ethernet OAM Link Monitor";
            leaf supported {
              tailf:info
                "Support link monitoring on the interface";
              tailf:cli-boolean-no;
              tailf:cli-full-command;
              type boolean;
              default "true";
            }
            leaf on {
              tailf:info
                "Enable link monitoring on the interface";
              tailf:cli-boolean-no;
              tailf:cli-full-command;
              type boolean;
              default "true";
            }
            container receive-crc {
              tailf:info
                "Received frames with CRC errors in a period";
              leaf window {
                tailf:info
                  "Window size of a polling period";
                type uint16 {
                  tailf:info
                    "<10-1800>;;Set window size in multiple of 100 milliseconds (will be rounded off to second)";
                  range "10..1800";
                }
              }
            }
          }
        }
      }
      leaf oam {
        tailf:info
          "Operations, Administration and Maintenance";
        type empty;
      }
      container dot1ad {
        tailf:info
          "dot1ad port";
        choice dot1ad-choice {
          leaf nni {
            tailf:info
              "dot1ad nni port";
            type empty;
          }
          container uni {
            tailf:info
              "dot1ad uni";
            choice uni-choice {
              container c-port {
                tailf:info
                  "dot1ad uni customer bridge port";
                tailf:cli-delete-when-empty;
                presence "true";
                leaf isolate {
                  tailf:info
                    "split horizon";
                  type empty;
                }
              }
              container s-port {
                tailf:info
                  "dot1ad uni s bridge port";
                tailf:cli-delete-when-empty;
                presence "true";
                leaf isolate {
                  tailf:info
                    "split horizon";
                  type empty;
                }
              }
            }
          }
        }
      }
      container cfm {
        tailf:info
          "Ethernet CFM interface commands";
        container mip {
          tailf:info
            "Maintenance Intermediate Point";
          list level {
            tailf:info
              "Maintenance Level";
            tailf:cli-suppress-mode;
            tailf:cli-delete-when-empty;
            tailf:cli-incomplete-command;
            key "level";
            leaf level {
              type uint8 {
                tailf:info
                  "<0-7>;;maintenance level number";
                range "0..7";
              }
            }
            leaf-list vlan {
              tailf:info
                "Specify vlan (range 1-4094)";
              tailf:cli-range-list-syntax;
              type uint16 {
                tailf:info
                  "<1-4094>;;VLAN id";
                range "1..4094";
              }
            }
          }
        }
        container mep {
          tailf:info
            "Maintenance End Point";
          list mep-list {
            tailf:cli-drop-node-name;
            tailf:cli-suppress-mode;
            tailf:cli-delete-when-empty;
            tailf:cli-compact-syntax;
            tailf:cli-sequence-commands;
            key "mpid";
            leaf mpid {
              tailf:info
                "Maintenance End Point Identifier";
              tailf:cli-expose-key-name;
              type uint16 {
                tailf:info
                  "<1-8191>;;Maintenance End Point Identifier";
                range "1..8191";
              }
            }
            leaf domain {
              tailf:info
                "maintenance domain";
              tailf:cli-prefix-key;
              type string {
                tailf:info
                  "WORD;;maintenance domain name";
              }
            }
            leaf vlan {
              tailf:info
                "Specify vlan (range 1-4094)";
              tailf:cli-optional-in-sequence;
              tailf:cli-full-command;
              type uint16 {
                tailf:info
                  "<1-4094>;;VLAN id";
              }
            }
            container service {
              tailf:info
                "Maintenance Association within Domain";
              tailf:cli-flatten-container;
              tailf:cli-compact-syntax;
              choice service-choice {
                leaf short-ma-name {
                  tailf:cli-drop-node-name;
                  type string {
                    tailf:info
                      "WORD;;service instance id - short MA name";
                  }
                }
                leaf number {
                  tailf:info
                    "Maintenance Association number value";
                  type uint16 {
                    tailf:info
                      "<0-65535>;;Maintenance Association number";
                  }
                }
              }
            }
          }
        }
        leaf enable {
          tailf:info
            "CFM interface enabling";
          tailf:cli-boolean-no;
          tailf:cli-full-command;
          type boolean;
          default "true";
        }
        leaf interface {
          tailf:info
            "CFM interface enable";
          tailf:cli-boolean-no;
          type boolean;
        }
      }
      container uni {
        tailf:info
          "Configure Ether UNI";
        leaf id {
          tailf:info
            "Configure Ether UNI ID";
          type string {
            tailf:info
              "WORD;;UNI ID of length <1-64>";
            length "0..64";
          }
        }
        container bundle {
          tailf:info
            "bundling service without multiplexing";
          tailf:cli-delete-when-empty;
          presence "true";
          leaf all-to-one {
            tailf:info
              "all-to-one bundling service";
            type empty;
          }
        }
      }
      container lmi {
        tailf:info
          "Ethernet LMI interface commands";
        leaf interface {
          tailf:info
            "Enable Ethernet LMI on this interface";
          tailf:cli-boolean-no;
          type boolean;
        }
      }
    }
    container negotiation {
      tailf:info
        "Select autonegotiation mode";
      leaf auto {
        tailf:info
          "Enable link autonegotiation";
        tailf:cli-boolean-no;
        type boolean;
      }
    }
    container synchronous {
      tailf:info
        "Synchronous";
      leaf mode {
        tailf:info
          "Mode";
        type empty;
      }
    }
    container esmc {
      tailf:info
        "Ethernet Synchronization Messaging Channe";
      container mode {
        tailf:info
          "ESMC mode";
        leaf direction {
          tailf:cli-drop-node-name;
          tailf:cli-full-command;
          type enumeration {
            enum "rx" {
              tailf:info
                "ESMC receive-only mode";
            }
            enum "tx" {
              tailf:info
                "ESMC transmit-only mode";
            }
          }
        }
        leaf ql-disabled {
          tailf:info
            "QL disabled";
          type empty;
        }
      }
    }
    leaf speed {
      tailf:info
        "Configure speed operation.";
      tailf:cli-no-value-on-delete;
      tailf:cli-full-command;
      tailf:cli-diff-dependency "../negotiation" {
        tailf:xpath-root 3;
      }
      tailf:cli-diff-dependency "../media-type" {
        tailf:xpath-root 3;
        tailf:cli-trigger-on-set;
      }
      tailf:meta-data "patch-interface-speed";
      type enumeration {
        enum "10" {
          tailf:info
            "Force 10 Mbps operation";
        }
        enum "100" {
          tailf:info
            "Force 100 Mbps operation";
        }
        enum "1000" {
          tailf:info
            "Force 1000 Mbps operation";
        }
        enum "10000" {
          tailf:info
            "Force 10000 Mbps operation";
        }
        enum "auto" {
          tailf:info
            "Enable AUTO speed configuration";
        }
        enum "nonegotiate" {
          tailf:info
            "Do not negotiate speed";
        }
      }
      default "auto";
    }
    leaf duplex {
      tailf:info
        "Configure duplex operation.";
      tailf:cli-no-value-on-delete;
      tailf:cli-full-command;
      tailf:cli-diff-dependency "../negotiation" {
        tailf:xpath-root 3;
      }
      tailf:cli-diff-dependency "../speed" {
        tailf:xpath-root 3;
      }
      type enumeration {
        enum "auto" {
          tailf:code-name "duplex_auto";
          tailf:info
            "Enable AUTO duplex configuration";
        }
        enum "full" {
          tailf:code-name "duplex_full";
          tailf:info
            "Force full duplex operation";
        }
        enum "half" {
          tailf:code-name "duplex_half";
          tailf:info
            "Force half-duplex operation";
        }
      }
      default "auto";
    }
    uses ncs_rpc_notif_xconnect-interface-grouping;
    container pppoe {
      tailf:info
        "pppoe interface subcommands";
      container enable {
        tailf:info
          "Enable pppoe";
        presence "true";
        leaf group {
          tailf:info
            "attach a BBA group";
          type union {
            type string {
              tailf:info
                "WORD;;BBA Group name";
            }
            type enumeration {
              enum "global" {
                tailf:info
                  "Attach global PPPoE group";
              }
            }
          }
        }
      }
      leaf max-sessions {
        tailf:info
          "Maximum PPPOE sessions";
        type uint16 {
          tailf:info
            "<1-4085>;;Maximum PPPOE sessions";
          range "1..4085";
        }
      }
    }
    container vlan-id {
      tailf:info
        "Process VLAN-encapsulated packets with a specific VLAN ID";
      list dot1q {
        tailf:info
          "802.1Q VLAN";
        tailf:cli-mode-name "config-if-vlan-id";
        tailf:cli-exit-command "exit-vlan-config" {
          tailf:info
            "Exit from VLAN configuration mode";
        }
        key "id";
        leaf id {
          type uint16 {
            tailf:info
              "<1-4094>;;VLAN ID";
            range "1..4094";
          }
        }
      }
    }
    container service {
      tailf:info
        "Configure Ether Service";
      list instance {
        tailf:info
          "Configure Ether Service Instance";
        tailf:cli-mode-name "config-if-srv";
        tailf:cli-compact-syntax;
        tailf:cli-sequence-commands;
        tailf:cli-incomplete-command;
        key "id";
        leaf id {
          tailf:cli-diff-dependency "../../../service-policy/output" {
            tailf:xpath-root 3;
            tailf:cli-trigger-on-set;
          }
          tailf:cli-diff-dependency "../../../service-policy/input" {
            tailf:xpath-root 3;
            tailf:cli-trigger-on-set;
          }
          tailf:cli-diff-dependency "../../../cdp/enable" {
            tailf:xpath-root 3;
            tailf:cli-trigger-on-set;
          }
          tailf:cli-diff-dependency "../../../ip/no-address/address" {
            tailf:xpath-root 3;
            tailf:cli-trigger-on-set;
          }
          type uint32 {
            tailf:info
              "<1-4294967295>;;Service Instance Identifier";
            range "1..4294967295";
          }
        }
        leaf trunk {
          tailf:cli-optional-in-sequence;
          tailf:cli-prefix-key;
          type empty;
        }
        leaf ethernet {
          tailf:info
            "Configure an Ethernet Instance";
          tailf:cli-hide-in-submode;
          type empty;
        }
        leaf ethernet-evc-name {
          tailf:cli-drop-node-name;
          tailf:cli-hide-in-submode;
          // NCS drop tailf-common:non-strict-leafref statement
          type string {
            tailf:info
              "WORD;;Attach an EVC to the service instance";
          }
        }
        leaf description {
          tailf:cli-break-sequence-commands;
          tailf:info
            "Service instance specific description";
          tailf:cli-multi-value;
          tailf:cli-preformatted;
          tailf:cli-full-command;
          type string {
            tailf:info
              "LINE;;Up to 240 characters describing this service instance";
            length "0..240";
          }
        }
        container encapsulation {
          tailf:info
            "Configure ethernet frame match criteria";
          choice encapsulation-choice {
            container dot1q {
              tailf:info
                "IEEE 802.1Q Virtual LAN or S-VLAN";
              tailf:cli-compact-syntax;
              tailf:cli-sequence-commands {
                tailf:cli-reset-siblings;
              }
              tailf:cli-diff-dependency "../untagged" {
                tailf:xpath-root 3;
                tailf:cli-trigger-on-set;
              }
              uses ncs_rpc_notif_if-srv-encapsulation-dot1q-grouping;
            }
            container dot1ad {
              tailf:info
                "IEEE 802.1ad VLAN-tagged packets";
              tailf:cli-compact-syntax;
              tailf:cli-sequence-commands {
                tailf:cli-reset-siblings;
              }
              leaf-list id {
                tailf:cli-drop-node-name;
                tailf:cli-replace-all;
                tailf:cli-range-list-syntax;
                type uint16 {
                  tailf:info
                    "<1-4094>;;VLAN id";
                  range "1..4094";
                }
              }
              leaf-list dot1q {
                tailf:info
                  "IEEE 802.1Q VLAN-tagged packets";
                tailf:cli-range-list-syntax;
                tailf:cli-replace-all;
                type uint16 {
                  tailf:info
                    "<1-4094>;;Single VLAN id";
                  range "1..4094";
                }
              }
            }
            container untagged {
              tailf:info
                "Untagged encapsulation";
              tailf:cli-compact-syntax;
              tailf:cli-sequence-commands {
                tailf:cli-reset-siblings;
              }
              tailf:cli-delete-when-empty;
              tailf:cli-diff-dependency "../dot1q" {
                tailf:xpath-root 3;
                tailf:cli-trigger-on-set;
              }
              tailf:meta-data "diff-interface-move-encap-untagged-1" {
                tailf:meta-value "no rewrite ingress tag pop \\d+ symmetric :: before :: encapsulation untagged";
              }
              presence "true";
              leaf comma {
                tailf:info
                  "comma";
                tailf:alt-name ",";
                type empty;
              }
              container dot1q {
                tailf:info
                  "IEEE 802.1Q Virtual LAN or S-VLAN";
                tailf:cli-flatten-container;
                tailf:cli-compact-syntax;
                tailf:cli-sequence-commands {
                  tailf:cli-reset-siblings;
                }
                uses ncs_rpc_notif_if-srv-encapsulation-dot1q-grouping;
              }
            }
            container default {
              tailf:info
                "catch-all unconfigured encapsulation";
              presence "true";
            }
          }
        }
        container rewrite {
          tailf:info
            "Configure ethernet rewrite criteria";
          container ingress {
            tailf:info
              "Ingress Rewrite";
            container tag {
              tailf:info
                "Configure Rewrite Tag";
              tailf:cli-compact-syntax;
              tailf:cli-sequence-commands {
                tailf:cli-reset-siblings;
              }
              tailf:cli-diff-dependency "../../../encapsulation" {
                tailf:xpath-root 3;
              }
              choice tag-choice {
                leaf pop {
                  tailf:info
                    "Pop the tag";
                  type enumeration {
                    enum "1" {
                      tailf:info
                        "Pop the outermost tag";
                    }
                    enum "2" {
                      tailf:info
                        "Pop two outermost tags";
                    }
                  }
                }
                case push {
                  leaf push {
                    tailf:info
                      "Rewrite Operation of push";
                    type enumeration {
                      enum "dot1ad" {
                        tailf:info
                          "Push dot1ad tag";
                      }
                      enum "dot1q" {
                        tailf:info
                          "Push dot1q tag";
                      }
                    }
                  }
                  leaf vlan-id {
                    tailf:cli-drop-node-name;
                    type uint16 {
                      tailf:info
                        "<1-4094>;;VLAN id";
                      range "1..4094";
                    }
                  }
                }
                case translate {
                  leaf translate {
                    tailf:info
                      "Translate Tag";
                    tailf:cli-incomplete-command;
                    type enumeration {
                      enum "1-to-1" {
                        tailf:info
                          "Translate 1-to-1";
                      }
                      enum "1-to-2" {
                        tailf:info
                          "Translate 1-to-2";
                      }
                      enum "2-to-1" {
                        tailf:info
                          "Translate 2-to-1";
                      }
                      enum "2-to-2" {
                        tailf:info
                          "Translate 2-to-2";
                      }
                    }
                  }
                  leaf dot1ad {
                    tailf:info
                      "Ethertype dot1ad of the translation";
                    tailf:cli-optional-in-sequence;
                    type uint16 {
                      tailf:info
                        "<1-4094>;;VLAN id";
                      range "1..4094";
                    }
                  }
                  leaf dot1q {
                    tailf:info
                      "Ethertype dot1q of the translation";
                    type uint16 {
                      tailf:info
                        "<1-4094>;;VLAN id";
                      range "1..4094";
                    }
                  }
                  leaf second-dot1q {
                    tailf:info
                      "Second dot1q tag";
                    tailf:cli-optional-in-sequence;
                    type uint16 {
                      tailf:info
                        "<1-4094>;;VLAN id";
                      range "1..4094";
                    }
                  }
                  leaf vlan-type {
                    tailf:info
                      "Vlan protocol type";
                    tailf:cli-optional-in-sequence;
                    type enumeration {
                      enum "0x88A8" {
                        tailf:info
                          "vlan protocol type 0x88A8";
                      }
                      enum "0x9100" {
                        tailf:info
                          "vlan protocol type 0x9100";
                      }
                      enum "0x9200" {
                        tailf:info
                          "vlan protocol type 0x9200";
                      }
                    }
                  }
                }
              }
              leaf mode {
                tailf:cli-drop-node-name;
                type enumeration {
                  enum "symmetric" {
                    tailf:info
                      "Tag egress packets as specified in encapsulation";
                  }
                }
              }
            }
          }
        }
        container storm-control {
          tailf:info
            "storm configuration";
          container broadcast {
            tailf:info
              "Broadcast address storm control";
            leaf cir {
              tailf:info
                "Committed Information Rate";
              type string {
                tailf:info
                  "<8000-1000000000>;;Target Bit Rate (biTs per second)";
              }
            }
          }
          container multicast {
            tailf:info
              "Multicast address storm control";
            leaf cir {
              tailf:info
                "Committed Information Rate";
              type string {
                tailf:info
                  "<8000-1000000000>;;Target Bit Rate (biTs per second)";
              }
            }
          }
        }
        leaf group {
          tailf:info
            "Join a service group";
          tailf:cli-full-command;
          tailf:cli-diff-dependency "/ios:service-group" {
            tailf:xpath-root 3;
          }
          type uint16 {
            tailf:info
              "<1-65532>;;Service group ID number";
            range "1..65532";
          }
        }
        container errdisable {
          tailf:info
            "Configure error disable";
          container recovery {
            tailf:info
              "enable auto recovery";
            container cause {
              tailf:info
                "error disable cause";
              leaf mac-security {
                tailf:info
                  "mac-security violation";
                type uint32 {
                  tailf:info
                    "<30-86400>;;timer interval(sec)";
                  range "30..86400";
                }
              }
            }
          }
        }
        container snmp {
          tailf:info
            "Modify SNMP service instance parameters";
          container trap {
            tailf:info
              "Allow a specific SNMP trap";
            leaf link-status {
              tailf:info
                "Allow SNMP LINKUP and LINKDOWN traps";
              type empty;
            }
          }
          container ifindex {
            tailf:info
              "Persist ifindex for the service instance";
            leaf persist {
              tailf:info
                "Enable/Disable ifIndex persistence";
              type empty;
            }
          }
        }
        leaf shutdown {
          tailf:info
            "Take the Service Instance out of Service";
          type empty;
        }
        container mac {
          tailf:info
            "Commands for MAC Address-based features";
          container security {
            tailf:info
              "MAC Security commands";
            tailf:cli-display-separated;
            tailf:cli-delete-when-empty;
            presence "true";
            list address {
              tailf:info
                "MAC Address";
              tailf:cli-suppress-mode;
              tailf:cli-delete-when-empty;
              key "operation mac-address";
              leaf operation {
                type enumeration {
                  enum "deny" {
                    tailf:info
                      "Specify an address that must not be learnt";
                  }
                  enum "permit" {
                    tailf:info
                      "Specify an address to statically configure in the MAC table";
                  }
                }
              }
              leaf mac-address {
                type string {
                  tailf:info
                    "H.H.H;;Specify the 48-bit MAC Address to deny/permit";
                }
              }
            }
            container maximum {
              tailf:info
                "Configure an upper bound";
              leaf addresses {
                tailf:info
                  "Maximum addresses that can be learnt on this service instance";
                type uint16 {
                  tailf:info
                    "<1-1000>;;Address count";
                  range "1..1000";
                }
              }
            }
            leaf violation {
              tailf:info
                "Configure the response when a MAC security policy is violated";
              tailf:cli-full-command;
              type enumeration {
                enum "protect" {
                  tailf:info
                    "Protect mode - don't report violations, drop violating frames";
                }
                enum "restrict" {
                  tailf:info
                    "Restrict mode - report violations, drop violating frames";
                }
              }
            }
          }
          container static {
            tailf:info
              "static MAC address";
            list address {
              tailf:info
                "MAC Address";
              tailf:cli-suppress-mode;
              tailf:cli-delete-when-empty;
              key "mac-addr";
              leaf mac-addr {
                type string {
                  tailf:info
                    "H.H.H;;Specify the 48-bit Static MAC Address";
                }
              }
            }
          }
          list access-group {
            tailf:info
              "Specify access control for packets";
            tailf:cli-suppress-mode;
            tailf:cli-delete-when-empty;
            tailf:cli-compact-syntax;
            tailf:cli-sequence-commands;
            key "direction";
            leaf direction {
              type enumeration {
                enum "in" {
                  tailf:info
                    "Apply to Ingress";
                }
                enum "out" {
                  tailf:info
                    "Apply to Egress";
                }
              }
            }
            leaf access-list {
              tailf:cli-drop-node-name;
              tailf:cli-prefix-key;
              type string {
                tailf:info
                  "WORD;;ACL name";
              }
            }
          }
        }
        container l2protocol {
          tailf:info
            "Configure l2 control protocol processing";
          container peer {
            tailf:info
              "peer L2 control protocol packets as data";
            tailf:cli-delete-when-empty;
            presence "true";
            leaf-list protocol {
              tailf:cli-drop-node-name;
              tailf:cli-flat-list-syntax;
              type l2protocol-type;
            }
          }
          container forward {
            tailf:info
              "forward L2 control protocol packets as data";
            tailf:cli-delete-when-empty;
            presence "true";
            leaf-list protocol {
              tailf:cli-drop-node-name;
              tailf:cli-flat-list-syntax;
              type l2protocol-type;
            }
          }
          container tunnel {
            tailf:info
              "tunnel L2 control protocol packets as data";
            tailf:cli-delete-when-empty;
            presence "true";
            leaf-list protocol {
              tailf:cli-drop-node-name;
              tailf:cli-flat-list-syntax;
              type l2protocol-type;
            }
          }
        }
        container bridge-domain {
          tailf:info
            "Bridge-domain";
          tailf:cli-compact-syntax;
          tailf:cli-sequence-commands {
            tailf:cli-reset-all-siblings;
          }
          tailf:cli-diff-dependency "../encapsulation" {
            tailf:xpath-root 3;
          }
          leaf from-encapsulation {
            tailf:info
              "Derive bridge domains from encapsulation vlan list,";
            tailf:cli-optional-in-sequence;
            tailf:cli-full-command;
            type empty;
          }
          leaf bridge-id {
            tailf:cli-drop-node-name;
            // NCS drop tailf-common:non-strict-leafref statement
            type uint16 {
              tailf:info
                "<1-16384>;;Bridge-domain number";
              range "1..16384";
            }
          }
          container split-horizon {
            tailf:info
              "Configure this port as a member of a split horizon group";
            tailf:cli-flatten-container;
            leaf group {
              tailf:info
                "Split-horizon group";
              type uint8 {
                tailf:info
                  "<0-2>;;Split-horizon group number";
                range "0..2";
              }
            }
          }
        }
        container service-policy {
          tailf:info
            "Attach a policy-map to an EFP";
          list input {
            tailf:info
              "service policy input";
            tailf:cli-suppress-mode;
            tailf:cli-delete-when-empty;
            max-elements 1;
            key "name";
            leaf name {
              // NCS drop tailf-common:non-strict-leafref statement
              type string {
                tailf:info
                  "WORD;;input Policy-map name";
              }
            }
          }
          list output {
            tailf:info
              "service policy output";
            tailf:cli-suppress-mode;
            tailf:cli-delete-when-empty;
            max-elements 1;
            key "name";
            leaf name {
              // NCS drop tailf-common:non-strict-leafref statement
              type string {
                tailf:info
                  "WORD;;output Policy-map name";
              }
            }
          }
        }
        uses ncs_rpc_notif_xconnect-grouping {
          refine "xconnect-choice/xconnect/xconnect" {
            tailf:cli-diff-dependency "../encapsulation" {
              tailf:xpath-root 3;
            }
          }
          refine "xconnect-choice/xconnect/xconnect/mtu" {
            tailf:cli-diff-dependency "../../../../mtu" {
              tailf:xpath-root 3;
            }
          }
        }
        container cfm {
          tailf:info
            "Ethernet CFM EFP subcommands";
          container mip {
            leaf level {
              type uint8 {
                tailf:info
                  "<0-7>;;maintenance level number";
                range "0..7";
              }
            }
          }
          container mep {
            tailf:info
              "Maintenance End Point";
            tailf:cli-add-mode;
            tailf:cli-mode-name "config-if-srv-ecfm-mep";
            tailf:cli-compact-syntax;
            tailf:cli-sequence-commands;
            leaf domain {
              tailf:info
                "Configure a domain for this mep";
              tailf:cli-hide-in-submode;
              tailf:cli-incomplete-command;
              tailf:cli-diff-dependency "/ios:ethernet/cfm/domain" {
                tailf:xpath-root 3;
              }
              type string {
                tailf:info
                  "WORD;;maintenance domain name";
              }
            }
            leaf mpid {
              tailf:info
                "Maintenance End Point Identifier";
              tailf:cli-hide-in-submode;
              type uint16 {
                tailf:info
                  "<1-8191>;;Maintenance End Point Identifier";
                range "1..8191";
              }
            }
            container continuity-check {
              tailf:info
                "Enable Continuity Check for this local MEP";
              tailf:cli-break-sequence-commands;
              container static {
                tailf:info
                  "Verify MEP in received CCM is valid";
                leaf rmep {
                  tailf:info
                    "MEP defined using rmep mpid";
                  type empty;
                }
              }
            }
            container rmep {
              tailf:info
                "Static Remote MEP associated with this DOWN MEP";
              leaf mpid {
                tailf:info
                  "Maintenance End Point Identifier";
                type uint16 {
                  tailf:info
                    "<1-8191>;;Identifier value";
                  range "1..8191";
                }
              }
            }
            leaf cos {
              tailf:info
                "Specify Class of Service sent in CFM mssages for EFP MEP";
              type uint8 {
                tailf:info
                  "<0-7>;;CoS value";
                range "0..7";
              }
            }
          }
        }
        container ethernet-if-srv {
          tailf:cli-drop-node-name;
          container ethernet {
            tailf:info
              "ethernet";
            container lmi {
              tailf:info
                "Configure ether lmi parameters";
              container ce-vlan {
                tailf:info
                  "Configure ether lmi customer vlans";
                leaf-list map {
                  tailf:info
                    "Configure ether lmi ce-vlan/evc map";
                  tailf:cli-replace-all;
                  tailf:cli-range-list-syntax;
                  type union {
                    type uint16 {
                      tailf:info
                        "<1-4094>;;VLAN id";
                      range "1..4094";
                    }
                    type enumeration {
                      enum "default" {
                        tailf:info
                          "Default EFP";
                      }
                      enum "untagged" {
                        tailf:info
                          "Untagged frames";
                      }
                    }
                  }
                }
              }
            }
            container loopback {
              tailf:info
                "Ethernet Dataplane Loopback";
              container permit {
                tailf:info
                  "Allow data plane loopback to be activated";
                leaf external {
                  tailf:info
                    "Allow to loopback the traffic from the wire";
                  type empty;
                }
                leaf internal {
                  tailf:info
                    "Allow to loopback the traffic from the relay";
                  type empty;
                }
              }
            }
          }
        }
      }
    }
    container channel-group {
      tailf:info
        "Add this interface to an Etherchannel group";
      tailf:cli-compact-syntax;
      tailf:cli-sequence-commands {
        tailf:cli-reset-siblings;
      }
      leaf number {
        tailf:cli-drop-node-name;
        tailf:cli-diff-dependency "../../mls/qos/trust" {
          tailf:xpath-root 3;
        }
        tailf:cli-diff-dependency "../../mls" {
          tailf:xpath-root 3;
          tailf:cli-trigger-on-set;
        }
        tailf:cli-diff-dependency "../../ip" {
          tailf:xpath-root 3;
          tailf:cli-trigger-on-set;
        }
        tailf:cli-diff-dependency "../../ipv6" {
          tailf:xpath-root 3;
          tailf:cli-trigger-on-set;
        }
        tailf:cli-diff-dependency "../../service-policy" {
          tailf:xpath-root 3;
          tailf:cli-trigger-on-set;
        }
        tailf:cli-diff-dependency "../../mtu" {
          tailf:xpath-root 3;
          tailf:cli-trigger-on-set;
        }
        tailf:cli-diff-dependency "../../storm-control" {
          tailf:xpath-root 3;
          tailf:cli-trigger-on-set;
        }
        tailf:cli-diff-dependency "../../port-type" {
          tailf:xpath-root 3;
        }
        type uint16 {
          tailf:info
            "<1-512>;;Channel group number";
          range "1..512";
        }
      }
      leaf mode {
        tailf:info
          "Etherchannel Mode of the interface";
        type enumeration {
          enum "active" {
            tailf:info
              "Enable LACP unconditionally";
          }
          enum "auto" {
            tailf:info
              "Enable PAgP only if a PAgP device is detected";
          }
          enum "desirable" {
            tailf:info
              "Enable PAgP unconditionally";
          }
          enum "on" {
            tailf:info
              "Enable Etherchannel only";
          }
          enum "passive" {
            tailf:info
              "Enable LACP only if a LACP device is detected";
          }
        }
      }
    }
    container soak {
      tailf:info
        "Soak hardware link notification";
      container link {
        tailf:info
          "link";
        leaf notification {
          tailf:info
            "notification";
          type uint16 {
            tailf:info
              "<0-300>;;duration";
            range "0..300";
          }
        }
      }
    }
  }

  grouping ncs_rpc_notif_interface-ethernet-grouping {
    uses ncs_rpc_notif_interface-ethernet-grouping0 {
      refine "service/instance/service-policy" {
        tailf:cli-diff-dependency "../../../../../policy-map" {
          tailf:xpath-root 3;
        }
      }
      refine "service/instance/bridge-domain/bridge-id" {
        tailf:cli-diff-dependency "../../../../../../vlan/vlan-list" {
          tailf:xpath-root 3;
        }
      }
      refine "channel-group/number" {
        tailf:cli-diff-dependency "../../../../interface/Port-channel" {
          tailf:xpath-root 3;
        }
      }
    }
  }

  grouping ncs_rpc_notif_sub-interface-ethernet-grouping {
    uses ncs_rpc_notif_interface-ethernet-grouping0 {
      refine "service/instance/service-policy" {
        tailf:cli-diff-dependency "../../../../../../policy-map" {
          tailf:xpath-root 3;
        }
      }
      refine "service/instance/bridge-domain/bridge-id" {
        tailf:cli-diff-dependency "../../../../../../../vlan/vlan-list" {
          tailf:xpath-root 3;
        }
      }
      refine "channel-group/number" {
        tailf:cli-diff-dependency "../../../../../interface/Port-channel" {
          tailf:xpath-root 3;
        }
      }
    }
  }

  grouping ncs_rpc_notif_interface-ethernet-switch-grouping {
    uses ncs_rpc_notif_interface-ethernet-grouping {
      refine "service/instance" {
        tailf:cli-diff-dependency "../../switchport" {
          tailf:xpath-root 3;
        }
      }
      refine "channel-group/number" {
        tailf:cli-diff-dependency "../../switchport" {
          tailf:xpath-root 3;
        }
      }
    }
  }

  grouping ncs_rpc_notif_sub-interface-ethernet-switch-grouping {
    uses ncs_rpc_notif_sub-interface-ethernet-grouping {
      refine "service/instance" {
        tailf:cli-diff-dependency "../../switchport" {
          tailf:xpath-root 3;
        }
      }
      refine "channel-group/number" {
        tailf:cli-diff-dependency "../../switchport" {
          tailf:xpath-root 3;
        }
      }
    }
  }

  grouping ncs_rpc_notif_interface-ethernet-post-grouping0 {
    leaf bridge-group {
      tailf:info
        "Transparent bridging interface parameters";
      tailf:cli-remove-before-change;
      tailf:cli-full-command;
      type uint8 {
        tailf:info
          "<1-255>;;Assign an interface to a Bridge Group.";
        range "1..255";
      }
    }
    container bridge-group-conf {
      tailf:cli-drop-node-name;
      when "../bridge-group" {
        tailf:xpath-root 3;
        tailf:dependency "../bridge-group";
      }
      list bridge-group {
        tailf:info
          "Transparent bridging interface parameters";
        tailf:cli-suppress-mode;
        tailf:cli-delete-when-empty;
        tailf:cli-incomplete-command;
        tailf:cli-incomplete-no;
        max-elements 1;
        key "id";
        leaf id {
          type uint8 {
            tailf:info
              "<1-255>;;Assign an interface to a Bridge Group.";
            range "1..255";
          }
        }
        leaf subscriber-loop-control {
          tailf:info
            "Configure subscriber loop control";
          tailf:cli-full-command;
          type empty;
        }
        leaf block-unknown-source {
          tailf:info
            "block traffic which come from unknown source MAC address";
          tailf:cli-full-command;
          type empty;
        }
        leaf source-learning {
          tailf:info
            "learn source MAC address";
          tailf:cli-boolean-no;
          tailf:cli-full-command;
          type boolean;
          default "true";
        }
        leaf unicast-flooding {
          tailf:info
            "flood packets with unknown unicast destination MAC addresses";
          tailf:cli-boolean-no;
          tailf:cli-full-command;
          type boolean;
          default "true";
        }
        leaf spanning-disabled {
          tailf:info
            "Disable spanning tree on a bridge group";
          tailf:cli-full-command;
          type empty;
        }
      }
    }
    list vrrp {
      tailf:info
        "VRRP Interface configuration commands";
      tailf:cli-suppress-mode;
      tailf:cli-delete-when-empty;
      key "id";
      leaf id {
        type uint8 {
          tailf:info
            "<1-255>;;Group number";
          range "1..255";
        }
      }
      container authentication {
        tailf:info
          "Authentication";
        choice auth {
          leaf word {
            tailf:cli-drop-node-name;
            tailf:cli-disallow-value "md5|text";
            type string {
              tailf:info
                "WORD;;Plain text authentication string";
            }
          }
          container md5 {
            tailf:info
              "Use MD5 authentication";
            leaf key-chain {
              tailf:info
                "Set key chain";
              type string {
                tailf:info
                  "WORD;;Name of key-chain";
              }
            }
            container key-string {
              tailf:info
                "Set key string";
              tailf:cli-flatten-container;
              tailf:cli-compact-syntax;
              tailf:cli-sequence-commands;
              uses ncs_rpc_notif_password-grouping;
              leaf timeout {
                tailf:info
                  "Set timeout";
                type uint16 {
                  tailf:info
                    "<0-32767>;;Timeout until only accepting new key (seconds)";
                  range "0..32767";
                }
              }
            }
          }
          leaf text {
            tailf:info
              "Plain text authentication";
            type string {
              tailf:info
                "WORD;;Plain text authentication string (8 chars max)";
            }
          }
        }
      }
      uses ncs_rpc_notif_interface-vrrp-grouping;
      container ip {
        tailf:info
          "Enable Virtual Router Redundancy Protocol (VRRP) for IP";
        tailf:cli-compact-syntax;
        tailf:cli-sequence-commands {
          tailf:cli-reset-siblings;
        }
        leaf address {
          tailf:cli-drop-node-name;
          type inet:ipv4-address {
            tailf:info
              "A.B.C.D;;VRRP group IP address";
          }
        }
        leaf secondary {
          tailf:info
            "Specify an additional VRRP address for this group";
          type empty;
        }
      }
    }
    container vrrv3p-v3 {
      when "/ios:fhrp/version/vrrp = 'v3'" {
        tailf:xpath-root 3;
        // NCS drop tailf-common:dependency statement
      }
      tailf:cli-drop-node-name;
      list vrrp {
        tailf:cli-mode-name "config-if-vrrp";
        tailf:cli-full-command;
        tailf:cli-exit-command "exit-vrrp" {
          tailf:info
            "Exit from VRRP group configuration mode";
        }
        key "id address-family";
        leaf id {
          type uint8 {
            tailf:info
              "<1-255>;;Group number";
            range "1..255";
          }
        }
        leaf address-family {
          tailf:cli-expose-key-name;
          tailf:info
            "Address family of the group";
          type enumeration {
            enum "ipv4" {
              tailf:info
                "ipv4 Address family";
            }
            enum "ipv6" {
              tailf:info
                "ipv6 Address family";
            }
          }
        }
        uses ncs_rpc_notif_interface-vrrp-grouping;
        container address {
          tailf:info
            "IPv4 address config";
          list primary-list {
            tailf:cli-drop-node-name;
            tailf:cli-suppress-mode;
            tailf:cli-delete-when-empty;
            max-elements 1;
            key "address";
            leaf address {
              type union {
                type inet:ipv4-address {
                  tailf:info
                    "A.B.C.D;;IP address";
                }
                type inet:ipv6-address {
                  tailf:info
                    "X:X:X:X::X;;IPv6 address";
                }
              }
            }
            leaf primary {
              tailf:info
                "Primary Address";
              type empty;
            }
          }
          list secondary-list {
            tailf:cli-drop-node-name;
            tailf:cli-suppress-mode;
            tailf:cli-delete-when-empty;
            key "address";
            leaf address {
              type union {
                type inet:ipv4-address {
                  tailf:info
                    "A.B.C.D;;IP address";
                }
                type ios:ipv6-prefix {
                  tailf:info
                    "X:X:X:X::X/<0-128>;;IPv6 address and prefix";
                }
              }
            }
            leaf secondary {
              tailf:info
                "Secondary Address";
              type empty;
            }
          }
        }
      }
    }
    container vrrs {
      tailf:info
        "VRRS Interface configuration commands";
      list pathway {
        tailf:info
          "Configure a VRRS pathway";
        tailf:cli-mode-name "config-if-vrrs-pw";
        tailf:cli-exit-command "exit-vrrs-pw";
        key "name";
        leaf name {
          type string {
            tailf:info
              "WORD;;Name of the VRRS tag to associate with pathway";
          }
        }
        uses ncs_rpc_notif_description-grouping;
        list address {
          tailf:info
            "IPv4/IPv6 Address configuration";
          tailf:cli-suppress-mode;
          tailf:cli-delete-when-empty;
          key "address";
          leaf address {
            type union {
              type inet:ipv4-address {
                tailf:info
                  "A.B.C.D;;IP address";
              }
              type inet:ipv6-address {
                tailf:info
                  "X:X:X:X::X;;IPv6 link-local address";
              }
              type ios:ipv6-prefix {
                tailf:info
                  "X:X:X:X::X/<0-128>;;IPv6 address and prefix";
              }
            }
          }
        }
      }
    }
  }

  grouping ncs_rpc_notif_interface-ethernet-post-grouping {
    uses ncs_rpc_notif_interface-ethernet-post-grouping0 {
      refine "vrrv3p-v3" {
        tailf:cli-diff-dependency "../../../fhrp/version/vrrp" {
          tailf:xpath-root 3;
        }
      }
    }
  }

  grouping ncs_rpc_notif_sub-interface-ethernet-post-grouping {
    uses ncs_rpc_notif_interface-ethernet-post-grouping0 {
      refine "vrrv3p-v3" {
        tailf:cli-diff-dependency "../../../../fhrp/version/vrrp" {
          tailf:xpath-root 3;
        }
      }
    }
  }

  grouping ncs_rpc_notif_interface-pointtopoint-grouping {
    container encapsulation-pointtopoint {
      tailf:cli-drop-node-name;
      container encapsulation {
        tailf:info
          "Set encapsulation type for an interface";
        container isl {
          tailf:info
            "Inter Switch Link - Virtual LAN encapsulation";
          tailf:cli-compact-syntax;
          tailf:cli-sequence-commands;
          leaf vlan-id {
            tailf:cli-drop-node-name;
            type uint16 {
              tailf:info
                "<1-4095>;;Virtual LAN Identifier.";
              range "1..4095";
            }
          }
        }
        container ppp {
          tailf:info
            "Point-to-Point protocol";
          presence "true";
        }
        container slip {
          tailf:info
            "Serial Line IP";
          presence "true";
        }
        container frame-relay {
          tailf:info
            "Frame Relay networks";
          tailf:cli-delete-when-empty;
          presence "true";
          leaf IETF {
            tailf:info
              "Use RFC1490/RFC2427 encapsulation";
            tailf:cli-full-command;
            type empty;
          }
          leaf MFR {
            tailf:info
              "Multilink Frame Relay bundle interface";
            tailf:cli-allow-join-with-value {
              tailf:cli-display-joined;
            }
            tailf:cli-full-command;
            // NCS drop tailf-common:non-strict-leafref statement
            type uint32 {
              tailf:info
                "<0-2147483647>;;MFR interface number";
            }
          }
        }
        container hdlc {
          tailf:cli-delete-when-empty;
          presence "true";
        }
      }
    }
    container dialer {
      tailf:info
        "Dial-on-demand routing (DDR) commands";
      container in-band {
        tailf:info
          "Set v.25bis dialing for interface";
        tailf:cli-delete-when-empty;
        presence "true";
        leaf parity {
          tailf:cli-drop-node-name;
          type enumeration {
            enum "no-parity" {
              tailf:info
                "No parity";
            }
            enum "odd-parity" {
              tailf:info
                "Odd parity";
            }
          }
        }
      }
      container idle-timeout {
        tailf:info
          "Specify idle timeout before disconnecting line";
        tailf:cli-compact-syntax;
        tailf:cli-sequence-commands {
          tailf:cli-reset-siblings;
        }
        leaf seconds {
          tailf:cli-drop-node-name;
          type uint32 {
            tailf:info
              "<0-2147483>;;Idle timeout before disconnecting a call";
          }
        }
        leaf direction {
          tailf:cli-drop-node-name;
          type enumeration {
            enum "either" {
              tailf:info
                "Reset idle timer based on both inbound and outbound traffic";
            }
            enum "inbound" {
              tailf:info
                "Reset idle timer based on inbound traffic only";
            }
          }
        }
      }
      leaf enable-timeout {
        tailf:info
          "Set length of time an interface stays down before it is available for dialing";
        type uint32 {
          tailf:info
            "<1-2147483>;;Enable timeout in seconds";
          range "1..2147483";
        }
      }
      leaf string {
        tailf:info
          "Specify telephone number to be passed to DCE device";
        type string {
          tailf:info
            "WORD;;Dialer string (quote strings containing #)";
        }
      }
      leaf pool {
        tailf:info
          "Specify dialer pool to be used";
        type uint8 {
          tailf:info
            "<1-255>;;Dialer pool number";
          range "1..8";
        }
      }
      container map {
        tailf:info
          "Define multiple dial-on-demand numbers";
        list ip {
          tailf:info
            "IP";
          tailf:cli-suppress-mode;
          tailf:cli-delete-when-empty;
          tailf:cli-compact-syntax;
          key "address";
          leaf address {
            type inet:ipv4-address {
              tailf:info
                "A.B.C.D;;Protocol specific address";
            }
          }
          leaf name {
            tailf:info
              "Map to a host";
            type string {
              tailf:info
                "WORD;;Hostname to map";
            }
          }
          leaf class {
            tailf:info
              "dialer map class";
            type string {
              tailf:info
                "WORD;;name of dialer map class";
            }
          }
        }
      }
      leaf watch-group {
        tailf:info
          "Assign interface to dialer-watch-list";
        type uint16 {
          tailf:info
            "<1-255>;;Dialer watch group number";
          range "1..255";
        }
        // NCS drop tailf-common:non-strict-leafref statement
      }
    }
    leaf dialer-group {
      tailf:info
        "Assign interface to dialer-list";
      type uint8 {
        tailf:info
          "<1-128>;;Dialer list number";
        range "1..128";
      }
    }
    container ppp {
      tailf:info
        "Point-to-Point Protocol";
      container mtu {
        tailf:info
          "PPP MTU configuration";
        leaf adaptive {
          tailf:info
            "Adapt MTU to peer's MRU";
          tailf:cli-diff-dependency "../../../dialer" {
            tailf:xpath-root 3;
          }
          type empty;
        }
      }
      container pfc {
        tailf:info
          "Options for Protocol Field Compression";
        leaf local {
          tailf:info
            "Specify use of PFC option in outbound Config-Requests";
          type enumeration {
            enum "forbid" {
              tailf:info
                "Do not include PFC option in our Config-Requests, ever";
            }
            enum "request" {
              tailf:info
                "Include PFC option in our Config-Requests";
            }
          }
        }
      }
      container acfc {
        tailf:info
          "Options for HDLC Address & Control Field Compression";
        leaf local {
          tailf:info
            "Specify use of ACFC option in outbound Config-Requests";
          type enumeration {
            enum "forbid" {
              tailf:info
                "Do not include ACFC option in our Config-Requests, ever";
            }
            enum "request" {
              tailf:info
                "Include ACFC option in our Config-Requests";
            }
          }
        }
        leaf remote {
          tailf:info
            "Specify handling of ACFC option in inbound Config-Requests";
          type enumeration {
            enum "apply" {
              tailf:info
                "Do ACFC if peer indicates it can receive such frames";
            }
            enum "ignore" {
              tailf:info
                "Accept ACFC option, but do not apply ACFC on outbound frames";
            }
            enum "reject" {
              tailf:info
                "Explicitly reject the ACFC option and disallow ACFC";
            }
          }
        }
      }
      leaf accounting {
        tailf:info
          "Set PPP network accounting method";
        type union {
          type string {
            tailf:info
              "WORD;;Named accounting list.";
          }
          type enumeration {
            enum "default" {
              tailf:info
                "The default accounting list.";
            }
          }
        }
      }
      container authentication {
        tailf:info
          "Set PPP link authentication method";
        tailf:cli-compact-syntax;
        tailf:cli-sequence-commands;
        leaf method {
          tailf:cli-drop-node-name;
          type enumeration {
            enum "chap" {
              tailf:info
                "Challenge Handshake Authentication Protocol (CHAP)";
            }
            enum "eap" {
              tailf:info
                "Extensible Authentication Protocol (EAP)";
            }
            enum "ms-chap" {
              tailf:info
                "Microsoft Challenge Handshake Authentication Protocol (MS-CHAP)";
            }
            enum "ms-chap-v2" {
              tailf:info
                "Microsoft CHAP Version 2 (MS-CHAP-V2)";
            }
            enum "pap" {
              tailf:info
                "Password Authentication Protocol (PAP)";
            }
          }
        }
        leaf list-name {
          tailf:cli-break-sequence-commands;
          tailf:cli-drop-node-name;
          type string {
            tailf:info
              "WORD;;Use an authentication list with this name";
          }
          tailf:cli-disallow-value "(callback)|(callin)|(callout)|(default)|(eap)|(ms-chap)|(ms-chap-v2)|(one-time)|(optional)|(pap)";
        }
        leaf chap {
          when "not(../method = 'chap')" {
            tailf:xpath-root 3;
            tailf:dependency "../method";
          }
          tailf:info
            "Challenge Handshake Authentication Protocol (CHAP)";
          type empty;
        }
        leaf callback {
          tailf:info
            "Authenticate remote on callback only";
          type empty;
        }
        leaf callin {
          tailf:info
            "Authenticate remote on incoming call only";
          type empty;
        }
        leaf callout {
          tailf:info
            "Authenticate remote on outgoing call only";
          type empty;
        }
        leaf default {
          tailf:info
            "Use the default authentication list";
          type empty;
        }
        leaf eap {
          when "not(../method = 'eap')" {
            tailf:xpath-root 3;
            tailf:dependency "../method";
          }
          tailf:info
            "Extensible Authentication Protocol (EAP)";
          type empty;
        }
        leaf ms-chap {
          when "not(../method = 'ms-chap')" {
            tailf:xpath-root 3;
            tailf:dependency "../method";
          }
          tailf:info
            "Microsoft Challenge Handshake Authentication Protocol (MS-CHAP)";
          type empty;
        }
        leaf ms-chap-v2 {
          when "not(../method = 'ms-chap-v2')" {
            tailf:xpath-root 3;
            tailf:dependency "../method";
          }
          tailf:info
            "Microsoft CHAP Version 2 (MS-CHAP-V2)";
          type empty;
        }
        leaf one-time {
          tailf:info
            "Allow use of username*OTP for one-time passwords";
          type empty;
        }
        leaf optional {
          tailf:info
            "Allow peer to refuse to authenticate";
          type empty;
        }
        leaf pap {
          when "not(../method = 'pap')" {
            tailf:xpath-root 3;
            tailf:dependency "../method";
          }
          tailf:info
            "Password Authentication Protocol (PAP)";
          type empty;
        }
      }
      leaf authorization {
        tailf:info
          "Set PPP network authorization method";
        type union {
          type string {
            tailf:info
              "WORD;;Named authorization list.";
          }
          type enumeration {
            enum "default" {
              tailf:info
                "The default authorization list.";
            }
          }
        }
      }
      container chap {
        tailf:info
          "Set CHAP authentication parameters";
        leaf hostname {
          tailf:info
            "Set alternate CHAP hostname";
          type string {
            tailf:info
              "WORD;;Alternate CHAP hostname";
          }
        }
        container password {
          tailf:info
            "Set default CHAP password";
          tailf:cli-compact-syntax;
          tailf:cli-sequence-commands;
          uses ncs_rpc_notif_password-grouping;
        }
      }
      container ipcp {
        tailf:info
          "Set IPCP negotiation options";
        container address {
          tailf:info
            "Additional ipcp address options";
          tailf:cli-compact-syntax;
          leaf accept {
            tailf:info
              "Accept any non zero IP address from our peer";
            tailf:cli-full-command;
            type empty;
          }
          leaf proxy {
            tailf:info
              "Peer proxy IP address (XCONNECT)";
            tailf:cli-full-command;
            type inet:ipv4-address;
          }
          leaf request {
            tailf:info
              "Request any address from our peer";
            tailf:cli-full-command;
            type enumeration {
              enum "ignore" {
                tailf:info
                  "Ignore negotiated address";
              }
            }
          }
          leaf required {
            tailf:info
              "Disconnect peers with no IP address negotiated";
            tailf:cli-full-command;
            type empty;
          }
          leaf unique {
            tailf:info
              "Disconnect if peer IP address already in use";
            tailf:cli-full-command;
            type empty;
          }
        }
        container dns {
          tailf:info
            "Specify DNS negotiation options";
          tailf:cli-compact-syntax;
          tailf:cli-sequence-commands;
          choice dns-choice {
            case dns-address {
              leaf primary {
                tailf:cli-drop-node-name;
                type inet:ipv4-address {
                  tailf:info
                    "A.B.C.D;;Primary DNS IP address";
                }
              }
              leaf secondary {
                tailf:cli-drop-node-name;
                type inet:ipv4-address {
                  tailf:info
                    "A.B.C.D;;Secondary DNS IP address";
                }
              }
            }
            container request {
              tailf:info
                "Request server addresses from peer";
              tailf:cli-delete-when-empty;
              presence "true";
              leaf accept {
                tailf:info
                  "Accept any non zero DNS address";
                type empty;
              }
            }
          }
        }
      }
      container multilink {
        tailf:info
          "Make interface multilink capable";
        tailf:cli-display-separated;
        presence "true";
        leaf interleave {
          tailf:info
            "Allow interleaving of small packets with fragments";
          type empty;
        }
        container links {
          tailf:info
            "Specify the limits on the number of links in a bundle";
          container minimum {
            tailf:info
              "Minimum number of links desired in the bundle";
            tailf:cli-compact-syntax;
            tailf:cli-sequence-commands {
              tailf:cli-reset-all-siblings;
            }
            leaf minimum-value {
              tailf:cli-drop-node-name;
              type uint8 {
                tailf:info
                  "<1-255>;;Specify minimum desired number of links in a bundle";
              }
            }
            leaf mandatory {
              tailf:info
                "Disable network layer until minimum number of links is reach";
              type empty;
            }
          }
        }
        leaf group {
          tailf:info
            "Put interface in a multilink bundle";
          type uint32 {
            tailf:info
              "<1-2147483647>;;Multilink group number";
            range "1..2147483647";
          }
        }
        container fragment {
          tailf:info
            "Specify fragmentation parameters";
          leaf disable {
            tailf:info
              "Suppress multilink fragmentation when possible";
            tailf:cli-full-command;
            type empty;
          }
          leaf size {
            tailf:info
              "Specify the maximum size of a multilink fragment";
            type uint16 {
              tailf:info
                "<42-65535>;;Maximum fragment size in bytes";
              range "42..65535";
            }
          }
          container delay {
            tailf:info
              "Specify the maximum delay for each fragment";
            tailf:cli-compact-syntax;
            tailf:cli-sequence-commands {
              tailf:cli-reset-siblings;
            }
            leaf delay-value {
              tailf:cli-drop-node-name;
              type uint16 {
                tailf:info
                  "<0-1000>;;Delay in milliseconds";
                range "0..1000";
              }
            }
            leaf additional-delay-value {
              tailf:cli-drop-node-name;
              type uint16 {
                tailf:info
                  "<1-999>;;Additional delay in microseconds";
                range "1..999";
              }
            }
          }
        }
        leaf fragmentation {
          tailf:info
            "Enable/Disable multilink fragmentation";
          tailf:cli-full-command;
          tailf:cli-boolean-no;
          type boolean;
          default "true";
        }
        container queue {
          tailf:info
            "Specify link queuing parameters";
          container depth {
            tailf:info
              "Specify maximum depth for link transmit queues";
            leaf fifo {
              tailf:info
                "Set max depth for link queues when bundle has FIFO queuing";
              type uint8 {
                tailf:info
                  "<2-255>;;Max queue depth for link";
                range "2..255";
              }
            }
            leaf qos {
              tailf:info
                "Set max depth for link queues when bundle has non-FIFO queuing";
              type uint8 {
                tailf:info
                  "<2-255>;;Max queue depth for link";
                range "2..255";
              }
            }
          }
        }
        container min-links {
          tailf:cli-compact-syntax;
          tailf:cli-sequence-commands {
            tailf:cli-reset-siblings;
          }
          leaf links {
            tailf:cli-drop-node-name;
            type uint8;
          }
          leaf mandatory {
            type empty;
          }
        }
      }
    }
    leaf multilink-group {
      tailf:info
        "Put interface in a multilink bundle";
      type uint32 {
        tailf:info
          "<1-2147483647>;;Multilink group number";
        range "1..2147483647";
      }
    }
    leaf physical-layer {
      tailf:info
        "Configure sync or async physical layer on serial interface";
      type enumeration {
        enum "async" {
          tailf:info
            "Configure asynchronous physical layer on serial interface";
        }
        enum "sync" {
          tailf:info
            "Configure synchronous physical layer on serial interface";
        }
      }
    }
    container async {
      tailf:info
        "Async interface parameters";
      container mode {
        tailf:info
          "Specify line mode (interactive or dedicated interface use)";
        leaf dedicated {
          tailf:info
            "Line is dedicated as an async interface";
          type empty;
        }
        leaf interactive {
          tailf:info
            "Line may be switched between interactive use and async interface";
          type empty;
        }
      }
    }
    container pulse-time {
      tailf:info
        "Force DTR low during resets";
      choice pulse-time-choice {
        leaf seconds {
          tailf:cli-drop-node-name;
          type uint8 {
            tailf:info
              "<0-60>;;DTR low time in seconds";
            range "0..60";
          }
        }
        leaf msec {
          tailf:info
            "millisecond (resolution)";
          type uint16 {
            tailf:info
              "<1-59999>;;DTR low time in milliseconds";
            range "1..59999";
          }
        }
      }
    }
    container serial {
      tailf:info
        "serial interface commands";
      container restart-delay {
        tailf:info
          "Configure serial interface restart-delay";
        tailf:cli-compact-syntax;
        tailf:cli-sequence-commands {
          tailf:cli-reset-siblings;
        }
        leaf seconds {
          tailf:cli-drop-node-name;
          type uint16 {
            tailf:info
              "<0-900>;;Restart delay (seconds)";
            range "0..900";
          }
        }
        leaf milliseconds {
          tailf:cli-drop-node-name;
          type uint16 {
            tailf:info
              "<0-999>;;Restart delay (milliseconds)";
            range "0..999";
          }
        }
      }
    }
  }

  grouping ncs_rpc_notif_interface-switch-grouping0 {
    container switchport {
      tailf:info
        "Set switching mode characteristics";
      tailf:cli-display-separated;
      tailf:cli-recursive-delete;
      tailf:cli-show-no;
      presence "true";
      tailf:callpoint interface-switchport-hook {
        tailf:set-hook node;
      }
      tailf:cli-diff-dependency "../ip/address" {
        tailf:xpath-root 3;
        tailf:cli-trigger-on-set;
      }
      tailf:cli-diff-dependency "../ip/no-address/address" {
        tailf:xpath-root 3;
        tailf:cli-trigger-on-set;
      }
      tailf:cli-diff-dependency "../ip/redirects" {
        tailf:xpath-root 3;
        tailf:cli-trigger-on-set;
      }
      tailf:cli-diff-dependency "../ip/ospf" {
        tailf:xpath-root 3;
        tailf:cli-trigger-on-set;
      }
      tailf:cli-diff-dependency "../standby" {
        tailf:xpath-root 3;
        tailf:cli-trigger-on-set;
      }
      tailf:cli-diff-dependency "../service-policy/output" {
        tailf:xpath-root 3;
        tailf:cli-trigger-on-set;
      }
      tailf:cli-diff-dependency "../service-policy/input" {
        tailf:xpath-root 3;
        tailf:cli-trigger-on-set;
      }
      tailf:cli-diff-dependency "../udld" {
        tailf:xpath-root 3;
        tailf:cli-trigger-on-set;
      }
      tailf:meta-data "inject-interface-config-sp-input" {
        tailf:meta-value "service-policy/input :: service-policy input :: after :: any";
      }
      tailf:meta-data "inject-interface-config-sp-output" {
        tailf:meta-value "service-policy/output :: service-policy output :: after :: any";
      }
      tailf:meta-data "inject-interface-config-lacp-rate" {
        tailf:meta-value "lacp/rate :: lacp rate :: after :: any";
      }
      tailf:ned-data "../service-policy" {
        tailf:xpath-root 3;
        tailf:transaction to;
      }
      tailf:ned-data "../lacp/rate" {
        tailf:xpath-root 3;
        tailf:transaction to;
      }
      container mode {
        tailf:info
          "Set trunking mode of the interface";
        choice mode-choice {
          container access {
            tailf:info
              "Set trunking mode to ACCESS unconditionally";
            presence "true";
          }
          container dot1q-tunnel {
            tailf:info
              "set trunking mode to TUNNEL unconditionally";
            presence "true";
          }
          leaf dynamic {
            tailf:info
              "Set trunking mode to dynamically negotiate access or trunk mode";
            tailf:cli-diff-dependency "../../nonegotiate" {
              tailf:xpath-root 3;
              tailf:cli-trigger-on-set;
            }
            tailf:cli-diff-dependency "../../port-security" {
              tailf:xpath-root 3;
              tailf:cli-trigger-on-set;
            }
            type enumeration {
              enum "auto" {
                tailf:info
                  "Set trunking mode dynamic negotiation parameter to AUTO";
              }
              enum "desirable" {
                tailf:info
                  "Set trunking mode dynamic negotiation parameter to DESIRABLE";
              }
            }
          }
          container trunk {
            tailf:info
              "Set trunking mode to TRUNK unconditionally";
            tailf:cli-diff-dependency "../../trunk/encapsulation" {
              tailf:xpath-root 3;
              tailf:cli-trigger-on-set;
            }
            presence "true";
          }
          container private-vlan {
            tailf:info
              "Set private-vlan mode";
            choice private-vlan-choice {
              leaf host {
                tailf:info
                  "Set the mode to private-vlan host";
                type empty;
              }
              leaf promiscuous {
                tailf:info
                  "Set the mode to private-vlan promiscuous";
                type empty;
              }
              container trunk {
                tailf:info
                  "Set the mode to private-vlan trunk";
                presence "true";
              }
            }
          }
        }
      }
      container trunk {
        tailf:info
          "Set trunking characteristics of the interface";
        leaf encapsulation {
          tailf:info
            "Set encapsulation format on trunk port";
          tailf:cli-diff-dependency "../../mode/dynamic" {
            tailf:xpath-root 3;
            tailf:cli-trigger-on-set;
          }
          type enumeration {
            enum "dot1q" {
              tailf:info
                "Interface uses only 802.1q trunking encapsulation when trunking";
            }
            enum "isl" {
              tailf:info
                "Interface uses only ISL trunking encapsulation when trunking";
            }
            enum "negotiate" {
              tailf:info
                "Device will negotiate trunking encapsulation with peer on interface";
            }
          }
          default "negotiate";
        }
        container native {
          tailf:info
            "Set trunking native characteristics when interface is in trunking mode";
          leaf vlan {
            tailf:info
              "Set native VLAN when interface is in trunking mode";
            type union {
              type enumeration {
                enum "tag" {
                  tailf:info
                    "Set native VLAN tagging state";
                }
              }
              type uint16 {
                tailf:info
                  "<1-4094>;;VLAN ID of the native VLAN when this port is in trunking mode";
                range "1..4094";
              }
            }
          }
        }
        container allowed {
          tailf:info
            "Set allowed VLAN characteristics when interface is in trunking mode";
          container vlan {
            tailf:info
              "Set allowed VLANs when interface is in trunking mode";
            tailf:cli-delete-when-empty;
            tailf:cli-display-separated;
            tailf:cli-incomplete-command;
            presence "true";
            choice vlan-choice {
              leaf-list vlans {
                tailf:cli-drop-node-name;
                tailf:cli-range-list-syntax;
                tailf:cli-diff-dependency "../../../../mode" {
                  tailf:xpath-root 3;
                }
                tailf:cli-diff-dependency "../../vlan" {
                  tailf:xpath-root 3;
                }
                type uint16 {
                  tailf:info
                    "WORD;;VLAN IDs of the allowed VLANs when this port is in trunking mode";
                  range "1..4094";
                }
              }
              leaf none {
                tailf:info
                  "no VLANs";
                type empty;
              }
            }
          }
        }
        container pruning {
          tailf:info
            "Set pruning VLAN characteristics when interface is in trunking mode";
          container vlan {
            tailf:info
              "Set VLANs enabled for pruning when interface is in trunking mode";
            choice vlan-choice {
              leaf-list vlans {
                tailf:cli-drop-node-name;
                tailf:cli-range-list-syntax;
                tailf:cli-replace-all;
                type uint16 {
                  tailf:info
                    "WORD;;VLAN IDs of the allowed VLANs when this port is in trunking mode";
                  range "1..4094";
                }
              }
              leaf none {
                tailf:info
                  "no VLANs";
                type empty;
              }
            }
          }
        }
      }
      container autostate {
        tailf:info
          "Include or exclude this port from vlan link up calculation";
        leaf exclude {
          tailf:info
            "Exclude this port from vlan link up calculation";
          type empty;
        }
      }
      container private-vlan {
        tailf:info
          "Set the private VLAN configuration";
        container trunk {
          tailf:info
            "Set the private vlan trunking configuration";
          container native {
            tailf:info
              "Set the private vlan trunking native configuration";
            leaf vlan {
              tailf:info
                "Set native VLAN configuration";
              type union {
                type enumeration {
                  enum "tag" {
                    tailf:info
                      "Set native VLAN tagging state";
                  }
                }
                type uint16 {
                  tailf:info
                    "<1-4094>;;VLAN ID of the native VLAN when this port is in trunking mode";
                  range "1..4094";
                }
              }
            }
          }
          container allowed {
            tailf:info
              "Set allowed VLAN characteristics when interface is in private-vlan trunking mode";
            container vlan {
              tailf:info
                "Set allowed VLANs when interface is in private-vlan trunking mode";
              choice vlan-choice {
                leaf-list vlans {
                  tailf:cli-replace-all;
                  tailf:cli-range-list-syntax;
                  tailf:cli-drop-node-name;
                  type uint16 {
                    tailf:info
                      "WORD;;VLAN IDs of the allowed VLANs when interface is in private-vlan trunking mode";
                    range "1..4094";
                  }
                }
                leaf none {
                  tailf:info
                    "no VLANs";
                  type empty;
                }
              }
            }
          }
        }
        container association {
          tailf:info
            "Set the private VLAN association";
          list trunk {
            tailf:cli-suppress-mode;
            tailf:cli-delete-when-empty;
            tailf:cli-incomplete-command;
            key "primary-vlan-id";
            leaf primary-vlan-id {
              type uint16 {
                tailf:info
                  "<2-4094>;;Primary VLAN ID of the private VLAN trunk association";
                range "2..4094";
              }
            }
            leaf secondary-vlan-id {
              tailf:cli-drop-node-name;
              type uint16 {
                tailf:info
                  "<2-4094>;;Secondary VLAN ID of the private VLAN port/trunk association";
                range "2..4094";
              }
            }
          }
        }
      }
      container access {
        tailf:info
          "Set access mode characteristics of the interface";
        leaf vlan {
          tailf:info
            "Set VLAN when interface is in access mode";
          tailf:cli-diff-dependency "../../../service/instance" {
            tailf:xpath-root 3;
            tailf:cli-trigger-on-set;
          }
          type union {
            type uint16 {
              tailf:info
                "<1-4094>;;VLAN ID of the VLAN when this port is in access mode";
              range "1..4094";
            }
            type enumeration {
              enum "dynamic" {
                tailf:info
                  "When in access mode, this interfaces VLAN is controlled by VMPS";
              }
            }
          }
          default "1";
        }
      }
      container backup {
        tailf:info
          "Set backup for the interface";
        list interface {
          tailf:info
            "Specify an interface as backup";
          tailf:cli-suppress-mode;
          tailf:cli-delete-when-empty;
          key "name";
          leaf name {
            type string {
              tailf:info
                "WORD;;Interface Name";
            }
          }
          container preemption {
            tailf:info
              "preemption parameters";
            leaf mode {
              tailf:info
                "set the preemption mode";
              type enumeration {
                enum "bandwidth" {
                  tailf:info
                    "higher bandwidth interface preferred";
                }
                enum "forced" {
                  tailf:info
                    "active interface preferred";
                }
                enum "off" {
                  tailf:info
                    "turn off preemption";
                }
              }
            }
            leaf delay {
              tailf:info
                "preemption parameters";
              type uint16 {
                tailf:info
                  "<1-300>;;preemption delay in seconds";
                range "1..300";
              }
            }
          }
        }
      }
      leaf nonegotiate {
        tailf:info
          "Device will not engage in negotiation protocol on this interface";
        tailf:cli-diff-dependency "../trunk" {
          tailf:xpath-root 3;
        }
        tailf:cli-diff-dependency "../mode/trunk" {
          tailf:xpath-root 3;
        }
        tailf:cli-diff-dependency "../mode/access" {
          tailf:xpath-root 3;
        }
        type empty;
      }
      container block {
        tailf:info
          "Disable forwarding of unknown uni/multi cast addresses";
        leaf multicast {
          tailf:info
            "Block unknown multicast addresses";
          tailf:cli-full-command;
          type empty;
        }
        leaf unicast {
          tailf:cli-full-command;
          tailf:info
            "Block unknown unicast addresses";
          type empty;
        }
      }
      container port-security {
        tailf:info
          "Security related command";
        tailf:cli-display-separated;
        tailf:cli-diff-dependency "../mode/access" {
          tailf:xpath-root 3;
        }
        tailf:cli-diff-dependency "../mode/trunk" {
          tailf:xpath-root 3;
        }
        presence "true";
        container aging {
          tailf:info
            "Port-security aging commands";
          leaf time {
            tailf:info
              "Port-security aging time";
            type uint16 {
              tailf:info
                "<1-1440>;;Aging time in minutes. Enter a value between 1 and 1440";
              range "1..1440";
            }
          }
          leaf type {
            tailf:info
              "Port-security aging type";
            type enumeration {
              enum "absolute" {
                tailf:info
                  "Absolute aging (default)";
              }
              enum "inactivity" {
                tailf:info
                  "Aging based on inactivity time period";
              }
            }
          }
        }
        container mac-address {
          tailf:info
            "Secure mac address";
          tailf:cli-compact-syntax;
          tailf:cli-sequence-commands {
            tailf:cli-reset-siblings;
          }
          leaf sticky {
            tailf:info
              "Configure dynamic secure addresses as sticky";
            tailf:cli-optional-in-sequence;
            type empty;
          }
          leaf hw-address {
            tailf:cli-drop-node-name;
            type yang:mac-address {
              tailf:info
                "H.H.H;;48 bit mac address";
            }
          }
          leaf vlan {
            tailf:info
              "set VLAN ID of the VLAN on which this address can be learned";
            type uint16 {
              tailf:info
                "<1-4094>;;VLAN ID on which this address can be learned";
              range "1..4094";
            }
          }
        }
        leaf maximum {
          tailf:info
            "Max secure addresses";
          tailf:cli-no-value-on-delete;
          tailf:cli-full-command;
          type uint16 {
            tailf:info
              "<1-8192>;;Maximum addresses";
            range "1..8192";
          }
        }
        container maximum-vlan {
          tailf:cli-drop-node-name;
          tailf:cli-compact-syntax;
          tailf:cli-sequence-commands {
            tailf:cli-reset-siblings;
          }
          leaf maximum {
            tailf:cli-no-value-on-delete;
            tailf:cli-incomplete-command;
            type uint16 {
              tailf:info
                "<1-8192>;;Maximum addresses";
              range "1..8192";
            }
          }
          leaf vlan {
            tailf:info
              "Max secure addresses per vlan";
            type empty;
          }
        }
        container maximum-vlan-list {
          tailf:cli-drop-node-name;
          list maximum {
            tailf:cli-suppress-mode;
            tailf:cli-delete-when-empty;
            tailf:cli-compact-syntax;
            tailf:cli-sequence-commands {
              tailf:cli-reset-siblings;
            }
            key "max-addresses vlan";
            leaf max-addresses {
              type uint16 {
                tailf:info
                  "<1-8192>;;Maximum addresses";
                range "1..8192";
              }
            }
            leaf vlan {
              tailf:info
                "Max secure addresses per vlan";
              tailf:cli-expose-key-name;
              type string {
                tailf:info
                  "WORD;;VLAN IDs to which this maximum applies";
              }
            }
          }
        }
        leaf violation {
          tailf:info
            "Security violation mode";
          type enumeration {
            enum "protect" {
              tailf:info
                "Security violation protect mode";
            }
            enum "restrict" {
              tailf:info
                "Security violation restrict mode";
            }
            enum "shutdown" {
              tailf:info
                "Security violation shutdown mode";
            }
          }
        }
      }
      container priority {
        tailf:info
          "Set appliance 802.1p priority";
        tailf:cli-incomplete-command;
        container extend {
          tailf:info
            "Set appliance 802.1p priority";
          tailf:cli-incomplete-command;
          choice trust-choice {
            leaf trust {
              tailf:cli-full-command;
              tailf:info
                "Trust 802.1p priorities of devices on appliance";
              type empty;
            }
            leaf cos {
              tailf:info
                "Override 802.1p priority of devices on appliance";
              tailf:cli-full-command;
              type uint8 {
                tailf:info
                  "<0-7>;;Priority for devices on appliance";
                range "0..7";
              }
            }
          }
        }
      }
      leaf protected {
        tailf:info
          "Configure an interface to be a protected port";
        type empty;
      }
      container voice {
        tailf:info
          "Voice appliance attributes";
        leaf vlan {
          tailf:info
            "Vlan for voice traffic";
          type union {
            type enumeration {
              enum "dot1p" {
                tailf:info
                  "Priority tagged on PVID";
              }
              enum "none" {
                tailf:info
                  "Don't tell telephone about voice vlan";
              }
              enum "untagged" {
                tailf:info
                  "Untagged on PVID";
              }
            }
            type uint16 {
              tailf:info
                "<1-4094>;;Vlan for voice traffic";
              range "1..4094";
            }
          }
        }
        container detect {
          tailf:info
            "detection enhancement keyword";
          tailf:cli-incomplete-command;
          container cisco-phone {
            tailf:info
              "Cisco IP phone";
            presence "true";
            leaf full-duplex {
              tailf:info
                "full duplex keyword";
              type empty;
            }
          }
        }
      }
      leaf host {
        tailf:info
          "Set port host";
        type empty;
      }
    }
    container l2protocol-tunnel {
      tailf:info
        "Tunnel Layer2 protocols";
      tailf:cli-delete-when-empty;
      tailf:cli-diff-dependency "../switchport" {
        tailf:xpath-root 3;
      }
      presence "true";
      leaf cdp {
        tailf:info
          "Cisco Discovery Protocol";
        type empty;
      }
      container drop-threshold {
        tailf:info
          "Set drop threshold for protocol packets";
        leaf packet-rate {
          tailf:cli-drop-node-name;
          type uint16 {
            tailf:info
              "<1-4096>;;Packets/sec rate beyond which protocol packets will be dropped";
            range "1..4096";
          }
        }
        leaf cdp {
          tailf:info
            "Cisco Discovery Protocol";
          type uint16 {
            tailf:info
              "<1-4096>;;Packets/sec rate beyond which protocol packets will be dropped";
            range "1..4096";
          }
        }
        leaf stp {
          tailf:info
            "Spanning Tree Protocol";
          type uint16 {
            tailf:info
              "<1-4096>;;Packets/sec rate beyond which protocol packets will be dropped";
            range "1..4096";
          }
        }
        leaf vtp {
          tailf:info
            "Vlan Trunking Protocol";
          type uint16 {
            tailf:info
              "<1-4096>;;Packets/sec rate beyond which protocol packets will be dropped";
            range "1..4096";
          }
        }
      }
      container shutdown-threshold {
        tailf:info
          "Set shutdown threshold for protocol packets";
        leaf packet-rate {
          tailf:cli-drop-node-name;
          type uint16 {
            tailf:info
              "<1-4096>;;Packets/sec rate beyond which interface is put to err-disable";
            range "1..4096";
          }
        }
        leaf cdp {
          tailf:info
            "Cisco Discovery Protocol";
          type uint16 {
            tailf:info
              "<1-4096>;;Packets/sec rate beyond which interface is put to err-disable";
            range "1..4096";
          }
        }
        leaf stp {
          tailf:info
            "Spanning Tree Protocol";
          type uint16 {
            tailf:info
              "<1-4096>;;Packets/sec rate beyond which interface is put to err-disable";
            range "1..4096";
          }
        }
        leaf vtp {
          tailf:info
            "Vlan Trunking Protocol";
          type uint16 {
            tailf:info
              "<1-4096>;;Packets/sec rate beyond which interface is put to err-disable";
            range "1..4096";
          }
        }
        leaf lldp {
          tailf:info
            "Link Layer Discovery Protocol";
          type uint16 {
            tailf:info
              "<1-4096>;;Packets/sec rate beyond which interface is put to err-disable";
            range "1..4096";
          }
        }
      }
      leaf stp {
        tailf:info
          "Spanning Tree Protocol";
        type empty;
      }
      leaf vtp {
        tailf:info
          "Vlan Trunking Protocol";
        type empty;
      }
      leaf lldp {
        tailf:info
          "Link Layer Discovery Protocol";
        type empty;
      }
      container point-to-point {
        tailf:info
          "point-to-point L2 Protocol";
        leaf lacp {
          tailf:info
            "Link Aggregation Control Protocol";
          type empty;
        }
        leaf pagp {
          tailf:info
            "Port Aggregation Protocol";
          type empty;
        }
        leaf udld {
          tailf:info
            "Unidirectional Link Detection";
          type empty;
        }
      }
    }
  }

  grouping ncs_rpc_notif_interface-switch-grouping {
    uses ncs_rpc_notif_interface-switch-grouping0 {
      refine "switchport" {
        tailf:cli-diff-dependency "../../../vlan/vlan-list" {
          tailf:xpath-root 3;
        }
      }
    }
  }

  grouping ncs_rpc_notif_sub-interface-switch-grouping {
    uses ncs_rpc_notif_interface-switch-grouping0 {
      refine "switchport" {
        tailf:cli-diff-dependency "../../../../vlan/vlan-list" {
          tailf:xpath-root 3;
        }
      }
    }
  }

  grouping ncs_rpc_notif_crypto-pki-token-grouping {
    container removal {
      tailf:info
        "actions to take after token removal";
      leaf timeout {
        tailf:info
          "seconds after token removal at which keys from the token are cleared";
        type uint16 {
          tailf:info
            "<0-480>;;Token key timeout in seconds";
          range "0..480";
        }
      }
    }
  }

  grouping ncs_rpc_notif_router-bgp-max-path-grouping {
    container paths {
      tailf:cli-drop-node-name;
      tailf:cli-compact-syntax;
      tailf:cli-sequence-commands {
        tailf:cli-reset-siblings;
      }
      leaf number-of-paths {
        tailf:cli-drop-node-name;
        type uint16 {
          tailf:info
            "<1-16>;;Number of paths";
          range "1..16";
        }
        default "1";
      }
      leaf import {
        tailf:info
          "Maximum import paths";
        type uint16 {
          tailf:info
            "<1-16>;;Number of import paths";
          range "1..16";
        }
      }
    }
  }

  grouping ncs_rpc_notif_router-bgp-redistribute-isis-grouping {
    choice osi-ip-choice {
      leaf ip {
        tailf:info
          "Redistribution of IP dynamic routes";
        tailf:cli-no-name-on-delete;
        tailf:cli-no-value-on-delete;
        tailf:cli-remove-before-change;
        type empty;
      }
      leaf clns {
        tailf:info
          "Redistribution of OSI dynamic routes";
        tailf:cli-no-name-on-delete;
        tailf:cli-no-value-on-delete;
        tailf:cli-remove-before-change;
        type empty;
      }
    }
    leaf level {
      tailf:cli-drop-node-name;
      tailf:cli-no-name-on-delete;
      tailf:cli-no-value-on-delete;
      type enumeration {
        enum "level-1" {
          tailf:info
            "IS-IS level-1 routes only";
        }
        enum "level-2" {
          tailf:info
            "IS-IS level-2 routes only";
        }
        enum "level-1-2" {
          tailf:info
            "IS-IS level-1 and level-2 routes";
        }
      }
    }
  }

  grouping ncs_rpc_notif_router-bgp-redistribute-grouping {
    leaf metric {
      tailf:info
        "Metric for redistributed routes";
      tailf:cli-no-name-on-delete;
      tailf:cli-no-value-on-delete;
      tailf:cli-remove-before-change;
      type uint32 {
        tailf:info
          "<0-4294967295>;;Default metric";
        range "0..4294967295";
      }
    }
    leaf subnets {
      tailf:info
        "Consider subnets for redistribution into BGP";
      tailf:cli-no-name-on-delete;
      tailf:cli-no-value-on-delete;
      type empty;
    }
    leaf route-map {
      tailf:info
        "Route map reference";
      tailf:cli-no-name-on-delete;
      tailf:cli-no-value-on-delete;
      type string {
        tailf:info
          "WORD;;Pointer to route-map entries";
      }
    }
    leaf include-connected {
      tailf:info
        "Include connected";
      tailf:cli-no-name-on-delete;
      tailf:cli-no-value-on-delete;
      type empty;
    }
  }

  grouping ncs_rpc_notif_router-bgp-redistribute-ospf-grouping {
    leaf metric {
      tailf:info
        "Metric for redistributed routes";
      tailf:cli-no-name-on-delete;
      tailf:cli-no-value-on-delete;
      tailf:cli-remove-before-change;
      type uint32 {
        tailf:info
          "<0-4294967295>;;Default metric";
        range "0..4294967295";
      }
    }
    leaf subnets {
      tailf:info
        "Consider subnets for redistribution into BGP";
      tailf:cli-no-name-on-delete;
      tailf:cli-no-value-on-delete;
      type empty;
    }
    leaf route-map {
      tailf:info
        "Route map reference";
      tailf:cli-no-name-on-delete;
      tailf:cli-no-value-on-delete;
      type string {
        tailf:info
          "WORD;;Pointer to route-map entries";
      }
    }
    leaf include-connected {
      tailf:info
        "Include connected";
      tailf:cli-no-name-on-delete;
      tailf:cli-no-value-on-delete;
      type empty;
    }
    leaf match {
      tailf:info
        "Redistribution of OSPF routes";
      tailf:cli-no-name-on-delete;
      tailf:cli-no-value-on-delete;
      tailf:cli-incomplete-command;
      type empty;
    }
    leaf internal {
      when "../match" {
        tailf:xpath-root 3;
        tailf:dependency "../match";
      }
      tailf:info
        "Redistribute OSPF internal routes";
      tailf:cli-no-name-on-delete;
      tailf:cli-no-value-on-delete;
      type empty;
    }
    container external-1 {
      when "../match" {
        tailf:xpath-root 3;
        tailf:dependency "../match";
      }
      tailf:cli-drop-node-name;
      tailf:cli-flatten-container;
      tailf:cli-compact-syntax;
      leaf external {
        tailf:info
          "Redistribute OSPF external routes";
        tailf:cli-no-name-on-delete;
        tailf:cli-no-value-on-delete;
        type enumeration {
          enum "1" {
            tailf:info
              "Redistribute external type 1 routes";
          }
        }
      }
    }
    container external-2 {
      when "../match" {
        tailf:xpath-root 3;
        tailf:dependency "../match";
      }
      tailf:cli-drop-node-name;
      tailf:cli-flatten-container;
      tailf:cli-compact-syntax;
      leaf external {
        tailf:info
          "Redistribute OSPF external routes";
        tailf:cli-no-name-on-delete;
        tailf:cli-no-value-on-delete;
        type enumeration {
          enum "2" {
            tailf:info
              "Redistribute external type 2 routes";
          }
        }
      }
    }
    container nssa-external-1 {
      when "../match" {
        tailf:xpath-root 3;
        tailf:dependency "../match";
      }
      tailf:cli-drop-node-name;
      tailf:cli-flatten-container;
      tailf:cli-compact-syntax;
      leaf nssa-external {
        tailf:info
          "Redistribute OSPF NSSA external routes";
        tailf:cli-no-name-on-delete;
        tailf:cli-no-value-on-delete;
        type enumeration {
          enum "1" {
            tailf:info
              "Redistribute NSSA external type 1 routes";
          }
        }
      }
    }
    container nssa-external-2 {
      when "../match" {
        tailf:xpath-root 3;
        tailf:dependency "../match";
      }
      tailf:cli-drop-node-name;
      tailf:cli-flatten-container;
      tailf:cli-compact-syntax;
      leaf nssa-external {
        tailf:info
          "Redistribute OSPF NSSA external routes";
        tailf:cli-no-name-on-delete;
        tailf:cli-no-value-on-delete;
        type enumeration {
          enum "2" {
            tailf:info
              "Redistribute NSSA external type 2 routes";
          }
        }
      }
    }
  }

  grouping ncs_rpc_notif_route-map-metric-grouping {
    leaf route-map {
      tailf:info
        "Route map reference";
      type string {
        tailf:info
          "WORD;;Pointer to route-map entries";
      }
    }
    leaf metric {
      tailf:info
        "Metric for redistributed routes";
      type uint32 {
        tailf:info
          "<0-4294967295>;;Default metric";
        range "0..4294967295";
      }
    }
  }

  grouping ncs_rpc_notif_router-bgp-neighbor-distribute-list-grouping {
    list distribute-list {
      tailf:info
        "Filter networks in routing updates";
      tailf:cli-suppress-mode;
      tailf:cli-delete-when-empty;
      tailf:cli-compact-syntax;
      tailf:cli-sequence-commands;
      tailf:cli-remove-before-change;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      key "direction";
      leaf direction {
        type enumeration {
          enum "in" {
            tailf:info
              "Filter incoming routing updates";
          }
          enum "out" {
            tailf:info
              "Filter outgoing routing updates";
          }
        }
      }
      uses ncs_rpc_notif_distribute-list-content-grouping;
    }
    container distribute-list-interface {
      tailf:cli-drop-node-name;
      list distribute-list {
        tailf:info
          "Filter networks in routing updates";
        tailf:cli-suppress-mode;
        tailf:cli-delete-when-empty;
        tailf:cli-compact-syntax;
        tailf:cli-sequence-commands;
        tailf:cli-remove-before-change;
        tailf:cli-diff-dependency "../../inherit/peer-session" {
          tailf:xpath-root 3;
        }
        tailf:cli-diff-dependency "../../peer-group" {
          tailf:xpath-root 3;
        }
        tailf:cli-diff-dependency "../../remote-as" {
          tailf:xpath-root 3;
        }
        tailf:cli-diff-dependency "../../activate" {
          tailf:xpath-root 3;
        }
        key "direction interface";
        leaf direction {
          type enumeration {
            enum "in" {
              tailf:info
                "Filter incoming routing updates";
            }
            enum "out" {
              tailf:info
                "Filter outgoing routing updates";
            }
          }
        }
        leaf interface {
          tailf:cli-diff-dependency "/ios:interface" {
            tailf:xpath-root 3;
          }
          type string {
            tailf:info
              "WORD;;Interface name";
          }
        }
        uses ncs_rpc_notif_distribute-list-content-grouping;
      }
    }
  }

  grouping ncs_rpc_notif_router-bgp-peer-policy-grouping {
    leaf advertisement-interval {
      tailf:info
        "Minimum interval between sending BGP routing updates";
      tailf:cli-full-command;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      type uint16 {
        tailf:info
          "<0-600>;;time in seconds";
        range "0..600";
      }
    }
    leaf next-hop-self {
      tailf:info
        "Disable the next hop calculation for this neighbor";
      tailf:cli-full-command;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      type empty;
    }
    container aigp {
      tailf:cli-delete-when-empty;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      presence "true";
    }
    container send-community {
      tailf:info
        "Send Community attribute to this neighbor";
      tailf:cli-delete-when-empty;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      presence "true";
      leaf send-community-where {
        tailf:cli-drop-node-name;
        type enumeration {
          enum "both" {
            tailf:info
              "Send Standard and Extended Community attributes";
          }
          enum "extended" {
            tailf:info
              "Send Extended Community attribute";
          }
          enum "standard" {
            tailf:code-name "send_standard";
            tailf:info
              "Send Standard Community attribute";
          }
        }
      }
    }
    container send-label {
      tailf:info
        "Send NLRI + MPLS Label to this peer";
      tailf:cli-delete-when-empty;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      presence "true";
      leaf explicit-null {
        tailf:info
          "Advertise Explicit Null label in place of Implicit Null";
        type empty;
      }
    }
    container maximum-prefix {
      tailf:info
        "Maximum number of prefixes accepted from this peer";
      tailf:cli-compact-syntax;
      tailf:cli-sequence-commands {
        tailf:cli-reset-all-siblings;
      }
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      leaf max-prefix-no {
        tailf:cli-drop-node-name;
        type uint32 {
          tailf:info
            "<1-2147483647>;;maximum no. of prefix limit";
          range "1..2147483647";
        }
      }
      leaf threshold {
        tailf:cli-drop-node-name;
        tailf:cli-break-sequence-commands;
        type uint8 {
          tailf:info
            "<1-100>;;Threshold value (%) at which to generate a warning msg";
          range "1..100";
        }
      }
      leaf restart {
        tailf:cli-full-command;
        tailf:info
          "Restart bgp connection after limit is exceeded";
        type uint16 {
          tailf:info
            "<1-65535>;;Restart interval in minutes";
          range "1..65535";
        }
      }
      leaf warning-only {
        tailf:cli-full-command;
        tailf:info
          "Only give warning message when limit is exceeded";
        type empty;
      }
    }
    container allowas-in {
      tailf:info
        "Accept as-path with my AS present in it";
      tailf:cli-delete-when-empty;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      presence "true";
      leaf as-no {
        tailf:cli-drop-node-name;
        type uint8 {
          tailf:info
            "<1-10>;;Number of occurances of AS number";
          range "1..10";
        }
      }
    }
    container as-override {
      tailf:info
        "Override matching AS-number while sending update";
      tailf:cli-delete-when-empty;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      presence "true";
      leaf disable {
        type empty;
      }
    }
    list route-map {
      tailf:info
        "Apply route map to neighbor";
      tailf:cli-suppress-mode;
      tailf:cli-delete-when-empty;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      key "direction";
      leaf direction {
        type enumeration {
          enum "in" {
            tailf:info
              "Apply map to incoming routes";
          }
          enum "out" {
            tailf:info
              "Apply map to outbound routes";
          }
        }
      }
      leaf route-map-name {
        tailf:cli-drop-node-name;
        tailf:cli-prefix-key;
        type string {
          tailf:info
            "WORD;;Name of route map";
        }
      }
    }
    list advertise-map {
      tailf:info
        "Apply advertise map to neighbor";
      tailf:cli-suppress-mode;
      tailf:cli-delete-when-empty;
      tailf:cli-incomplete-command;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      key "name";
      leaf name {
        type string {
          tailf:info
            "WORD;;Name of route map";
        }
      }
      list exist-map {
        tailf:info
          "advertise prefix only if prefix is in the condition exists";
        tailf:cli-suppress-mode;
        tailf:cli-delete-when-empty;
        key "name";
        leaf name {
          type string {
            tailf:info
              "WORD;;condition route-map name";
          }
        }
      }
    }
    container default-originate {
      tailf:info
        "Originate default route to this neighbour";
      tailf:cli-delete-when-empty;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      presence "true";
      leaf route-map {
        tailf:info
          "Route-map to specify criteria to originate default";
        type string {
          tailf:info
            "WORD;;route-map name";
        }
      }
    }
    list prefix-list {
      tailf:info
        "Filter updates to/from this neighbor";
      tailf:cli-suppress-mode;
      tailf:cli-delete-when-empty;
      tailf:cli-compact-syntax;
      tailf:cli-sequence-commands;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      key "direction";
      leaf direction {
        type enumeration {
          enum "in" {
            tailf:info
              "Filter incoming updates";
          }
          enum "out" {
            tailf:info
              "Filter outgoing updates";
          }
        }
      }
      leaf prefix-list-name {
        tailf:cli-drop-node-name;
        tailf:cli-prefix-key;
        // NCS drop tailf-common:non-strict-leafref statement
        type string {
          tailf:info
            "WORD;;Name of a prefix list";
        }
      }
    }
    leaf route-reflector-client {
      tailf:info
        "Configure a neighbor as Route Reflector client";
      tailf:cli-full-command;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      type empty;
    }
    leaf soft-reconfiguration {
      tailf:info
        "Per neighbor soft reconfiguration";
      tailf:cli-full-command;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      type enumeration {
        enum "inbound" {
          tailf:info
            "Allow inbound soft reconfiguration for this neighbor";
        }
      }
    }
    container remove-private-as {
      tailf:info
        "Remove private AS number from outbound updates";
      tailf:cli-compact-syntax;
      tailf:cli-sequence-commands {
        tailf:cli-reset-siblings;
      }
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      presence "true";
      leaf all {
        tailf:info
          "Remove all private AS numbers";
        type empty;
      }
      leaf replace-as {
        tailf:info
          "Replace all private AS numbers with local AS";
        type empty;
      }
    }
  }

  grouping ncs_rpc_notif_router-bgp-peer-session-grouping {
    container local-as {
      tailf:info
        "Specify a local-as number";
      tailf:cli-compact-syntax;
      tailf:cli-sequence-commands {
        tailf:cli-reset-siblings;
      }
      tailf:cli-delete-when-empty;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      presence "true";
      leaf as-no {
        tailf:cli-drop-node-name;
        type bgp-as-no-type;
      }
      leaf no-prepend {
        tailf:info
          "Do not prepend local-as to updates from ebgp peers";
        type empty;
      }
      leaf replace-as {
        tailf:info
          "Replace real AS with local AS in the EBGP updates";
        type empty;
      }
      leaf dual-as {
        tailf:info
          "Accept either real AS or local AS from the ebgp peer";
        type empty;
      }
    }
    container password {
      tailf:info
        "Set a password";
      tailf:cli-compact-syntax;
      tailf:cli-sequence-commands {
        tailf:cli-reset-siblings;
      }
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      leaf enctype {
        tailf:cli-drop-node-name;
        tailf:cli-optional-in-sequence;
        tailf:cli-incomplete-command;
        type uint8 {
          tailf:info
            "<0-7>;;Encryption type (0 to disable encryption, 7 for proprietary)";
          range "0..7";
        }
        default "0";
      }
      leaf text {
        tailf:cli-drop-node-name;
        tailf:cli-multi-value;
        tailf:cli-full-command;
        tailf:cli-disallow-value "0|1|2|3|4|5|6|7";
        type string {
          tailf:info
            "LINE;;The password";
        }
      }
    }
    container ttl-security {
      tailf:info
        "BGP ttl security check";
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      leaf hops {
        tailf:info
          "IP hops";
        type uint8 {
          tailf:info
            "<1-254>;;maximum number of hops";
          range "1..254";
        }
      }
    }
    container timers {
      tailf:info
        "BGP per neighbor timers";
      tailf:cli-compact-syntax;
      tailf:cli-sequence-commands {
        tailf:cli-reset-siblings;
      }
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      leaf keepalive-interval {
        tailf:cli-drop-node-name;
        tailf:cli-incomplete-command;
        type uint16 {
          range "0..65535";
          tailf:info
            "<0-65535>;;Keepalive interval";
        }
      }
      leaf holdtime {
        tailf:cli-drop-node-name;
        type uint16 {
          tailf:info
            "<0-65535>;;Holdtime";
          range "0..65535";
        }
      }
      leaf minimum-neighbor-hold {
        tailf:cli-drop-node-name;
        type uint16 {
          tailf:info
            "<0-65535>;;Minimum hold time from neighbor";
          range "0..65535";
        }
      }
    }
    container fall-over {
      tailf:info
        "session fall on peer route lost";
      tailf:cli-delete-when-empty;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      presence "true";
      leaf route-map {
        tailf:info
          "Route map for peer route";
        type string {
          tailf:info
            "WORD;;Name of the route map";
        }
      }
    }
    container fall-over-bfd {
      tailf:cli-drop-node-name;
      container fall-over {
        tailf:info
          "session fall on peer route lost";
        tailf:cli-incomplete-command;
        tailf:cli-incomplete-no;
        tailf:cli-diff-dependency "../../inherit/peer-session" {
          tailf:xpath-root 3;
        }
        tailf:cli-diff-dependency "../../peer-group" {
          tailf:xpath-root 3;
        }
        tailf:cli-diff-dependency "../../remote-as" {
          tailf:xpath-root 3;
        }
        tailf:cli-diff-dependency "../../activate" {
          tailf:xpath-root 3;
        }
        tailf:cli-diff-dependency "../../fall-over" {
          tailf:xpath-root 3;
        }
        leaf bfd {
          tailf:info
            "Use BFD to detect failure";
          type empty;
        }
      }
    }
    container ebgp-multihop {
      tailf:info
        "Allow EBGP neighbors not on directly connected networks";
      tailf:cli-delete-when-empty;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      presence "true";
      leaf max-hop {
        tailf:cli-drop-node-name;
        type uint8 {
          tailf:info
            "<1-255>;;maximum hop count";
          range "1..255";
        }
      }
    }
    container update-source {
      tailf:info
        "Source of routing updates";
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      uses ncs_rpc_notif_interface-name-grouping;
    }
    container path-attribute {
      tailf:info
        "BGP optional attribute filtering";
      list discard {
        tailf:info
          "Discard matching path-attribute for this neighbor";
        tailf:cli-suppress-mode;
        tailf:cli-delete-when-empty;
        tailf:cli-incomplete-command;
        key "id";
        leaf id {
          type uint8 {
            tailf:info
              "<1-255>;;path attribute type";
            range "1..255";
          }
        }
        leaf in {
          tailf:info
            "Perform inbound path-attribute filtering";
          type empty;
        }
      }
    }
    leaf version {
      tailf:info
        "Set the BGP version to match a neighbor";
      tailf:cli-full-command;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      type uint8 {
        tailf:info
          "<4-4>;;Neighbor's BGP version";
        range "4";
      }
    }
    container transport {
      tailf:info
        "Transport options";
      leaf connection-mode {
        tailf:info
          "Specify passive or active connection";
        type enumeration {
          enum "active" {
            tailf:info
              "Actively establish the TCP session";
          }
          enum "passive" {
            tailf:info
              "Passively establish the TCP session";
          }
        }
      }
      container path-mtu-discovery {
        tailf:info
          "Use transport path MTU discovery";
        tailf:cli-delete-when-empty;
        presence "true";
        leaf disable {
          tailf:info
            "disable";
          type empty;
        }
      }
    }
    leaf disable-connected-check {
      tailf:info
        "One-hop away EBGP peer using loopback address";
      tailf:cli-full-command;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      type empty;
    }
  }

  grouping ncs_rpc_notif_router-bgp-neighbor-grouping {
    leaf remote-as {
      tailf:info
        "Specify a BGP neighbor";
      tailf:cli-delete-container-on-delete;
      tailf:cli-full-command;
      tailf:cli-diff-dependency "../inherit/peer-session" {
        tailf:xpath-root 3;
      }
      tailf:cli-diff-dependency "../peer-group" {
        tailf:xpath-root 3;
      }
      type string {
        tailf:info
          "AS of remote neighbor";
      }
    }
    leaf activate {
      tailf:info
        "Enable the Address Family for this Neighbor";
      tailf:cli-delete-container-on-delete;
      tailf:cli-full-command;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      type empty;
    }
    uses ncs_rpc_notif_router-bgp-peer-session-grouping;
    uses ncs_rpc_notif_router-bgp-peer-policy-grouping;
    leaf soo {
      tailf:info
        "Site-of-Origin extended community";
      tailf:cli-full-command;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      type string {
        tailf:info
          "ASN:nn or IP-address:nn;;VPN extended community";
      }
    }
    container capability {
      tailf:info
        "Advertise capability to the peer";
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      container orf {
        tailf:info
          "Advertise ORF capability to the peer";
        leaf-list prefix-list {
          tailf:info
            "Advertise prefixlist ORF capability to this neighbor";
          tailf:cli-flat-list-syntax;
          max-elements 1;
          type enumeration {
            enum "both" {
              tailf:info
                "Capability to SEND and RECEIVE the ORF to/from this neighbor";
            }
            enum "receive" {
              tailf:info
                "Capability to RECEIVE the ORF from this neighbor";
            }
            enum "send" {
              tailf:info
                "Capability to SEND the ORF to this neighbor";
            }
          }
        }
      }
    }
    leaf description {
      tailf:info
        "Neighbor specific description";
      tailf:cli-multi-value;
      tailf:cli-preformatted;
      tailf:cli-full-command;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      type string {
        tailf:info
          "LINE;;Up to 80 characters describing this neighbor";
      }
    }
    uses ncs_rpc_notif_router-bgp-neighbor-distribute-list-grouping;
    leaf dmzlink-bw {
      tailf:info
        "Propagate the DMZ link bandwidth";
      tailf:cli-full-command;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      type empty;
    }
    list filter-list {
      tailf:info
        "Establish BGP filters";
      tailf:cli-suppress-mode;
      tailf:cli-delete-when-empty;
      tailf:cli-compact-syntax;
      tailf:cli-sequence-commands;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      key "direction";
      leaf direction {
        type enumeration {
          enum "in" {
            tailf:info
              "Filter incoming routes";
          }
          enum "out" {
            tailf:info
              "Filter outgoing routes";
          }
        }
      }
      leaf as-path-list {
        tailf:cli-drop-node-name;
        tailf:cli-prefix-key;
        type string {
          tailf:info
            "WORD;;Access-list number or name";
        }
      }
    }
    container inherit {
      tailf:info
        "Inherit a template";
      tailf:cli-diff-dependency "../peer-group" {
        tailf:xpath-root 3;
      }
      tailf:cli-diff-dependency "../remote-as" {
        tailf:xpath-root 3;
      }
      leaf peer-policy {
        tailf:info
          "Inherit a peer-policy template";
        tailf:cli-full-command;
        tailf:cli-diff-dependency "/ios:router/bgp/template/peer-policy" {
          tailf:xpath-root 3;
        }
        tailf:cli-diff-dependency "../../activate" {
          tailf:xpath-root 3;
        }
        type string {
          tailf:info
            "WORD;;Template name";
        }
      }
      leaf peer-session {
        tailf:info
          "Inherit a peer-session template";
        tailf:cli-full-command;
        tailf:cli-diff-dependency "/ios:router/bgp/template/peer-session" {
          tailf:xpath-root 3;
        }
        tailf:cli-diff-dependency "/ios:router/bgp/template/peer-session/remote-as" {
          tailf:xpath-root 3;
        }
        type string {
          tailf:info
            "WORD;;Template name";
        }
      }
    }
    container next-hop-self-arg {
      tailf:cli-drop-node-name;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      leaf next-hop-self {
        type string;
      }
    }
    leaf next-hop-unchanged {
      tailf:info
        "Propagate the iBGP paths's next hop unchanged for this neighbor";
      tailf:cli-full-command;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      type empty;
    }
    leaf shutdown {
      tailf:info
        "Administratively shut down this neighbor";
      tailf:cli-full-command;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      type empty;
    }
    container translate-update {
      tailf:info
        "Translate Update to MBGP format";
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      container ipv4 {
        tailf:info
          "Address Family";
        container multicast {
          tailf:info
            "Address Family modifier";
          tailf:cli-delete-when-empty;
          presence "Address Family modifier";
          leaf unicast {
            tailf:info
              "Address Family modifier";
            type empty;
          }
        }
      }
    }
    leaf unsuppress-map {
      tailf:info
        "Route-map to selectively unsuppress suppressed routes";
      tailf:cli-full-command;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      type string {
        tailf:info
          "WORD;;Name of route map";
      }
    }
    leaf weight {
      tailf:info
        "Set default weight for routes from this neighbor";
      tailf:cli-full-command;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      type uint16 {
        tailf:info
          "<0-65535>;;default weight";
        range "0..65535";
      }
    }
    container ha-mode {
      tailf:info
        "high availability mode";
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      container graceful-restart {
        tailf:info
          "graceful-restart for this peer";
        presence "true";
        leaf disable {
          tailf:info
            "disable graceful-restart";
          type empty;
        }
      }
      container sso {
        tailf:info
          "stateful-switchover support for this peer";
        presence "true";
        leaf disable {
          tailf:info
            "disable stateful-switchover";
          type empty;
        }
      }
    }
    container suppress-signaling-protocol {
      tailf:info
        "suppress VPLS signaling protocol";
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      leaf ldp {
        tailf:info
          "suppress ldp signaling, enable bgp signaling";
        tailf:cli-full-command;
        type empty;
      }
    }
    leaf prefix-length-size {
      tailf:info
        "Packet Level storage size for Prefixes";
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      type uint8 {
        tailf:info
          "<1-2>;;Storage size in bytes";
        range "1..2";
      }
    }
  }

  grouping ncs_rpc_notif_router-bgp-af-grouping {
    leaf synchronization {
      tailf:info
        "Perform IGP synchronization";
      tailf:cli-full-command;
      type empty;
    }
    leaf table-map {
      tailf:info
        "Map external entry attributes into routing table";
      tailf:cli-full-command;
      type string {
        tailf:info
          "WORD;;route-map name";
      }
    }
    container bgp-af {
      tailf:cli-drop-node-name;
      container bgp {
        tailf:info
          "BGP specific commands";
        leaf redistribute-internal {
          tailf:info
            "Allow redistribution of iBGP into IGPs (dangerous)";
          tailf:cli-full-command;
          type empty;
        }
        container dampening {
          tailf:info
            "Enable route-flap dampening";
          presence "true";
          choice dampening-choice {
            leaf route-map {
              tailf:info
                "Route-map to specify criteria for dampening";
              type string {
                tailf:info
                  "WORD;;route-map name";
              }
            }
            container dampen {
              tailf:cli-drop-node-name;
              tailf:cli-compact-syntax;
              tailf:cli-sequence-commands;
              leaf half-life-time {
                tailf:cli-drop-node-name;
                type uint8 {
                  tailf:info
                    "<1-45>;;Half-life time for the penalty";
                  range "1..45";
                }
              }
              leaf reuse-time {
                tailf:cli-drop-node-name;
                tailf:cli-incomplete-command;
                type uint16 {
                  tailf:info
                    "<1-20000>;;Value to start reusing a route";
                  range "1..20000";
                }
              }
              leaf suppress-time {
                tailf:cli-drop-node-name;
                tailf:cli-incomplete-command;
                type uint16 {
                  tailf:info
                    "<1-20000>;;Value to start suppressing a route";
                  range "1..20000";
                }
              }
              leaf max-suppress-time {
                tailf:cli-drop-node-name;
                type uint8 {
                  tailf:info
                    "<1-255>;;Maximum duration to suppress a stable route";
                  range "1..255";
                }
              }
            }
          }
        }
        container additional-paths {
          tailf:info
            "Additional paths in the BGP table";
          choice send-receive-choice {
            leaf receive {
              tailf:info
                "Receive additional paths from neighbors";
              tailf:cli-full-command;
              type empty;
            }
            container send {
              tailf:info
                "Send additional paths to neighbors";
              tailf:cli-delete-when-empty;
              presence "true";
              leaf receive {
                tailf:info
                  "Receive additional paths from neighbors";
                type empty;
              }
            }
          }
          leaf install {
            tailf:info
              "Additional paths to install into RIB";
            tailf:cli-full-command;
            type empty;
          }
        }
        container bestpath {
          tailf:info
            "Change the default bestpath selection";
          container igp-metric {
            tailf:info
              "igp metric";
            leaf ignore {
              tailf:info
                "Ignore igp metric in bestpath selection";
              type empty;
            }
          }
        }
        leaf suppress-inactive {
          tailf:info
            "Suppress routes that are not in the routing table";
          tailf:cli-full-command;
          type empty;
        }
        leaf dmzlink-bw {
          tailf:info
            "Use DMZ Link Bandwidth as weight for BGP multipaths";
          tailf:cli-full-command;
          type empty;
        }
        leaf soft-reconfig-backup {
          tailf:info
            "Use soft-reconfiguration inbound only when route-refresh is not negotiated";
          tailf:cli-full-command;
          type empty;
        }
        container nexthop {
          tailf:info
            "Nexthop tracking commands";
          leaf route-map {
            tailf:info
              "Route map for valid nexthops";
            tailf:cli-full-command;
            type string {
              tailf:info
                "WORD;;route-map name";
            }
          }
          container trigger {
            tailf:info
              "Nexthop triggering";
            leaf delay {
              tailf:cli-full-command;
              tailf:info
                "Set the delay to tigger nexthop tracking";
              type uint8 {
                tailf:info
                  "<0-100>;;Delay value (seconds)";
                range "0..100";
              }
            }
            leaf enable {
              tailf:info
                "Enable nexthop tracking";
              tailf:cli-full-command;
              tailf:cli-boolean-no;
              type boolean;
              default "true";
            }
          }
        }
        leaf scan-time {
          tailf:cli-full-command;
          tailf:info
            "Configure background scanner interval";
          type uint8 {
            tailf:info
              "<5-60>;;Scanner interval (seconds)";
            range "5..60";
          }
        }
        list inject-map {
          tailf:info
            "Routemap which specifies prefixes to inject";
          tailf:cli-suppress-mode;
          tailf:cli-delete-when-empty;
          tailf:cli-compact-syntax;
          tailf:cli-sequence-commands;
          tailf:cli-incomplete-command;
          key "name";
          leaf name {
            type string {
              tailf:info
                "WORD;;route-map name";
            }
          }
          leaf exist-map {
            tailf:info
              "Routemap which specifies exist condition";
            type string {
              tailf:info
                "WORD;;route-map name";
            }
          }
          leaf copy-attributes {
            tailf:info
              "Copy attributes from aggregate";
            type empty;
          }
        }
        container recursion {
          tailf:info
            "recursion rule for the nexthops";
          leaf host {
            tailf:info
              "recursion via host for the nexthops";
            type empty;
          }
        }
      }
    }
    list network {
      tailf:info
        "Specify a network to announce via BGP";
      tailf:cli-suppress-mode;
      tailf:cli-delete-when-empty;
      tailf:cli-compact-syntax;
      tailf:cli-reset-container;
      key "number";
      leaf number {
        type union {
          type inet:ipv4-address {
            tailf:info
              "A.B.C.D;;Network number";
          }
          type ios:ipv6-prefix {
            tailf:info
              "X:X:X:X::X/<0-128>;;IPv6 prefix";
          }
        }
      }
      leaf backdoor {
        tailf:info
          "Specify a BGP backdoor route";
        tailf:cli-full-command;
        type empty;
      }
      leaf mask {
        tailf:info
          "Network mask";
        type inet:ipv4-address {
          tailf:info
            "A.B.C.D;;Network mask";
        }
      }
      leaf route-map {
        tailf:info
          "Route-map to modify the attributes";
        type string {
          tailf:info
            "WORD;;Name of the route map";
        }
      }
    }
    list aggregate-address {
      tailf:info
        "Configure BGP aggregate entries";
      tailf:cli-suppress-mode;
      tailf:cli-delete-when-empty;
      tailf:cli-compact-syntax;
      tailf:cli-sequence-commands {
        tailf:cli-reset-all-siblings;
      }
      key "address mask";
      leaf address {
        type inet:ipv4-address {
          tailf:info
            "A.B.C.D;;Aggregate address";
        }
      }
      leaf mask {
        type inet:ipv4-address {
          tailf:info
            "A.B.C.D;;Aggregate mask";
        }
      }
      uses ncs_rpc_notif_router-bgp-aggregate-address-content-grouping;
    }
    container aggregate-addres-ipv6 {
      tailf:cli-drop-node-name;
      list aggregate-address {
        tailf:info
          "Configure BGP aggregate entries";
        tailf:cli-suppress-mode;
        tailf:cli-delete-when-empty;
        tailf:cli-compact-syntax;
        tailf:cli-sequence-commands {
          tailf:cli-reset-all-siblings;
        }
        key "address";
        leaf address {
          type ipv6-prefix {
            tailf:info
              "X:X:X:X::X/<0-128>;;IPv6 Network number";
          }
        }
        uses ncs_rpc_notif_router-bgp-aggregate-address-content-grouping;
      }
    }
    container redistribute {
      tailf:info
        "Redistribute information from another routing protocol";
      container bgp {
        tailf:info
          "Border Gateway Protocol (BGP)";
        tailf:cli-compact-syntax;
        tailf:cli-sequence-commands;
        tailf:cli-delete-when-empty;
        leaf as-no {
          tailf:cli-drop-node-name;
          tailf:cli-remove-before-change;
          type bgp-as-no-type;
        }
        uses ncs_rpc_notif_router-bgp-redistribute-grouping {
          refine "metric" {
            tailf:cli-break-sequence-commands;
          }
        }
      }
      container connected {
        tailf:info
          "Connected";
        tailf:cli-compact-syntax;
        tailf:cli-delete-when-empty;
        presence "true";
        uses ncs_rpc_notif_router-bgp-redistribute-grouping;
      }
      container static {
        tailf:info
          "Static routes";
        tailf:cli-compact-syntax;
        tailf:cli-delete-when-empty;
        presence "true";
        uses ncs_rpc_notif_router-bgp-redistribute-grouping;
      }
      container dvmrp {
        tailf:info
          "Redistribution of DVMRP into BGP IPv4 Multicast";
        tailf:cli-compact-syntax;
        tailf:cli-sequence-commands;
        tailf:cli-delete-when-empty;
        presence "true";
        uses ncs_rpc_notif_route-map-metric-grouping;
      }
      list eigrp {
        tailf:info
          "Enhanced Interior Gateway Routing Protocol (EIGRP)";
        tailf:cli-suppress-mode;
        tailf:cli-delete-when-empty;
        tailf:cli-compact-syntax;
        tailf:cli-remove-before-change;
        key "as-no";
        leaf as-no {
          type eigrp-as-no-type;
        }
        uses ncs_rpc_notif_router-bgp-redistribute-grouping;
      }
      container isis {
        tailf:info
          "ISO IS-IS";
        tailf:cli-compact-syntax;
        tailf:cli-delete-when-empty;
        presence "true";
        uses ncs_rpc_notif_router-bgp-redistribute-isis-grouping;
        uses ncs_rpc_notif_router-bgp-redistribute-grouping;
        list isis-list {
          tailf:cli-drop-node-name;
          tailf:cli-suppress-mode;
          tailf:cli-delete-when-empty;
          tailf:cli-compact-syntax;
          tailf:cli-remove-before-change;
          key "name";
          leaf name {
            tailf:cli-disallow-value "level-1|level-2|level-1-2|metric|clns|ip|route-map|subnets|include-connected";
            type string {
              tailf:info
                "WORD;;ISO routing area tag";
            }
          }
          uses ncs_rpc_notif_router-bgp-redistribute-isis-grouping;
          uses ncs_rpc_notif_router-bgp-redistribute-grouping;
        }
      }
      container iso-igrp {
        tailf:info
          "IGRP for OSI networks";
        tailf:cli-compact-syntax;
        tailf:cli-delete-when-empty;
        uses ncs_rpc_notif_route-map-metric-grouping;
        list iso-igrp-area {
          tailf:cli-drop-node-name;
          tailf:cli-suppress-mode;
          tailf:cli-delete-when-empty;
          tailf:cli-compact-syntax;
          tailf:cli-remove-before-change;
          key "name";
          leaf name {
            type string {
              tailf:info
                "WORD;;Pointer to route-map entries";
              pattern '^([^r].*)|(r^[o].*)|(ro[^u].*)|(rou[^t].*)|(rout[^e].*)|(route[^\-].*)|(route-[^m].*)|(route-m[^a].*)|(route-ma[^p])|(route-map..*)';
            }
          }
          uses ncs_rpc_notif_route-map-metric-grouping;
        }
      }
      container mobile {
        tailf:info
          "Mobile routes";
        tailf:cli-compact-syntax;
        tailf:cli-delete-when-empty;
        presence "true";
        uses ncs_rpc_notif_router-bgp-redistribute-grouping;
      }
      container odr {
        tailf:info
          "On Demand stub Routes";
        tailf:cli-compact-syntax;
        tailf:cli-delete-when-empty;
        presence "true";
        uses ncs_rpc_notif_router-bgp-redistribute-grouping;
      }
      list ospf {
        tailf:info
          "Open Shortest Path First (OSPF)";
        tailf:cli-suppress-mode;
        tailf:cli-flatten-container;
        tailf:cli-compact-syntax;
        tailf:cli-delete-when-empty;
        tailf:cli-remove-before-change;
        key "id";
        leaf id {
          type uint16 {
            tailf:info
              "<1-65535>;;Process ID";
            range "1..65535";
          }
        }
        leaf vrf {
          tailf:info
            "VPN Routing/Forwarding Instance";
          tailf:cli-diff-dependency "/ios:ip/vrf" {
            tailf:xpath-root 3;
          }
          tailf:cli-diff-dependency "/ios:vrf/definition" {
            tailf:xpath-root 3;
          }
          type string {
            tailf:info
              "WORD;;VPN Routing/Forwarding Instance (VRF) name";
          }
        }
        uses ncs_rpc_notif_router-bgp-redistribute-ospf-grouping;
      }
      container rip {
        tailf:info
          "Routing Information Protocol (RIP)";
        tailf:cli-compact-syntax;
        tailf:cli-delete-when-empty;
        presence "true";
        uses ncs_rpc_notif_router-bgp-redistribute-grouping;
      }
      container lisp {
        tailf:info
          "Locator ID Separation Protocol (LISP)";
        tailf:cli-compact-syntax;
        tailf:cli-delete-when-empty;
        presence "true";
        uses ncs_rpc_notif_router-bgp-redistribute-grouping;
      }
    }
    container neighbor-tag {
      tailf:cli-drop-node-name;
      list neighbor {
        tailf:info
          "Specify a neighbor router";
        tailf:cli-suppress-mode;
        tailf:cli-delete-when-empty;
        tailf:cli-incomplete-command;
        tailf:cli-show-long-obu-diffs;
        ordered-by user;
        key "id";
        leaf id {
          type string {
            tailf:info
              "WORD;;Neighbor tag";
          }
        }
        leaf peer-group {
          tailf:info
            "Configure peer-group";
          tailf:cli-delete-container-on-delete;
          tailf:cli-full-command;
          type empty;
        }
        uses ncs_rpc_notif_router-bgp-neighbor-grouping;
      }
    }
    list neighbor {
      tailf:info
        "Specify a neighbor router";
      tailf:cli-suppress-mode;
      tailf:cli-delete-when-empty;
      tailf:cli-incomplete-command;
      tailf:cli-diff-dependency "../neighbor-tag/neighbor" {
        tailf:xpath-root 3;
      }
      key "id";
      leaf id {
        type union {
          type inet:ipv4-address {
            tailf:info
              "A.B.C.D;;Neighbor address";
          }
          type inet:ipv6-address {
            tailf:info
              "X:X:X:X::X;;Neighbor IPv6 address";
          }
        }
      }
      leaf peer-group {
        tailf:info
          "Member of the peer-group";
        tailf:cli-delete-container-on-delete;
        tailf:cli-full-command;
        type string {
          tailf:info
            "WORD;;peer-group name";
        }
      }
      uses ncs_rpc_notif_router-bgp-neighbor-grouping;
    }
    container maximum-paths {
      tailf:info
        "Forward packets over multiple paths";
      uses ncs_rpc_notif_router-bgp-max-path-grouping;
      container eibgp {
        tailf:info
          "Both eBGP and iBGP paths as multipath";
        uses ncs_rpc_notif_router-bgp-max-path-grouping;
      }
      container ibgp {
        tailf:info
          "iBGP-multipath";
        choice ibgp-choice {
          default "b";
          case a {
            container unequal-cost {
              tailf:info
                "Perform Un-Equal cost multipath selection";
              uses ncs_rpc_notif_router-bgp-max-path-grouping;
            }
          }
          case b {
            uses ncs_rpc_notif_router-bgp-max-path-grouping;
          }
        }
      }
      leaf import {
        tailf:info
          "Maximum import paths";
        type uint16 {
          tailf:info
            "<1-16>;;Number of import paths";
          range "1..16";
        }
      }
    }
    container import {
      tailf:info
        "Configure path import";
      container path {
        tailf:info
          "Path selection and path limit";
        container selection {
          tailf:info
            "Path selection policy";
          choice selection-choice {
            leaf all {
              tailf:info
                "Import all available paths";
              type empty;
            }
            container bestpath {
              tailf:info
                "Import the best available path.";
              tailf:cli-delete-when-empty;
              presence "true";
              leaf strict {
                tailf:info
                  "Do not fallback to best available path";
                type empty;
              }
            }
            container multipaths {
              tailf:info
                "Import all multipaths.";
              tailf:cli-delete-when-empty;
              presence "true";
              leaf strict {
                tailf:info
                  "Do not fallback to best available path";
                type empty;
              }
            }
          }
        }
        leaf limit {
          tailf:info
            "Per net imported path limit";
          type uint8 {
            tailf:info
              "<2-255>;;Maximum number of paths that can be imported into a net";
            range "2..255";
          }
        }
      }
    }
    container default-information {
      tailf:info
        "Control distribution of default information";
      leaf originate {
        tailf:info
          "Distribute a default route";
        type empty;
      }
    }
    leaf default-metric {
      tailf:info
        "Set metric of redistributed routes";
      tailf:cli-full-command;
      type uint32 {
        tailf:info
          "<1-4294967295>;;Default metric";
        range "1..4294967295";
      }
    }
    uses ncs_rpc_notif_router-distribute-list-grouping;
    container distance {
      tailf:info
        "Define an administrative distance";
      container bgp {
        tailf:info
          "BGP distance";
        tailf:cli-compact-syntax;
        tailf:cli-sequence-commands;
        leaf extern-as {
          tailf:cli-drop-node-name;
          tailf:cli-incomplete-command;
          type uint16 {
            tailf:info
              "<1-255>;;Distance for routes external to the AS";
            range "1..255";
          }
        }
        leaf internal-as {
          tailf:cli-drop-node-name;
          tailf:cli-incomplete-command;
          type uint16 {
            tailf:info
              "<1-255>;;Distance for routes internal to the AS";
            range "1..255";
          }
        }
        leaf local {
          tailf:cli-drop-node-name;
          type uint16 {
            tailf:info
              "<1-255>;;Distance for local routes";
            range "1..255";
          }
        }
      }
      list adm-distance {
        tailf:cli-drop-node-name;
        tailf:cli-suppress-mode;
        tailf:cli-delete-when-empty;
        key "srcip wildbits";
        leaf distance {
          tailf:cli-drop-node-name;
          tailf:cli-prefix-key;
          type uint16 {
            tailf:info
              "<1-255>;;Administrative distance";
            range "1..255";
          }
        }
        leaf srcip {
          type inet:ipv4-address {
            tailf:info
              "A.B.C.D;;IP Source address";
          }
        }
        leaf wildbits {
          type inet:ipv4-address {
            tailf:info
              "A.B.C.D;;Wildcard bits";
          }
        }
        leaf access-list {
          tailf:cli-drop-node-name;
          type std-ip-acl-type;
        }
      }
    }
    leaf auto-summary {
      tailf:info
        "Enable automatic network number summarization";
      tailf:cli-boolean-no;
      tailf:cli-full-command;
      type boolean;
    }
  }

  grouping ncs_rpc_notif_router-bgp-bgp-grouping {
    container bgp {
      leaf router-id {
        tailf:info
          "Override configured router identifier (peers will reset)";
        tailf:cli-full-command;
        type inet:ipv4-address {
          tailf:info
            "A.B.C.D;;Manually configured router identifier";
        }
      }
      leaf fast-external-fallover {
        tailf:info
          "Immediately reset session if a link to a directly connected external peer goes down";
        tailf:cli-boolean-no;
        tailf:cli-full-command;
        type boolean;
        default "true";
      }
      leaf always-compare-med {
        tailf:info
          "Allow comparing MED from different neighbors";
        tailf:cli-full-command;
        type empty;
      }
      leaf cluster-id {
        tailf:cli-full-command;
        type union {
          type uint32 {
            tailf:info
              "<1-4294967295>;;Route-Reflector Cluster-id as 32 bit quantity";
            range "1..4294967295";
          }
          type inet:ipv4-address {
            tailf:info
              "A.B.C.D;;Route-Reflector Cluster-id in IP address format";
          }
        }
      }
      container transport {
        tailf:info
          "global enable/disable transport session parameters";
        leaf path-mtu-discovery {
          tailf:info
            "transport path MTU discovery";
          tailf:cli-boolean-no;
          tailf:cli-full-command;
          type boolean;
          default "true";
        }
      }
      leaf enforce-first-as {
        tailf:info
          "Enforce the first AS for EBGP routes(default)";
        tailf:cli-boolean-no;
        tailf:cli-full-command;
        type boolean;
        default "true";
      }
      container client-to-client {
        tailf:info
          "Configure client to client route reflection";
        leaf reflection {
          tailf:info
            "reflection of routes allowed";
          tailf:cli-boolean-no;
          tailf:cli-full-command;
          type boolean;
          default "true";
        }
      }
      leaf log-neighbor-changes {
        tailf:info
          "Log neighbor up/down and reset reason";
        tailf:cli-boolean-no;
        tailf:cli-full-command;
        type boolean;
      }
      container confederation {
        tailf:info
          "AS confederation parameters";
        leaf identifier {
          tailf:info
            "as number";
          tailf:cli-full-command;
          type uint16 {
            tailf:info
              "<1-65535>;;Set routing domain confederation AS";
            range "1..65535";
          }
        }
        container peers {
          tailf:info
            "Peer ASs in BGP confederation";
          leaf-list as-no {
            tailf:cli-drop-node-name;
            tailf:cli-flat-list-syntax;
            type bgp-as-no-type;
          }
        }
      }
      leaf deterministic-med {
        tailf:cli-full-command;
        tailf:info
          "Pick the best-MED path among paths advertised from the neighboring AS";
        type empty;
      }
      container listen {
        tailf:info
          "Neighbor subnet range listener";
        list range {
          tailf:info
            "Subnet network range";
          tailf:cli-suppress-mode;
          tailf:cli-delete-when-empty;
          tailf:cli-incomplete-command;
          key "network-length";
          leaf network-length {
            type ios:ipv4-prefix {
              tailf:info
                "A.B.C.D/nn;;Subnet range <network>/<length>, e.g., 10.0.0.0/24";
            }
          }
          leaf peer-group {
            tailf:info
              "Member of the peer-group";
            type string {
              tailf:info
                "WORD;;peer-group name";
            }
          }
        }
        leaf limit {
          tailf:info
            "Set the max limit for the dynamic subnet range neighbors";
          type uint32 {
            tailf:info
              "<1-5000>;;max number";
            range "1..5000";
          }
        }
      }
      leaf update-delay {
        tailf:info
          "Set the max initial delay for sending update";
        tailf:cli-full-command;
        type uint16 {
          tailf:info
            "<1-3600>;;Delay value (seconds)";
          range "1..3600";
        }
      }
      container graceful-restart-conf {
        tailf:cli-drop-node-name;
        container graceful-restart {
          tailf:info
            "Graceful restart capability parameters";
          tailf:cli-incomplete-no;
          tailf:cli-incomplete-command;
          leaf restart-time {
            tailf:info
              "Set the max time needed to restart and come back up";
            tailf:cli-full-command;
            type uint16 {
              tailf:info
                "<1-3600>;;Delay value (seconds)";
              range "1..3600";
            }
            default "120";
          }
          leaf stalepath-time {
            tailf:info
              "Set the max time to hold onto restarting peer's stale paths";
            type uint16 {
              tailf:info
                "<1-3600>;;Delay value (seconds)";
              range "1..3600";
            }
            default "360";
          }
        }
      }
      leaf graceful-restart {
        tailf:info
          "Graceful restart capability parameters";
        tailf:cli-full-command;
        type empty;
      }
      container regexp {
        tailf:info
          "Select regular expression engine";
        leaf deterministic {
          tailf:info
            "Enable bounded-execution-time regular expression engine";
          tailf:cli-boolean-no;
          type boolean;
          default "true";
        }
      }
      container bestpath {
        tailf:info
          "Change the default bestpath selection";
        leaf compare-routerid {
          tailf:info
            "Compare router-id for identical EBGP paths";
          tailf:cli-full-command;
          type empty;
        }
        container cost-community {
          tailf:info
            "cost community";
          leaf ignore {
            tailf:info
              "Ignore cost communities in bestpath selection";
            type empty;
          }
        }
        container med {
          tailf:info
            "MED attribute";
          choice med-choice {
            container confed {
              tailf:info
                "Compare MED among confederation paths";
              presence "Compare MED among confederation paths";
              leaf missing-at-worst {
                tailf:info
                  "Treat missing MED as the least preferred one";
                type empty;
              }
            }
            leaf missing-at-worst {
              tailf:info
                "Treat missing MED as the least preferred one";
              type empty;
            }
          }
        }
        container as-path {
          leaf multipath-relax {
            type empty;
          }
        }
      }
      leaf maxas-limit {
        tailf:info
          "Allow AS-PATH attribute from any neighbor imposing a limit on number of ASes";
        tailf:cli-full-command;
        type uint16 {
          tailf:info
            "<1-2000>;;Number of ASes in the AS-PATH attribute";
          range "1..2000";
        }
      }
      container default {
        tailf:info
          "Configure BGP defaults";
        leaf ipv4-unicast {
          tailf:info
            "Activate ipv4-unicast for a peer by default";
          tailf:cli-boolean-no;
          type boolean;
          default "true";
        }
        leaf ipv4-activate {
          tailf:cli-boolean-no;
          type boolean;
          default "true";
        }
        leaf local-preference {
          tailf:info
            "local preference (higher=more preferred)";
          type uint32 {
            tailf:info
              "<0-4294967295>;;Configure default local preference value";
            range "1..4294967295";
          }
        }
        container route-target {
          tailf:info
            "Control behavior based on Route-Target attributes";
          leaf filter {
            tailf:info
              "Control automatic VPN Route-Target filtering";
            tailf:cli-boolean-no;
            type boolean;
            default "true";
          }
        }
      }
    }
    container timers {
      tailf:info
        "Adjust routing timers";
      container bgp {
        tailf:info
          "BGP timers";
        tailf:cli-compact-syntax;
        tailf:cli-sequence-commands {
          tailf:cli-reset-siblings;
        }
        leaf keepalive {
          tailf:cli-drop-node-name;
          tailf:cli-incomplete-command;
          type uint16 {
            tailf:info
              "<0-65535>;;Keepalive interval";
            range "0..65535";
          }
        }
        leaf holdtime {
          tailf:cli-drop-node-name;
          type uint16 {
            tailf:info
              "<0-65535>;;Holdtime";
            range "0..65535";
          }
        }
        leaf min-holdtime {
          tailf:cli-drop-node-name;
          type uint16 {
            tailf:info
              "<0-65535>;;Minimum hold time from neighbor";
            range "0..65535";
          }
        }
      }
    }
  }

  grouping ncs_rpc_notif_router-ospf-af-grouping;

  grouping ncs_rpc_notif_router-ospfv3-af-grouping {
    container capability {
      tailf:info
        "Enable a specific feature";
      leaf vrf-lite {
        tailf:info
          "Do not perform PE specific checks";
        type empty;
      }
    }
    container discard-route {
      tailf:info
        "Enable or disable discard-route installation";
      leaf external {
        tailf:info
          "Discard route for summarised redistributed routes";
        tailf:cli-boolean-no;
        tailf:cli-full-command;
        type boolean;
        default "true";
      }
      leaf internal {
        tailf:info
          "Discard route for summarised inter-area routes";
        tailf:cli-boolean-no;
        tailf:cli-full-command;
        type boolean;
        default "true";
      }
    }
  }

  grouping ncs_rpc_notif_router-ospf-common-af-grouping {
    container default-information {
      tailf:info
        "Control distribution of default information";
      container originate {
        tailf:info
          "Distribute a default route";
        tailf:cli-compact-syntax;
        tailf:meta-data "trim-delete-when-empty" {
          tailf:meta-value "( originate)";
        }
        tailf:ned-data "." {
          tailf:xpath-root 3;
          tailf:transaction to;
        }
        presence "true";
        leaf always {
          tailf:info
            "Always advertise default route";
          type empty;
        }
        leaf metric {
          tailf:info
            "OSPF default metric";
          type uint32 {
            tailf:info
              "<0-16777214>;;OSPF metric";
            range "0..16777214";
          }
        }
        leaf metric-type {
          tailf:info
            "OSPF metric type for default routes";
          type ospf-metric-type;
          default "2";
        }
        leaf route-map {
          tailf:info
            "Route map reference";
          type string {
            tailf:info
              "WORD;;Route map name";
          }
        }
      }
    }
    leaf default-metric {
      tailf:info
        "Set metric of redistributed routes";
      tailf:cli-full-command;
      type uint32 {
        tailf:info
          "<1-16777214>;;OSPF default metric";
        range "1..16777214";
      }
    }
    container distance {
      tailf:info
        "Define an administrative distance";
      leaf weight {
        tailf:cli-drop-node-name;
        type uint8 {
          tailf:info
            "<1-255>;;Administrative distance";
          range "1..255";
        }
      }
      list distance-list {
        tailf:cli-drop-node-name;
        tailf:cli-suppress-mode;
        tailf:cli-delete-when-empty;
        tailf:cli-compact-syntax;
        tailf:cli-sequence-commands {
          tailf:cli-reset-siblings;
        }
        key "ip-address wildcard-mask";
        leaf ip-address {
          type inet:ipv4-address {
            tailf:info
              "A.B.C.D;;IP source address";
          }
        }
        leaf wildcard-mask {
          type inet:ipv4-address {
            tailf:info
              "A.B.C.D;;Wildcard bits";
          }
        }
        leaf weight {
          tailf:cli-drop-node-name;
          tailf:cli-prefix-key;
          type uint8 {
            tailf:info
              "<1-255>;;Administrative distance";
            range "1..255";
          }
        }
        leaf access-list {
          tailf:cli-drop-node-name;
          type std-ip-acl-type;
        }
      }
      container ospf {
        tailf:info
          "OSPF routes Administrative distance";
        tailf:cli-compact-syntax;
        leaf intra-area {
          tailf:info
            "Intra-area routes";
          type uint32 {
            tailf:info
              "<1-255>;;Distance for intra-area routes";
            range "1..255";
          }
        }
        leaf inter-area {
          tailf:info
            "Inter-area routes";
          type uint32 {
            tailf:info
              "<1-255>;;Distance for inter-area routes";
            range "1..255";
          }
        }
        leaf external {
          tailf:info
            "External routes";
          type uint32 {
            tailf:info
              "<1-255>;;Distance for external routes";
            range "1..255";
          }
        }
      }
    }
    leaf maximum-paths {
      tailf:info
        "Forward packets over multiple paths";
      tailf:cli-full-command;
      type uint32 {
        range "1..32";
        tailf:info
          "<1-32>;;Number of paths";
      }
    }
    leaf nsr {
      tailf:info
        "Enable non-stop routing";
      type empty;
    }
    container redistribute {
      tailf:info
        "Redistribute information from another routing protocol";
      container connected {
        tailf:info
          "Connected";
        tailf:cli-compact-syntax;
        tailf:cli-delete-when-empty;
        presence "true";
        uses ncs_rpc_notif_router-ospf-redistribute-grouping;
        uses ncs_rpc_notif_router-ospf-route-map-grouping;
      }
      container static {
        tailf:info
          "Static routes";
        tailf:cli-compact-syntax;
        tailf:cli-delete-when-empty;
        presence "true";
        uses ncs_rpc_notif_router-ospf-redistribute-grouping;
        uses ncs_rpc_notif_router-ospf-route-map-grouping;
      }
      container odr {
        tailf:info
          "On Demand stub Routes";
        tailf:cli-compact-syntax;
        presence "true";
        uses ncs_rpc_notif_router-ospf-redistribute-grouping;
        uses ncs_rpc_notif_router-ospf-route-map-grouping;
      }
      container bgp {
        tailf:info
          "Border Gateway Protocol (BGP)";
        tailf:cli-compact-syntax;
        tailf:cli-sequence-commands;
        leaf as-no {
          tailf:cli-drop-node-name;
          tailf:cli-remove-before-change;
          tailf:cli-delete-container-on-delete;
          tailf:cli-diff-dependency "/ios:router/bgp" {
            tailf:xpath-root 3;
          }
          type bgp-as-no-type;
        }
        uses ncs_rpc_notif_router-ospf-redistribute-grouping {
          refine "metric" {
            tailf:cli-break-sequence-commands;
          }
        }
        uses ncs_rpc_notif_router-ospf-route-map-grouping;
      }
      list ospf {
        tailf:info
          "Open Shortest Path First (OSPF)";
        tailf:cli-suppress-mode;
        tailf:cli-delete-when-empty;
        tailf:cli-compact-syntax;
        key "id";
        leaf id {
          tailf:cli-suppress-range;
          type uint16 {
            tailf:info
              "<1-65535>;;Process ID";
            range "1..65535";
          }
        }
        uses ncs_rpc_notif_router-ospf-redistribute-grouping;
        uses ncs_rpc_notif_redistribute-ospf-match-grouping;
        uses ncs_rpc_notif_router-ospf-route-map-grouping;
      }
      container isis {
        tailf:info
          "ISO IS-IS";
        tailf:cli-compact-syntax;
        presence "true";
        uses ncs_rpc_notif_router-isis-level-grouping;
        uses ncs_rpc_notif_router-ospf-redistribute-grouping;
        uses ncs_rpc_notif_router-ospf-route-map-grouping;
        list isis-area {
          tailf:cli-drop-node-name;
          tailf:cli-suppress-mode;
          tailf:cli-delete-when-empty;
          tailf:cli-compact-syntax;
          key "name";
          leaf name {
            tailf:cli-disallow-value "level-1|level-2|level-1-2|metric|metric-type|route-map|nssa-only|subnets|tag";
            type string {
              tailf:info
                "WORD;;ISO routing area tag";
            }
          }
          uses ncs_rpc_notif_router-isis-level-grouping;
          uses ncs_rpc_notif_router-ospf-redistribute-grouping;
          uses ncs_rpc_notif_router-ospf-route-map-grouping;
        }
      }
      list eigrp {
        tailf:info
          "Enhanced Interior Gateway Routing Protocol (EIGRP)";
        tailf:cli-suppress-mode;
        tailf:cli-delete-when-empty;
        tailf:cli-compact-syntax;
        key "as-no";
        leaf as-no {
          type eigrp-as-no-type;
        }
        uses ncs_rpc_notif_router-ospf-redistribute-grouping;
        uses ncs_rpc_notif_router-ospf-route-map-grouping;
      }
      container iso-igrp {
        tailf:info
          "IGRP for OSI networks";
        tailf:cli-compact-syntax;
        tailf:cli-sequence-commands;
        presence "true";
        leaf area-tag {
          tailf:cli-drop-node-name;
          tailf:cli-disallow-value "route-map";
          tailf:cli-optional-in-sequence;
          type string {
            tailf:info
              "WORD;;ISO routing area tag";
          }
        }
        uses ncs_rpc_notif_router-ospf-route-map-grouping;
        uses ncs_rpc_notif_router-ospf-redistribute-grouping;
      }
      container maximum-prefix {
        tailf:info
          "Maximum number of prefixes redistributed to protocol";
        tailf:cli-compact-syntax;
        tailf:cli-sequence-commands;
        leaf number {
          tailf:cli-drop-node-name;
          type uint32 {
            tailf:info
              "<1-4294967295>;;Maximum number of IP prefixes redistributed";
            range "1..4294967295";
          }
        }
        container threshold-warning-only-container {
          tailf:cli-drop-node-name;
          tailf:cli-flatten-container;
          tailf:cli-compact-syntax;
          leaf threshold {
            tailf:cli-drop-node-name;
            type uint32 {
              tailf:info
                "<1-100>;;Threshold value (%) at which to generate a warning message";
              range "1..100";
            }
          }
          leaf warning-only {
            tailf:info
              "Only give warning message when limit is exceeded";
            tailf:cli-full-command;
            type empty;
          }
        }
      }
      container mobile {
        tailf:info
          "Mobile routes";
        tailf:cli-compact-syntax;
        presence "true";
        uses ncs_rpc_notif_router-ospf-redistribute-grouping;
        uses ncs_rpc_notif_router-ospf-route-map-grouping;
      }
      container rip {
        tailf:info
          "Routing Information Protocol (RIP)";
        tailf:cli-compact-syntax;
        presence "true";
        uses ncs_rpc_notif_router-ospf-redistribute-grouping;
        uses ncs_rpc_notif_router-ospf-route-map-grouping;
        list redistribute-list-rip {
          tailf:cli-drop-node-name;
          tailf:cli-suppress-mode;
          tailf:cli-delete-when-empty;
          tailf:cli-compact-syntax;
          key "name";
          leaf name {
            type string {
              tailf:info
                "WORD;;User selected string identifying this process";
            }
          }
          uses ncs_rpc_notif_router-ospf-redistribute-grouping;
          uses ncs_rpc_notif_router-ospf-route-map-grouping;
        }
      }
      container lisp {
        tailf:info
          "Locator ID Separation Protocol (LISP)";
        container subnets {
          tailf:info
            "Consider subnets for redistribution into OSPF";
          tailf:cli-compact-syntax;
          tailf:cli-delete-when-empty;
          presence "true";
        }
      }
    }
  }

  grouping ncs_rpc_notif_router-ospf-common-grouping {
    list area {
      tailf:info
        "OSPF area parameters";
      tailf:cli-suppress-mode;
      tailf:cli-delete-when-empty;
      tailf:cli-incomplete-command;
      key "id";
      leaf id {
        tailf:cli-suppress-range;
        type ospf-area-type;
      }
      container authentication {
        tailf:info
          "Enable authentication";
        presence "true";
        leaf message-digest {
          tailf:info
            "Use message-digest authentication";
          type empty;
        }
        choice authentication-choice {
          leaf null {
            tailf:info
              "Use no authentication";
            tailf:cli-full-command;
            type empty;
          }
          leaf key-chain {
            tailf:info
              "Use a key-chain for cryptographic authentication keys";
            tailf:cli-full-command;
            type string {
              tailf:info
                "LINE;;name of key-chain";
            }
          }
        }
      }
      container nssa {
        tailf:info
          "Specify a NSSA area";
        tailf:cli-compact-syntax;
        tailf:meta-data "trim-delete-when-empty" {
          tailf:meta-value "( nssa)";
        }
        tailf:ned-data "." {
          tailf:xpath-root 3;
          tailf:transaction to;
        }
        tailf:cli-diff-dependency "../stub" {
          tailf:xpath-root 3;
          tailf:cli-trigger-on-set;
        }
        presence "true";
        leaf no-redistribution {
          tailf:info
            "No redistribution into this NSSA area";
          type empty;
        }
        leaf default-information-originate {
          tailf:info
            "Originate Type 7 default into NSSA area";
          type empty;
        }
        leaf metric {
          tailf:info
            "OSPF default metric";
          when "../default-information-originate" {
            tailf:xpath-root 3;
            tailf:dependency "../default-information-originate";
          }
          type uint32 {
            tailf:info
              "<0-16777214>;;OSPF metric";
            range "0..16777214";
          }
        }
        leaf metric-type {
          tailf:info
            "OSPF metric type for default routes";
          type ospf-metric-type;
          default "2";
        }
        leaf nssa-only {
          tailf:info
            "Limit default advertisement to this NSSA area";
          type empty;
        }
        leaf no-ext-capability {
          tailf:info
            "Do not send domain specific capabilities into NSSA";
          type empty;
        }
        leaf no-summary {
          tailf:info
            "Do not send summary LSA into NSSA";
          type empty;
        }
        container translate {
          tailf:info
            "Translate LSA";
          container type7 {
            tailf:info
              "From Type 7 to Type 5";
            tailf:cli-compact-syntax;
            leaf always {
              tailf:info
                "Always translate LSAs on this ABR";
              type empty;
            }
            leaf suppress-fa {
              tailf:info
                "Suppress forwarding address in translated LSAs";
              type empty;
            }
          }
        }
      }
      leaf default-cost {
        tailf:info
          "Set the summary default-cost of a NSSA/stub area";
        tailf:cli-full-command;
        type uint32 {
          tailf:info
            "<0-16777215;;Stub's advertised external route metric";
          range "0..16777215";
        }
      }
      list filter-list {
        tailf:info
          "Filter networks between OSPF areas";
        tailf:cli-suppress-mode;
        tailf:cli-delete-when-empty;
        tailf:cli-compact-syntax;
        tailf:cli-sequence-commands;
        key "direction";
        leaf direction {
          type enumeration {
            enum "in" {
              tailf:info
                "Filter networks sent to this area";
            }
            enum "out" {
              tailf:info
                "Filter networks sent from this area";
            }
          }
        }
        leaf prefix {
          tailf:cli-prefix-key;
          tailf:info
            "Filter prefixes between OSPF areas";
          type string {
            tailf:info
              "WORD;;Name of an IP prefix-list";
          }
        }
      }
      list range {
        tailf:info
          "Summarize routes matching address/mask (border routers only)";
        tailf:cli-compact-syntax;
        tailf:cli-suppress-mode;
        tailf:cli-delete-when-empty;
        key "ip mask";
        leaf ip {
          type inet:ipv4-address {
            tailf:info
              "A.B.C.D;;IP address to match";
          }
        }
        leaf mask {
          type inet:ipv4-address {
            tailf:info
              "A.B.C.D;;IP mask for address";
          }
        }
        leaf advertise {
          tailf:cli-drop-node-name;
          type enumeration {
            enum "advertise" {
              tailf:info
                "Advertise this range (default)";
            }
            enum "not-advertise" {
              tailf:info
                "DoNotAdvertise this range";
            }
          }
          default "advertise";
        }
        leaf cost {
          tailf:info
            "User specified metric for this range";
          type uint32 {
            tailf:info
              "<0-16777215>;;Advertised metric for this range";
            range "0..16777215";
          }
        }
      }
      container range-ipv6 {
        tailf:cli-drop-node-name;
        list range {
          tailf:info
            "Summarize routes matching address/mask(border routers only)";
          tailf:cli-compact-syntax;
          tailf:cli-suppress-mode;
          tailf:cli-delete-when-empty;
          key "prefix";
          leaf prefix {
            type ipv6-prefix {
              tailf:info
                "X:X:X:X::X/<0-128>;;IPv6 prefix to match";
            }
          }
          leaf advertise {
            tailf:cli-drop-node-name;
            type enumeration {
              enum "advertise" {
                tailf:info
                  "Advertise this range (default)";
              }
              enum "not-advertise" {
                tailf:info
                  "DoNotAdvertise this range";
              }
            }
            default "advertise";
          }
          leaf cost {
            tailf:info
              "User specified metric for this range";
            type uint32 {
              tailf:info
                "<0-16777215>;;Advertised metric for this range";
              range "0..16777215";
            }
          }
        }
      }
      list sham-link {
        tailf:info
          "Define a sham link and its parameters";
        tailf:cli-suppress-mode;
        tailf:cli-delete-when-empty;
        key "source dest";
        leaf source {
          type inet:ipv4-address {
            tailf:info
              "A.B.C.D;;IP addr associated with sham-link source";
          }
        }
        leaf dest {
          type inet:ipv4-address {
            tailf:info
              "A.B.C.D;;IP addr associated with sham-link destination";
          }
        }
        leaf cost {
          tailf:info
            "Associate a cost with the sham-link";
          type uint16 {
            tailf:info
              "<1-65535>;;Cost of the sham-link";
            range "0..65535";
          }
        }
      }
      container stub {
        tailf:info
          "Specify a stub area";
        tailf:cli-compact-syntax;
        tailf:meta-data "trim-delete-when-empty" {
          tailf:meta-value "( stub)";
        }
        tailf:ned-data "." {
          tailf:xpath-root 3;
          tailf:transaction to;
        }
        tailf:cli-diff-dependency "../nssa" {
          tailf:xpath-root 3;
          tailf:cli-trigger-on-set;
        }
        presence "true";
        leaf no-summary {
          tailf:info
            "Do not send summary LSA into stub area";
          type empty;
        }
        leaf no-ext-capability {
          tailf:info
            "Do not send domain specific capabilities into stub area";
          type empty;
        }
      }
      list virtual-link {
        tailf:info
          "Define a virtual link and its parameters";
        tailf:cli-suppress-mode;
        tailf:cli-delete-when-empty;
        tailf:cli-compact-syntax;
        key "id";
        leaf id {
          type inet:ipv4-address {
            tailf:info
              "A.B.C.D;;ID (IP addr) associated with virtual link neighbor";
          }
        }
        leaf retransmit-interval {
          tailf:info
            "LSA retransmit interval";
          type uint16 {
            tailf:info
              "<1-8192>;;Seconds";
            range "1..8192";
          }
        }
        leaf transmit-delay {
          tailf:info
            "LSA transmission delay";
          type uint16 {
            tailf:info
              "<1-8192>;;Seconds";
            range "1..8192";
          }
          default "1";
        }
        leaf hello-interval {
          tailf:info
            "Hello packet interval";
          type int32 {
            tailf:info
              "<1-8192;;Seconds>";
            range "1..8192";
          }
        }
        leaf dead-interval {
          tailf:info
            "Dead router detection time";
          type uint16 {
            tailf:info
              "<1-8192;;Seconds>";
            range "1..8192";
          }
        }
        leaf authentication {
          tailf:info
            "Set authentication type";
          type empty;
        }
        container authentication-key {
          tailf:info
            "Set authentication key";
          tailf:cli-flatten-container;
          tailf:cli-compact-syntax;
          tailf:cli-sequence-commands {
            tailf:cli-reset-siblings;
          }
          uses ncs_rpc_notif_password-grouping;
        }
        list message-digest-key {
          tailf:info
            "Set message digest key";
          tailf:cli-suppress-mode;
          tailf:cli-delete-when-empty;
          tailf:cli-compact-syntax;
          tailf:cli-incomplete-command;
          key "id";
          leaf id {
            tailf:cli-suppress-range;
            type uint8 {
              tailf:info
                "<1-255>;;Key ID";
              range "1..255";
            }
          }
          container md5 {
            tailf:info
              "Use MD5 algorithm";
            tailf:cli-compact-syntax;
            tailf:cli-sequence-commands {
              tailf:cli-reset-siblings;
            }
            leaf auth-type {
              tailf:cli-drop-node-name;
              tailf:cli-optional-in-sequence;
              tailf:cli-incomplete-command;
              type uint8 {
                tailf:info
                  "<0-7>;;Encryption type (0 for not yet encrypted, 7 for proprietary)";
                range "0..7";
              }
              default "0";
            }
            leaf auth-key {
              tailf:cli-drop-node-name;
              tailf:cli-full-command;
              type string {
                tailf:info
                  "WORD;;Authentication key (16 chars)";
                length "1..16";
              }
            }
          }
        }
      }
    }
    container auto-cost {
      tailf:info
        "Calculate OSPF interface cost according to bandwidth";
      presence "Calculate OSPF interface cost according to bandwidth";
      leaf reference-bandwidth {
        tailf:info
          "Use reference bandwidth method to assign OSPF cost";
        type uint32 {
          tailf:info
            "<1-4294967>;;The reference bandwidth in terms of Mbits per second";
          range "1..4294967";
        }
      }
    }
    container bfd {
      tailf:info
        "BFD configuration commands";
      leaf all-interfaces {
        tailf:info
          "Enable BFD on all interfaces";
        type empty;
      }
    }
    container interface-id {
      tailf:info
        "Source of the interface ID";
      leaf snmp-if-index {
        tailf:info
          "SNMP MIB ifIndex";
        type empty;
      }
    }
    container log-adjacency-changes {
      tailf:info
        "Log changes in adjacency state";
      tailf:cli-show-no;
      presence "true";
      leaf detail {
        tailf:info
          "Log all state changes";
        type empty;
      }
    }
    container max-lsa {
      tailf:info
        "maximum number of LSAs OSPF process will receive";
      tailf:cli-compact-syntax;
      tailf:cli-sequence-commands {
        tailf:cli-reset-all-siblings;
      }
      leaf maximum-number {
        tailf:cli-drop-node-name;
        type uint32 {
          tailf:info
            "<1-4294967294>;;Maximum number of non self-generated LSAs this process can receive";
          range "1..4294967294";
        }
      }
      leaf threshold-percentage {
        tailf:cli-break-sequence-commands;
        tailf:cli-drop-node-name;
        type uint8 {
          tailf:info
            "<1-100>;;Threshold value (%) at which to generate a warning msg";
          range "1..100";
        }
      }
      leaf warning-only {
        tailf:info
          "Only give warning message when limit is exceeded";
        tailf:cli-full-command;
        type empty;
      }
      leaf ignore-time {
        tailf:info
          "time during which all adjacencies are suppressed";
        type uint32 {
          tailf:info
            "<1-17895>;;number of minutes during which all adjacencies are suppressed";
          range "1..17895";
        }
      }
      leaf reset-time {
        tailf:info
          "time after which ignore-count is reset to zero";
        type uint32 {
          tailf:info
            "<2-35791>;;number of minutes after which ignore-count is reset to zero";
          range "2..35791";
        }
        default "60";
      }
      leaf ignore-count {
        tailf:info
          "maximum number of times adjacencies can be suppressed";
        type uint32 {
          range "1..65534";
          tailf:info
            "<1-65534>;;count on how many times adjacencies can be suppressed";
        }
      }
    }
    uses ncs_rpc_notif_passive-interface-grouping;
    container queue-depth {
      tailf:info
        "OSPF Hello/Router process queue depth";
      leaf hello {
        tailf:info
          "OSPF Hello process queue depth";
        type union {
          type uint32 {
            tailf:info
              "<1-2147483647>;;maximum numer of packets in the queue";
            range "1..2147483647";
          }
          type enumeration {
            enum "unlimited" {
              tailf:info
                "Unlimited queue depth";
            }
          }
        }
        default "unlimited";
      }
      leaf update {
        tailf:info
          "OSPF Router process queue depth";
        type union {
          type uint32 {
            tailf:info
              "<1-2147483647>;;maximum numer of packets in the queue";
            range "1..2147483647";
          }
          type enumeration {
            enum "unlimited" {
              tailf:info
                "Unlimited queue depth";
            }
          }
        }
      }
    }
    container timers {
      tailf:info
        "Adjust routing timers";
      container lsa {
        tailf:info
          "OSPF LSA timers";
        leaf arrival {
          tailf:info
            "OSPF LSA arrival timer";
          type uint32 {
            range "0..600000";
            tailf:info
              "<0-600000>;;The minimum interval in milliseconds between accepting the same LSA";
          }
        }
      }
      container pacing {
        tailf:info
          "OSPF pacing timers";
        leaf flood {
          tailf:info
            "OSPF flood pacing timer";
          tailf:cli-full-command;
          type uint32 {
            tailf:info
              "<5-100>;;The minimum interval in msec to pace limit flooding on interface";
            range "5..100";
          }
        }
        leaf lsa-group {
          tailf:info
            "OSPF LSA group pacing timer";
          tailf:cli-full-command;
          type uint32 {
            tailf:info
              "<10-1800>;;Interval in sec between group of LSA being refreshed or maxaged";
            range "10..1800";
          }
        }
        leaf retransmission {
          tailf:info
            "OSPF retransmission pacing timer";
          tailf:cli-full-command;
          type uint32 {
            tailf:info
              "<5-200>;;The minimum interval in msec between neighbor retransmissions";
            range "5..200";
          }
        }
      }
      container throttle {
        tailf:info
          "OSPF throttle timers";
        container lsa {
          tailf:info
            "OSPF LSA throttle timers";
          tailf:cli-compact-syntax;
          tailf:cli-sequence-commands;
          leaf all {
            tailf:info
              "For all type of OSPF LSAs";
            tailf:cli-optional-in-sequence;
            tailf:cli-incomplete-command;
            type empty;
          }
          leaf start-interval {
            tailf:cli-drop-node-name;
            tailf:cli-incomplete-command;
            type uint32 {
              tailf:info
                "<0-600000>;;Delay to generate first occurrence of LSA in milliseconds";
              range "0..600000";
            }
          }
          leaf hold-interval {
            tailf:cli-drop-node-name;
            tailf:cli-incomplete-command;
            type uint32 {
              tailf:info
                "<0-600000>;;Minimum delay between originating the same LSA in milliseconds";
              range "0..600000";
            }
          }
          leaf max-interval {
            tailf:cli-drop-node-name;
            type uint32 {
              tailf:info
                "<0-600000>;;Maximum delay between originating the same LSA in milliseconds";
              range "0..600000";
            }
          }
        }
        container spf {
          tailf:info
            "OSPF SPF throttle timers";
          tailf:cli-sequence-commands;
          tailf:cli-compact-syntax;
          leaf spf-start {
            tailf:cli-drop-node-name;
            tailf:cli-incomplete-command;
            type uint32 {
              tailf:info
                "<0-600000>;;Delay between receiving a change to SPF calculation in milliseconds";
              range "0..600000";
            }
          }
          leaf spf-hold {
            tailf:cli-drop-node-name;
            tailf:cli-incomplete-command;
            type uint32 {
              tailf:info
                "<0-600000>;;Delay between first and second SPF calculation in milliseconds";
              range "0..600000";
            }
          }
          leaf spf-max-wait {
            tailf:cli-drop-node-name;
            type uint32 {
              tailf:info
                "<0-600000>;;Maximum wait time in milliseconds for SPF calculations";
              range "0..600000";
            }
          }
        }
      }
    }
    leaf router-id {
      tailf:cli-full-command;
      tailf:info
        "Override configured router identifier (peers will reset)";
      type inet:ipv4-address {
        tailf:info
          "A.B.C.D;;Manually configured router identifier";
      }
    }
  }

  grouping ncs_rpc_notif_router-ospf-grouping {
    container capability {
      tailf:info
        "Enable specific OSPF feature";
      leaf vrf-lite {
        tailf:info
          "Do not perform PE specific checks";
        type empty;
      }
      leaf opaque {
        tailf:info
          "Opaque LSA";
        tailf:cli-boolean-no;
        tailf:cli-full-command;
        type boolean;
        default "true";
      }
      leaf lls {
        tailf:info
          "Link-local Signaling (LLS) support";
        tailf:cli-boolean-no;
        tailf:cli-full-command;
        type boolean;
        default "true";
      }
      leaf transit {
        tailf:info
          "Transit Area";
        tailf:cli-boolean-no;
        tailf:cli-full-command;
        type boolean;
        default "true";
      }
    }
    container compatible {
      tailf:info
        "OSPF compatibility list";
      leaf rfc1583 {
        tailf:info
          "compatible with RFC 1583";
        tailf:cli-boolean-no;
        type boolean;
        default "true";
      }
    }
    uses ncs_rpc_notif_router-distribute-list-grouping;
    container domain-id {
      tailf:info
        "OSPF domain-id";
      choice domain-id-choice {
        case a {
          leaf ip-format {
            tailf:cli-drop-node-name;
            type inet:ipv4-address {
              tailf:info
                "A.B.C.D;;OSPF domain ID in IP address format";
            }
          }
          container ip-format-secondary {
            tailf:cli-drop-node-name;
            tailf:cli-compact-syntax;
            tailf:cli-sequence-commands;
            leaf ip {
              tailf:cli-drop-node-name;
              type inet:ipv4-address {
                tailf:info
                  "A.B.C.D;;OSPF domain ID in IP address format";
              }
            }
            leaf secondary {
              tailf:info
                "Secondary Domain-ID";
              type empty;
            }
          }
        }
        leaf Null {
          tailf:info
            "Null Domain-ID";
          tailf:cli-full-command;
          type empty;
        }
        container type {
          tailf:info
            "OSPF domain ID type in Hex format";
          tailf:cli-sequence-commands;
          tailf:cli-compact-syntax;
          leaf type-leaf {
            tailf:cli-drop-node-name;
            tailf:cli-incomplete-command;
            type enumeration {
              enum "0005" {
                tailf:info
                  "Type 0x0005";
              }
              enum "0105" {
                tailf:info
                  "Type 0x0105";
              }
              enum "0205" {
                tailf:info
                  "Type 0x0205";
              }
              enum "8005" {
                tailf:info
                  "Type 0x8005";
              }
            }
          }
          leaf value {
            tailf:info
              "OSPF domain ID value in Hex format";
            type string {
              tailf:info
                "Hex-data;;OSPF domain ID ext. community value in Hex";
              pattern '[0-9a-fA-F]{12}';
            }
          }
        }
      }
    }
    leaf domain-tag {
      tailf:info
        "OSPF domain-tag";
      tailf:cli-full-command;
      type uint32 {
        tailf:info
          "<1-4294967295>;;OSPF domain tag - 32-bit value";
        range "1..4294967295";
      }
    }
    container ignore {
      tailf:info
        "Do not complain about specific event";
      container lsa {
        tailf:info
          "Do not complain upon receiving LSA of the specified type";
        leaf mospf {
          tailf:info
            "MOSPF Type 6 LSA";
          type empty;
        }
      }
    }
    leaf ispf {
      tailf:info
        "Enable incremental SPF computation";
      tailf:cli-full-command;
      type empty;
    }
    container limit {
      tailf:info
        "Limit a specific OSPF feature";
      container retransmissions {
        tailf:info
          "LS update, DBD, and LS request retransmissions";
        tailf:cli-compact-syntax;
        leaf dc {
          tailf:info
            "Demand circuit retransmissions";
          type limit-dc-non-dc-type;
        }
        leaf non-dc {
          tailf:info
            "Non-demand-circuit retransmissions";
          type limit-dc-non-dc-type;
        }
      }
    }
    container local-rib-criteria {
      tailf:info
        "Enable or disable usage of local RIB as route criteria";
      tailf:cli-compact-syntax;
      leaf forwarding-address {
        tailf:info
          "Local RIB used to validate external/NSSA forwarding addresses";
        type empty;
      }
      leaf inter-area-summary {
        tailf:info
          "Local RIB used as criteria for inter-area summaries";
        type empty;
      }
      leaf nssa-translation {
        tailf:info
          "Local RIB used as criteria for NSSA translation";
        type empty;
      }
    }
    container max-metric {
      tailf:info
        "Set maximum metric";
      container router-lsa {
        tailf:info
          "Maximum metric in self-originated router-LSAs";
        tailf:cli-compact-syntax;
        presence "true";
        leaf include-stub {
          tailf:info
            "Set maximum metric for stub links in router-LSAs";
          type empty;
        }
        leaf summary-lsa {
          tailf:info
            "Override summary-lsa metric with max-metric value";
          type empty;
        }
        leaf summary-lsa-max-metric-value {
          when "../summary-lsa" {
            tailf:xpath-root 3;
            tailf:dependency "../summary-lsa";
          }
          tailf:cli-drop-node-name;
          type uint32 {
            tailf:info
              "<1-16777215>;;Overriding metric in summary-LSAs (default 16711680)";
            range "1..16777215";
          }
        }
        leaf external-lsa {
          tailf:info
            "Override external-lsa metric with max-metric value";
          type empty;
        }
        leaf external-lsa-max-metric-value {
          when "../external-lsa" {
            tailf:xpath-root 3;
            tailf:dependency "../external-lsa";
          }
          tailf:cli-drop-node-name;
          type uint32 {
            tailf:info
              "<1-16777215>;;Overriding metric in external-LSAs (default 16711680)";
            range "1..16777215";
          }
        }
        container on-startup {
          tailf:info
            "Set maximum metric temporarily after reboot";
          tailf:cli-flatten-container;
          tailf:cli-compact-syntax;
          choice time-wait-for-bgp-choice {
            leaf seconds {
              tailf:cli-drop-node-name;
              type uint32 {
                tailf:info
                  "<5-86400>;;Time, in seconds, router-LSAs are originated with max-metric";
                range "5..86400";
              }
            }
            leaf wait-for-bgp {
              tailf:info
                "Let BGP decide when to originate router-LSA with normal metric";
              type empty;
            }
          }
        }
      }
    }
    container mpls {
      tailf:info
        "Configure MPLS routing protocol parameters";
      container ldp {
        tailf:info
          "routing protocol commands for MPLS LDP";
        container autoconfig {
          tailf:info
            "Configure LDP automatic configuration";
          presence "Configure LDP automatic configuration";
          leaf area {
            tailf:info
              "Configure an OSPF area to run MPLS LDP";
            type ospf-area-type;
          }
        }
        container sync {
          tailf:info
            "Configure LDP-IGP Synchronization";
          presence "Configure LDP-IGP Synchronization";
        }
      }
      container traffic-eng {
        tailf:info
          "routing protocol commands for MPLS Traffic Engineering";
        container router-id {
          tailf:info
            "Traffic Engineering stable IP address for system";
          uses ncs_rpc_notif_interface-name-grouping;
        }
        leaf area {
          tailf:info
            "configure an ospf area to run MPLS Traffic Engineering";
          tailf:cli-full-command;
          type ospf-area-type;
        }
        leaf multicast-intact {
          tailf:info
            "MPLS TE and PIM interaction";
          tailf:cli-full-command;
          type empty;
        }
        container interface {
          tailf:info
            "MPLS TE interface configuration for this OSPF process";
          tailf:cli-compact-syntax;
          tailf:cli-sequence-commands {
            tailf:cli-reset-siblings;
          }
          container name {
            tailf:cli-drop-node-name;
            tailf:cli-flatten-container;
            tailf:cli-compact-syntax;
            uses ncs_rpc_notif_interface-name-grouping;
          }
          leaf area {
            tailf:info
              "advertise MPLS TE information for this interface into area";
            type uint32 {
              tailf:info
                "<0-0>;;OSPF area ID as a decimal value";
            }
          }
        }
        list mesh-group {
          tailf:info
            "Traffic Engineering Mesh-Group advertisement";
          tailf:cli-suppress-mode;
          tailf:cli-delete-when-empty;
          tailf:cli-compact-syntax;
          tailf:cli-sequence-commands {
            tailf:cli-reset-siblings;
          }
          key "id area";
          leaf id {
            type uint32 {
              tailf:info
                "<0-4294967295>;;Mesh Group Id";
            }
          }
          leaf area {
            tailf:cli-expose-key-name;
            tailf:info
              "configure flooding scope as area";
            type ospf-area-type;
          }
          leaf interface {
            tailf:cli-drop-node-name;
            tailf:cli-prefix-key {
              tailf:cli-before-key 2;
            }
            type string {
              tailf:info
                "WORD;;Interface Name";
            }
          }
        }
      }
    }
    list neighbor {
      tailf:info
        "Specify a neighbor router";
      tailf:cli-suppress-mode;
      tailf:cli-delete-when-empty;
      key "ip";
      leaf ip {
        type inet:ipv4-address {
          tailf:info
            "A.B.C.D;;Neighbor address";
        }
      }
      container cost-database-filter-container {
        tailf:cli-drop-node-name;
        tailf:cli-compact-syntax;
        leaf cost {
          tailf:info
            "OSPF cost for point-to-multipoint neighbor";
          type uint32 {
            tailf:info
              "<1-65535>;;metric";
            range "1..65535";
          }
        }
        container database-filter {
          tailf:info
            "Filter OSPF LSA during synchronization and flooding for point-to-multipoint neighbor";
          tailf:cli-flatten-container;
          tailf:cli-compact-syntax;
          container all {
            tailf:info
              "Filter all LSA";
            tailf:cli-flatten-container;
            tailf:cli-compact-syntax;
            leaf out {
              tailf:info
                "Outgoing LSA";
              type empty;
            }
          }
        }
      }
      container poll-interval-priority-container {
        tailf:cli-drop-node-name;
        tailf:cli-compact-syntax;
        leaf poll-interval {
          tailf:info
            "OSPF dead-router polling interval";
          type uint32 {
            tailf:info
              "<0-65535>;;Seconds";
            range "0..65535";
          }
        }
        leaf priority {
          tailf:info
            "OSPF priority of non-broadcast neighbor";
          type uint32 {
            tailf:info
              "<0-255>;;Priority";
            range "0..255";
          }
        }
      }
    }
    list network {
      tailf:info
        "Enable routing on an IP network";
      tailf:cli-suppress-mode;
      tailf:cli-delete-when-empty;
      tailf:cli-incomplete-command;
      key "ip mask";
      leaf ip {
        type inet:ipv4-address {
          tailf:info
            "A.B.C.D;;Network number";
        }
      }
      leaf mask {
        type inet:ipv4-address {
          tailf:info
            "A.B.C.D;;OSPF wild card bits";
        }
      }
      leaf area {
        tailf:info
          "Set the OSPF area ID";
        type ospf-area-type;
      }
    }
    container nsf {
      tailf:info
        "Non-stop forwarding";
      presence "true";
      container cisco {
        tailf:info
          "Cisco Non-stop forwarding";
        tailf:cli-delete-when-empty;
        presence "true";
        container helper {
          tailf:info
            "helper support";
          presence "true";
          leaf disable {
            tailf:info
              "disable helper support";
            tailf:cli-reset-container;
            type empty;
          }
        }
      }
      container ietf {
        tailf:info
          "IETF graceful restart";
        container helper {
          tailf:info
            "helper support";
          presence "helper support";
          leaf disable {
            tailf:info
              "disable helper support";
            tailf:cli-reset-container;
            tailf:cli-delete-container-on-delete;
            type empty;
          }
          leaf strict-lsa-checking {
            tailf:info
              "enable helper strict LSA checking";
            type empty;
          }
        }
      }
    }
    container prefix-priority {
      tailf:info
        "OSPF prefix priority";
      container high {
        tailf:info
          "High prefix priority";
        leaf route-map {
          tailf:info
            "Prefix priority selection by route-map";
          type string {
            tailf:info
              "WORD;;Route map name";
          }
        }
      }
    }
    leaf prefix-suppression {
      tailf:info
        "OSPF prefix suppression";
      tailf:cli-full-command;
      type empty;
    }
    container process-min-time {
      tailf:info
        "Percentage of quantum to be used before releasing CPU";
      leaf percent {
        tailf:info
          "percent";
        type uint32 {
          range "1..100";
          tailf:info
            "<1-100>;;Minimum CPU quantum";
        }
      }
    }
    container traffic-share {
      tailf:info
        "How to compute traffic share over alternate paths";
      container min {
        tailf:info
          "All traffic shared among min metric paths";
        leaf across-interfaces {
          tailf:info
            "Use different interfaces for equal-cost paths";
          type empty;
        }
      }
    }
    leaf shutdown {
      tailf:info
        "Shutdown the OSPF protocol under the current instance";
      tailf:cli-boolean-no;
      type boolean;
    }
    list summary-address {
      tailf:info
        "Configure IP address summaries";
      tailf:cli-suppress-mode;
      tailf:cli-delete-when-empty;
      key "ip wildcard";
      leaf ip {
        type inet:ipv4-address {
          tailf:info
            "A.B.C.D;;IP summary address";
        }
      }
      leaf wildcard {
        type inet:ipv4-address {
          tailf:info
            "A.B.C.D;;Summary mask";
        }
      }
      choice tag-no-advertise-choice {
        leaf tag {
          tailf:info
            "Set tag";
          tailf:cli-full-command;
          type uint32 {
            range "0..4294967295";
            tailf:info
              "<0-4294967295>;;32-bit tag value";
          }
        }
        leaf not-advertise {
          tailf:info
            "Do not advertise when translating OSPF type-7 LSA";
          type empty;
          tailf:cli-full-command;
        }
      }
    }
    container discard-route {
      tailf:info
        "Enable or disable discard-route installation";
      tailf:cli-compact-syntax;
      presence "true";
      leaf external {
        tailf:info
          "Discard route for redistributed summarised routes";
        type uint32 {
          tailf:info
            "<1-255>;;Administrative distance for redistributed summarised routes";
          range "1..255";
        }
      }
      leaf internal {
        tailf:info
          "Discard route for summarised internal routes";
        type uint32 {
          tailf:info
            "<1-255>;;Administrative distance for summarised internal routes";
          range "1..255";
        }
      }
    }
    container fast-reroute {
      tailf:info
        "Configure Fast-Reroute";
      leaf keep-all-paths {
        tailf:info
          "Keep LFA FRR audit trail";
        tailf:cli-full-command;
        type empty;
      }
      container per-prefix {
        tailf:info
          "Per-prefix LFA FRR parameters";
        container enable {
          tailf:info
            "Enable LFA Fast Reroute";
          list area {
            tailf:info
              "Area to enable LFA FRR in";
            tailf:cli-suppress-mode;
            tailf:cli-delete-when-empty;
            tailf:cli-compact-syntax;
            tailf:cli-sequence-commands {
              tailf:cli-reset-siblings;
            }
            key "area";
            leaf area {
              type ospf-area-type;
            }
            leaf prefix-priority {
              tailf:info
                "Priority of prefixes to be protected";
              type enumeration {
                enum "high" {
                  tailf:info
                    "High priority prefixes";
                }
                enum "low" {
                  tailf:info
                    "Low priority prefixes";
                }
              }
            }
          }
          leaf prefix-priority {
            tailf:info
              "Priority of prefixes to be protected";
            type enumeration {
              enum "high" {
                tailf:info
                  "High priority prefixes";
              }
              enum "low" {
                tailf:info
                  "Low priority prefixes";
              }
            }
          }
        }
        container remote-lfa {
          tailf:info
            "Remote LFA FastReroute parameters";
          leaf area {
            tailf:info
              "Area for remote LFA command";
            tailf:cli-full-command;
            type ospf-area-type;
          }
          leaf maximum-cost {
            tailf:info
              "Maximum distance to tunnel endpoint";
            tailf:cli-full-command;
            type uint32 {
              tailf:info
                "<1-16777214>;;Value of the maximum distance to tunnel endpoint";
            }
          }
          leaf tunnel {
            tailf:info
              "Remote LFA tunnel type";
            tailf:cli-full-command;
            type enumeration {
              enum "mpls-ldp" {
                tailf:info
                  "Enable remote LFA tunneling via MPLS";
              }
            }
          }
        }
      }
    }
  }

  grouping ncs_rpc_notif_router-ospfv3-grouping {
    list summary-prefix {
      tailf:info
        "Configure IP summary prefix";
      tailf:cli-suppress-mode;
      tailf:cli-delete-when-empty;
      tailf:cli-compact-syntax;
      key "prefix";
      leaf prefix {
        type union {
          type ios:ipv4-prefix;
          type ios:ipv6-prefix;
        }
      }
    }
  }

  grouping ncs_rpc_notif_ospf-redistribute-match-grouping {
    leaf metric {
      tailf:info
        "Metric for redistributed routes";
      type uint32 {
        tailf:info
          "<0-16777214>;;OSPF default metric";
      }
    }
    leaf subnets {
      tailf:info
        "Consider subnets for redistribution into OSPF";
      type empty;
    }
    leaf route-map {
      tailf:info
        "Route map reference";
      type string {
        tailf:info
          "WORD;;Pointer to route-map entries";
      }
    }
    leaf tag {
      tailf:info
        "Set tag for routes redistributed into OSPF";
      type uint32 {
        tailf:info
          "<0-4294967295>;;32-bit tag value";
        range "0..4294967295";
      }
    }
  }

  grouping ncs_rpc_notif_router-isis-level-grouping {
    leaf level {
      tailf:cli-drop-node-name;
      type enumeration {
        enum "level-1" {
          tailf:info
            "IS-IS level-1 routes only";
        }
        enum "level-1-2" {
          tailf:info
            "IS-IS level-1 and level-2 routes";
        }
        enum "level-2" {
          tailf:info
            "IS-IS level-2 routes only";
        }
      }
    }
  }

  grouping ncs_rpc_notif_router-ospf-route-map-grouping {
    leaf route-map {
      tailf:info
        "Route map reference";
      tailf:cli-no-name-on-delete;
      tailf:cli-no-value-on-delete;
      type string {
        tailf:info
          "WORD;;Pointer to route-map entries";
      }
    }
  }

  grouping ncs_rpc_notif_router-ospf-redistribute-grouping {
    leaf metric {
      tailf:info
        "Metric for redistributed routes";
      tailf:cli-no-name-on-delete;
      tailf:cli-no-value-on-delete;
      type uint32 {
        tailf:info
          "<0-16777214>;;OSPF default metric";
      }
    }
    leaf metric-type {
      tailf:info
        "OSPF/IS-IS exterior metric type for redistributed routes";
      tailf:cli-no-name-on-delete;
      tailf:cli-no-value-on-delete;
      type enumeration {
        enum "1" {
          tailf:info
            "Set OSPF External Type 1 metrics";
        }
        enum "2" {
          tailf:info
            "Set OSPF External Type 2 metrics";
        }
      }
      default "2";
    }
    leaf subnets {
      tailf:info
        "Consider subnets for redistribution into OSPF";
      tailf:cli-no-name-on-delete;
      tailf:cli-no-value-on-delete;
      type empty;
    }
    leaf nssa-only {
      tailf:info
        "Limit redistributed routes to NSSA areas";
      tailf:cli-no-name-on-delete;
      tailf:cli-no-value-on-delete;
      type empty;
    }
    leaf tag {
      tailf:info
        "Set tag for routes redistributed into OSPF";
      tailf:cli-no-name-on-delete;
      tailf:cli-no-value-on-delete;
      type uint32 {
        tailf:info
          "<0-4294967295>;;32-bit tag value";
      }
    }
  }

  grouping ncs_rpc_notif_router-rip-af-grouping {
    leaf auto-summary {
      tailf:info
        "Enable automatic network number summarization";
      tailf:cli-boolean-no;
      tailf:cli-full-command;
      type boolean;
      default "true";
    }
    leaf maximum-paths {
      tailf:info
        "Forward packets over multiple paths";
      tailf:cli-full-command;
      type uint8 {
        tailf:info
          "1-32;;Number of paths";
        range "1..32";
      }
    }
    list neighbor {
      tailf:info
        "Specify a neighbor router";
      tailf:cli-suppress-mode;
      tailf:cli-delete-when-empty;
      key "ip";
      leaf ip {
        type inet:ipv4-address {
          tailf:info
            "A.B.C.D;;Neighbor address";
        }
      }
    }
    list network {
      tailf:info
        "Enable routing on an IP network";
      tailf:cli-suppress-mode;
      tailf:cli-delete-when-empty;
      key "ip";
      leaf ip {
        type inet:ipv4-address {
          tailf:info
            "A.B.C.D;;Network number";
        }
      }
    }
    leaf validate-update-source {
      tailf:info
        "Perform sanity checks against source address of routing updates";
      tailf:cli-boolean-no;
      tailf:cli-full-command;
      type boolean;
      default "true";
    }
    container default-information {
      tailf:info
        "Control distribution of default information";
      container originate {
        tailf:info
          "Distribute a default route";
        presence "true";
        leaf route-map {
          tailf:info
            "Route-map reference";
          type string {
            tailf:info
              "WORD;;Route map name";
          }
        }
      }
    }
    leaf default-metric {
      tailf:info
        "Set metric of redistributed routes";
      tailf:cli-full-command;
      type uint32 {
        tailf:info
          "<1-4294967295>;;Default metric";
        range "1..4294967295";
      }
    }
    container distance {
      tailf:info
        "Define an administrative distance";
      tailf:cli-compact-syntax;
      leaf distance-leaf {
        tailf:cli-drop-node-name;
        tailf:cli-full-command;
        type uint8 {
          tailf:info
            "1-255;;Administrative distance";
          range "1..255";
        }
      }
      list distance-list {
        tailf:cli-drop-node-name;
        tailf:cli-suppress-mode;
        tailf:cli-delete-when-empty;
        tailf:cli-compact-syntax;
        tailf:cli-sequence-commands {
          tailf:cli-reset-siblings;
        }
        key "ip mask";
        leaf number {
          tailf:cli-prefix-key;
          tailf:cli-drop-node-name;
          type uint8 {
            tailf:info
              "1-255;;Administrative distance";
            range "1..255";
          }
        }
        leaf ip {
          type inet:ipv4-address {
            tailf:info
              "A.B.C.D;;IP source address";
          }
        }
        leaf mask {
          type inet:ipv4-address {
            tailf:info
              "A.B.C.D;;Wildcard bits";
          }
        }
        leaf access-list {
          tailf:cli-drop-node-name;
          type std-ip-acl-type;
        }
      }
    }
    uses ncs_rpc_notif_router-distribute-list-grouping;
    uses ncs_rpc_notif_router-offset-list-grouping;
    container redistribute {
      tailf:info
        "Redistribute information from another routing protocol";
      container connected {
        tailf:info
          "Connected";
        tailf:cli-compact-syntax;
        presence "true";
        uses ncs_rpc_notif_router-rip-redistribute-grouping;
      }
      container bgp {
        tailf:info
          "Border Gateway Protocol (BGP)";
        tailf:cli-compact-syntax;
        leaf as-no {
          tailf:cli-drop-node-name;
          type bgp-as-no-type;
        }
        uses ncs_rpc_notif_router-rip-redistribute-grouping;
      }
      list eigrp {
        tailf:info
          "Enhanced Interior Gateway Routing Protocol (EIGRP)";
        tailf:cli-suppress-mode;
        tailf:cli-delete-when-empty;
        tailf:cli-compact-syntax;
        key "as-no";
        leaf as-no {
          type eigrp-as-no-type;
        }
        uses ncs_rpc_notif_router-rip-redistribute-grouping;
      }
      container isis {
        tailf:info
          "ISO IS-IS";
        tailf:cli-compact-syntax;
        tailf:cli-delete-when-empty;
        presence "true";
        list isis-list {
          tailf:cli-drop-node-name;
          tailf:cli-suppress-mode;
          tailf:cli-delete-when-empty;
          tailf:cli-compact-syntax;
          key "name";
          leaf name {
            tailf:cli-disallow-value "level-1|level-2|level-1-2|metric|route-map";
            type string {
              tailf:info
                "WORD;;ISO routing area tag";
            }
          }
          leaf level {
            tailf:cli-drop-node-name;
            type isis-level-type;
          }
          uses ncs_rpc_notif_router-rip-redistribute-grouping;
        }
        leaf level {
          tailf:cli-drop-node-name;
          type isis-level-type;
        }
        uses ncs_rpc_notif_router-rip-redistribute-grouping;
      }
      container iso-igrp {
        tailf:info
          "IGRP for OSI networks";
        presence "true";
        list iso-igrp-list {
          tailf:info
            "Border Gateway Protocol (BGP)";
          tailf:cli-suppress-mode;
          tailf:cli-delete-when-empty;
          tailf:cli-drop-node-name;
          key "name";
          leaf name {
            tailf:cli-disallow-value "metric|route-map";
            type string {
              tailf:info
                "WORD;;ISO routing area tag";
            }
          }
          uses ncs_rpc_notif_router-rip-redistribute-grouping;
        }
        uses ncs_rpc_notif_router-rip-redistribute-grouping;
      }
      container mobile {
        tailf:info
          "Mobile routes";
        tailf:cli-compact-syntax;
        presence "Mobile routes";
        uses ncs_rpc_notif_router-rip-redistribute-grouping;
      }
      container odr {
        tailf:info
          "On Demand stub Routes";
        tailf:cli-compact-syntax;
        presence "On Demand stub Routes";
        uses ncs_rpc_notif_router-rip-redistribute-grouping;
      }
      list ospf {
        tailf:info
          "Open Shortest Path First (OSPF)";
        tailf:cli-suppress-mode;
        tailf:cli-delete-when-empty;
        tailf:cli-compact-syntax;
        key "id";
        leaf id {
          tailf:cli-suppress-range;
          type uint16 {
            tailf:info
              "<1-65535>;;Process ID";
            range "1..65535";
          }
        }
        uses ncs_rpc_notif_router-rip-redistribute-grouping;
        uses ncs_rpc_notif_redistribute-ospf-match-grouping;
      }
      container static {
        tailf:info
          "Static routes";
        tailf:cli-compact-syntax;
        tailf:cli-delete-when-empty;
        presence "Static routes";
        uses ncs_rpc_notif_router-rip-redistribute-grouping;
      }
      container rip {
        tailf:info
          "Routing Information Protocol (RIP)";
        tailf:cli-compact-syntax;
        presence "true";
        uses ncs_rpc_notif_router-rip-redistribute-grouping;
      }
    }
    container timers {
      tailf:info
        "Adjust routing timers";
      tailf:cli-incomplete-no;
      tailf:cli-compact-syntax;
      container basic {
        tailf:info
          "Basic routing protocol update timers";
        tailf:cli-compact-syntax;
        tailf:cli-sequence-commands;
        tailf:cli-full-no;
        leaf updates {
          tailf:cli-drop-node-name;
          tailf:cli-incomplete-command;
          tailf:cli-no-value-on-delete;
          type uint32 {
            tailf:info
              "1-4294967295;;Interval between updates for RIP";
            range "1..4294967295";
          }
        }
        leaf invalid {
          tailf:cli-drop-node-name;
          tailf:cli-incomplete-command;
          tailf:cli-no-value-on-delete;
          type uint32 {
            tailf:info
              "1-4294967295;;Invalid";
            range "1..4294967295";
          }
        }
        leaf holddown {
          tailf:cli-drop-node-name;
          tailf:cli-incomplete-command;
          tailf:cli-no-value-on-delete;
          type uint32 {
            tailf:info
              "1-4294967295;;Holddown";
            range "1..4294967295";
          }
        }
        leaf flush {
          tailf:cli-drop-node-name;
          tailf:cli-incomplete-command;
          tailf:cli-no-value-on-delete;
          type uint32 {
            tailf:info
              "1-4294967295;;Flush";
            range "1..4294967295";
          }
        }
        leaf sleep {
          tailf:cli-drop-node-name;
          tailf:cli-no-value-on-delete;
          type uint32 {
            tailf:info
              "1-4294967295;;Sleep time, in milliseconds";
            range "1..4294967295";
          }
        }
      }
    }
    leaf version {
      tailf:info
        "Set routing protocol version";
      type uint8 {
        tailf:info
          "1-2;;rip version 1 or 2";
        range "1..2";
      }
    }
    container traffic-share {
      tailf:info
        "How to compute traffic share over alternate paths";
      container min {
        tailf:info
          "All traffic shared among min metric paths";
        leaf across-interfaces {
          tailf:info
            "Use different interfaces for equal-cost paths";
          type empty;
        }
      }
    }
  }

  grouping ncs_rpc_notif_router-rip-grouping {
    uses ncs_rpc_notif_router-rip-af-grouping;
    uses ncs_rpc_notif_passive-interface-grouping;
    leaf output-delay {
      tailf:info
        "Interpacket delay for RIP updates";
      tailf:cli-full-command;
      type uint8 {
        tailf:info
          "8-50;;Delay in milliseconds";
        range "8..50";
      }
    }
    leaf input-queue {
      tailf:info
        "Specify input queue depth";
      tailf:cli-full-command;
      type uint16 {
        tailf:info
          "0-1024;;queue depth";
        range "0..1024";
      }
    }
    leaf flash-update-threshold {
      tailf:info
        "Specify flash update threshold in second";
      tailf:cli-full-command;
      type uint8 {
        tailf:info
          "<0-30>;;threshold in seconds";
        range "0..30";
      }
    }
  }

  grouping ncs_rpc_notif_router-rip-redistribute-grouping {
    leaf metric {
      tailf:info
        "Metric for redistributed routes";
      type union {
        type uint8 {
          tailf:info
            "<0-16>;;Default metric";
          range "0..16";
        }
        type enumeration {
          enum "transparent" {
            tailf:info
              "Transparently redistribute metric";
          }
        }
      }
    }
    leaf route-map {
      tailf:info
        "Route map reference";
      type string {
        tailf:info
          "WORD;;Pointer to route-map entries";
      }
    }
  }

  grouping ncs_rpc_notif_router-eigrp-redistribute-grouping {
    container metric {
      tailf:info
        "Metric for redistributed routes";
      tailf:cli-break-sequence-commands;
      tailf:cli-flatten-container;
      tailf:cli-compact-syntax;
      tailf:cli-sequence-commands {
        tailf:cli-reset-siblings;
      }
      leaf bandwidth-metric {
        tailf:cli-drop-node-name;
        tailf:cli-incomplete-command;
        type uint32 {
          tailf:info
            "<1-4294967295>;;Bandwidth metric in Kbits per second";
        }
      }
      leaf delay-metric {
        tailf:cli-drop-node-name;
        tailf:cli-incomplete-command;
        type uint32 {
          tailf:info
            "<0-4294967295>;;EIGRP delay metric, in 10 microsecond units";
        }
      }
      leaf reliability-metric {
        tailf:cli-drop-node-name;
        tailf:cli-incomplete-command;
        type uint8 {
          tailf:info
            "<0-255>;;EIGRP reliability metric where 255 is 100% reliable";
        }
      }
      leaf effective-bandwidth-metric {
        tailf:cli-drop-node-name;
        tailf:cli-incomplete-command;
        type uint8 {
          tailf:info
            "<1-255>;;EIGRP Effective bandwidth metric (Loading) where 255 is 100% loaded";
          range "1..255";
        }
      }
      leaf mtu-bytes {
        tailf:cli-drop-node-name;
        type uint16 {
          tailf:info
            "<1-65535>;;EIGRP MTU of the path";
          range "1..65535";
        }
      }
    }
    leaf route-map {
      tailf:info
        "Route map reference";
      type string {
        tailf:info
          "WORD;;Pointer to route-map entries";
      }
    }
  }

  grouping ncs_rpc_notif_router-eigrp-grouping {
    container metric {
      tailf:info
        "Modify metrics and parameters for advertisement";
      leaf maximum-hops {
        tailf:info
          "Advertise greater than <hops> as unreachable";
        type uint8 {
          tailf:info
            "<1-255>;;Hop count";
          range "1..255";
        }
      }
      container weights {
        tailf:info
          "Modify metric coefficients";
        tailf:cli-compact-syntax;
        tailf:cli-sequence-commands {
          tailf:cli-reset-siblings;
        }
        leaf tos {
          tailf:cli-drop-node-name;
          tailf:cli-incomplete-command;
          type uint8 {
            tailf:info
              "<0-8>;;Type (Only TOS 0 supported)";
            range "0..8";
          }
        }
        leaf k1 {
          tailf:cli-drop-node-name;
          tailf:cli-incomplete-command;
          type uint8 {
            tailf:info
              "<0-255>;;K1";
          }
        }
        leaf k2 {
          tailf:cli-drop-node-name;
          tailf:cli-incomplete-command;
          type uint8 {
            tailf:info
              "<0-255>;;K2";
          }
        }
        leaf k3 {
          tailf:cli-drop-node-name;
          tailf:cli-incomplete-command;
          type uint8 {
            tailf:info
              "<0-255>;;K3";
          }
        }
        leaf k4 {
          tailf:cli-drop-node-name;
          tailf:cli-incomplete-command;
          type uint8 {
            tailf:info
              "<0-255>;;K4";
          }
        }
        leaf k5 {
          tailf:cli-drop-node-name;
          type uint8 {
            tailf:info
              "<0-255>;;K5";
          }
        }
      }
    }
    container network-ip {
      tailf:cli-drop-node-name;
      list network {
        tailf:info
          "Enable routing on an IP network";
        tailf:cli-suppress-mode;
        tailf:cli-delete-when-empty;
        key "ip";
        leaf ip {
          type inet:ipv4-address {
            tailf:info
              "A.B.C.D;;Network number";
          }
        }
      }
    }
    list network {
      tailf:info
        "Enable routing on an IP network";
      tailf:cli-suppress-mode;
      tailf:cli-delete-when-empty;
      key "ip mask";
      leaf ip {
        type inet:ipv4-address {
          tailf:info
            "A.B.C.D;;Network number";
        }
      }
      leaf mask {
        type inet:ipv4-address {
          tailf:info
            "A.B.C.D;;EIGRP wild card bits";
        }
      }
    }
    container neighbor {
      tailf:info
        "Specify a neighbor router";
      list neighbor-list {
        tailf:cli-drop-node-name;
        tailf:cli-suppress-mode;
        tailf:cli-delete-when-empty;
        key "address interface";
        leaf address {
          type inet:ipv4-address {
            tailf:info
              "A.B.C.D;;Neighbor address";
          }
        }
        leaf interface {
          tailf:cli-diff-dependency "/ios:interface" {
            tailf:xpath-root 3;
          }
          type string {
            tailf:info
              "WORD;;Interface name";
          }
        }
      }
    }
    container eigrp {
      tailf:info
        "EIGRP specific commands";
      leaf router-id {
        tailf:info
          "router id for this EIGRP process";
        type inet:ipv4-address {
          tailf:info
            "A.B.C.D;;EIGRP Router-ID in IP address format";
        }
      }
      container stub {
        tailf:info
          "Set address-family in stubbed mode";
        tailf:cli-compact-syntax;
        tailf:cli-reset-container;
        leaf connected {
          tailf:info
            "Do advertise connected routes";
          type empty;
        }
        leaf static {
          tailf:info
            "Do advertise static routes";
          type empty;
        }
        leaf summary {
          tailf:info
            "Do advertise summary routes";
          type empty;
        }
        leaf redistributed {
          tailf:info
            "Do advertise redistributed routes";
          type empty;
        }
      }
      leaf stub-site {
        tailf:info
          "Set address-family in stub-site mode";
        tailf:cli-full-command;
        type string {
          tailf:info
            "ASN:nn or 4BASN:nn Stub-Site ID in aa:nn format";
          pattern '[0-9]+:[0-9]+';
        }
      }
    }
  }

  grouping ncs_rpc_notif_router-eigrp-base-grouping {
    uses ncs_rpc_notif_router-distribute-list-grouping;
    container default-metric {
      tailf:info
        "Set metric of redistributed routes";
      tailf:cli-compact-syntax;
      tailf:cli-sequence-commands;
      leaf bandwidth {
        tailf:cli-drop-node-name;
        tailf:cli-incomplete-command;
        type uint32 {
          tailf:info
            "<1-4294967295>;;Bandwidth in Kbits per second";
          range "1..4294967295";
        }
      }
      leaf delay {
        tailf:cli-drop-node-name;
        tailf:cli-incomplete-command;
        type uint32 {
          tailf:info
            "<0-4294967295>;;delay metric in 10 microsecond units";
          range "0..4294967295";
        }
      }
      leaf reliability {
        tailf:cli-drop-node-name;
        tailf:cli-incomplete-command;
        type uint8 {
          tailf:info
            "<0-255>;;Reliability metric where 255 is 100% reliable";
          range "0..255";
        }
      }
      leaf loading {
        tailf:cli-drop-node-name;
        tailf:cli-incomplete-command;
        type uint8 {
          tailf:info
            "<1-255>;;Effective bandwidth metric (Loading) where 255 is 100% loaded";
          range "1..255";
        }
      }
      leaf mtu {
        tailf:cli-drop-node-name;
        type uint16 {
          tailf:info
            "<1-65535>;;Maximum Transmission Unit metric of the path";
          range "1..65535";
        }
      }
    }
    list summary-metric {
      tailf:info
        "Specify summary to apply metric/filtering";
      tailf:cli-suppress-mode;
      tailf:cli-delete-when-empty;
      tailf:cli-compact-syntax;
      tailf:cli-sequence-commands {
        tailf:cli-reset-siblings;
      }
      key "prefix";
      leaf prefix {
        type ios:ipv4-prefix {
          tailf:info
            "A.B.C.D/nn;;Summary <network>/<length>, e.g., 192.168.0.0/16";
        }
      }
      leaf bandwidth {
        tailf:cli-optional-in-sequence;
        tailf:cli-drop-node-name;
        tailf:cli-incomplete-command;
        type uint32 {
          tailf:info
            "<1-4294967295>;;Bandwidth metric in Kbits per second";
        }
      }
      leaf delay {
        when "../bandwidth" {
          tailf:xpath-root 3;
          tailf:dependency "../bandwidth";
        }
        tailf:cli-drop-node-name;
        tailf:cli-incomplete-command;
        type uint32 {
          tailf:info
            "<1-4294967295>;;delay metric in 10 microsecond units";
        }
      }
      leaf reliability {
        when "../delay" {
          tailf:xpath-root 3;
          tailf:dependency "../delay";
        }
        tailf:cli-drop-node-name;
        tailf:cli-incomplete-command;
        type uint8 {
          tailf:info
            "<0-255>;;reliability metric where 255 is 100% reliable";
        }
      }
      leaf load {
        when "../reliability" {
          tailf:xpath-root 3;
          tailf:dependency "../reliability";
        }
        tailf:cli-drop-node-name;
        tailf:cli-incomplete-command;
        type uint8 {
          tailf:info
            "<0-255>;;Effective bandwidth metric (Loading) where 255 is 100% loaded";
        }
      }
      leaf mtu {
        when "../load" {
          tailf:xpath-root 3;
          tailf:dependency "../load";
        }
        tailf:cli-drop-node-name;
        type uint16 {
          tailf:info
            "<1-65535>;;MTU of the path";
          range "1..65535";
        }
      }
      leaf distance {
        tailf:info
          "Set administrative distance for summary route";
        type uint8 {
          tailf:info
            "<1-255>;;Administrative distance";
          range "1..255";
        }
      }
    }
    uses ncs_rpc_notif_router-offset-list-grouping;
    container redistribute {
      tailf:info
        "Redistribute IPv4 routes from another routing protocol";
      container connected {
        tailf:info
          "Connected";
        tailf:cli-compact-syntax;
        tailf:cli-delete-when-empty;
        presence "true";
        uses ncs_rpc_notif_router-eigrp-redistribute-grouping;
      }
      container bgp {
        tailf:info
          "Border Gateway Protocol (BGP)";
        tailf:cli-compact-syntax;
        tailf:cli-sequence-commands {
          tailf:cli-reset-all-siblings;
        }
        leaf as-no {
          tailf:cli-drop-node-name;
          type bgp-as-no-type;
        }
        uses ncs_rpc_notif_router-eigrp-redistribute-grouping;
      }
      list eigrp {
        tailf:info
          "Enhanced Interior Gateway Routing Protocol (EIGRP)";
        tailf:cli-suppress-mode;
        tailf:cli-delete-when-empty;
        tailf:cli-compact-syntax;
        key "as-no";
        leaf as-no {
          type eigrp-as-no-type;
        }
        uses ncs_rpc_notif_router-eigrp-redistribute-grouping;
      }
      container isis {
        tailf:info
          "ISO IS-IS";
        tailf:cli-compact-syntax;
        presence "true";
        list isis-list {
          tailf:cli-drop-node-name;
          tailf:cli-suppress-mode;
          tailf:cli-delete-when-empty;
          tailf:cli-compact-syntax;
          key "name";
          leaf name {
            tailf:cli-disallow-value "level-1|level-2|level-1-2|metric|route-map";
            type string {
              tailf:info
                "WORD;;ISO routing area tag";
            }
          }
          leaf level {
            tailf:cli-drop-node-name;
            type isis-level-type;
          }
          uses ncs_rpc_notif_router-eigrp-redistribute-grouping;
        }
        leaf level {
          tailf:cli-drop-node-name;
          type isis-level-type;
        }
        uses ncs_rpc_notif_router-eigrp-redistribute-grouping;
      }
      container iso-igrp {
        tailf:info
          "IGRP for OSI networks";
        presence "true";
        list iso-igrp-list {
          tailf:info
            "Border Gateway Protocol (BGP)";
          tailf:cli-suppress-mode;
          tailf:cli-delete-when-empty;
          tailf:cli-drop-node-name;
          key "name";
          leaf name {
            tailf:cli-disallow-value "metric|route-map";
            type string {
              tailf:info
                "WORD;;ISO routing area tag";
            }
          }
          uses ncs_rpc_notif_router-eigrp-redistribute-grouping;
        }
        uses ncs_rpc_notif_router-eigrp-redistribute-grouping;
      }
      container mobile {
        tailf:info
          "Mobile routes";
        tailf:cli-compact-syntax;
        presence "true";
        uses ncs_rpc_notif_router-eigrp-redistribute-grouping;
      }
      container odr {
        tailf:info
          "On Demand stub Routes";
        tailf:cli-compact-syntax;
        presence "true";
        uses ncs_rpc_notif_router-eigrp-redistribute-grouping;
      }
      list ospf {
        tailf:info
          "Open Shortest Path First (OSPF)";
        tailf:cli-suppress-mode;
        tailf:cli-delete-when-empty;
        tailf:cli-compact-syntax;
        key "id";
        leaf id {
          tailf:cli-suppress-range;
          type uint16 {
            tailf:info
              "<1-65535>;;Process ID";
            range "1..65535";
          }
        }
        uses ncs_rpc_notif_redistribute-ospf-match-grouping;
        uses ncs_rpc_notif_router-eigrp-redistribute-grouping;
      }
      container static {
        tailf:info
          "Static routes";
        tailf:cli-compact-syntax;
        tailf:cli-delete-when-empty;
        presence "Static routes";
        uses ncs_rpc_notif_router-eigrp-redistribute-grouping;
      }
      container rip {
        tailf:info
          "Routing Information Protocol (RIP)";
        tailf:cli-compact-syntax;
        presence "true";
        uses ncs_rpc_notif_router-eigrp-redistribute-grouping;
      }
    }
    container distance {
      tailf:info
        "Define an administrative distance";
      container eigrp {
        tailf:info
          "Set distance for internal and external routes";
        tailf:cli-compact-syntax;
        tailf:cli-sequence-commands;
        leaf internal-distance {
          tailf:cli-drop-node-name;
          tailf:cli-incomplete-command;
          type uint8 {
            tailf:info
              "<1-255>;;Distance for internal routes";
            range "1..255";
          }
        }
        leaf external-distance {
          tailf:cli-drop-node-name;
          type uint8 {
            tailf:info
              "<1-255>;;Distance for external routes";
            range "1..255";
          }
        }
      }
      list distance-list {
        tailf:cli-drop-node-name;
        tailf:cli-suppress-mode;
        tailf:cli-delete-when-empty;
        tailf:cli-compact-syntax;
        tailf:cli-sequence-commands {
          tailf:cli-reset-siblings;
        }
        key "ip-address wildcard-mask";
        leaf ip-address {
          type inet:ipv4-address {
            tailf:info
              "A.B.C.D;;IP source address";
          }
        }
        leaf wildcard-mask {
          type inet:ipv4-address {
            tailf:info
              "A.B.C.D;;Wildcard bits";
          }
        }
        leaf weight {
          tailf:cli-drop-node-name;
          tailf:cli-prefix-key;
          type uint8 {
            tailf:info
              "<1-255>;;Administrative distance";
            range "1..255";
          }
        }
        leaf access-list {
          tailf:cli-drop-node-name;
          type std-ip-acl-type;
        }
      }
    }
    leaf auto-summary {
      tailf:info
        "Enable automatic network number summarization";
      tailf:cli-full-command;
      type empty;
    }
    uses ncs_rpc_notif_passive-interface-grouping;
  }

  grouping ncs_rpc_notif_router-eigrp-af-virtual-instance-grouping {
    list af-interface {
      tailf:cli-break-sequence-commands;
      tailf:info
        "Enter Address Family interface configuration";
      tailf:cli-mode-name "config-router-af-interface";
      tailf:cli-exit-command "exit-af-interface" {
        tailf:info
          "Exit from Address Family Interface configuration";
      }
      tailf:cli-show-long-obu-diffs;
      ordered-by user;
      key "name";
      leaf name {
        type string {
          tailf:info
            "WORD;;Interface name";
        }
      }
      list summary-address {
        tailf:info
          "Perform address summarization";
        tailf:cli-suppress-mode;
        tailf:cli-delete-when-empty;
        tailf:cli-compact-syntax;
        key "ip mask";
        leaf ip {
          type inet:ipv4-address {
            tailf:info
              "A.B.C.D;;Summary network address";
          }
        }
        leaf mask {
          type inet:ipv4-address {
            tailf:info
              "A.B.C.D;;Summary network mask";
          }
        }
        leaf leak-map {
          tailf:info
            "Allow dynamic prefixes based on the leak-map";
          type string {
            tailf:info
              "WORD;;leak-map name";
          }
        }
      }
      container summary-address-ipv6 {
        tailf:cli-drop-node-name;
        list summary-address {
          tailf:info
            "Perform address summarization";
          tailf:cli-suppress-mode;
          tailf:cli-delete-when-empty;
          tailf:cli-compact-syntax;
          key "ipv6";
          leaf ipv6 {
            type ipv6-prefix {
              tailf:info
                "X:X:X:X::X/<0-128>;;Summary network prefix";
            }
          }
          leaf leak-map {
            tailf:info
              "Allow dynamic prefixes based on the leak-map";
            type string {
              tailf:info
                "WORD;;leak-map name";
            }
          }
        }
      }
      container authentication {
        tailf:info
          "authentication subcommands";
        container mode {
          tailf:info
            "authentication mode";
          leaf md5 {
            tailf:info
              "Keyed message digest";
            type empty;
          }
        }
        leaf key-chain {
          tailf:info
            "key-chain";
          tailf:cli-full-command;
          type string {
            tailf:info
              "WORD;;name of key-chain";
          }
        }
      }
      leaf hello-interval {
        tailf:info
          "Configures hello interval";
        type uint16 {
          tailf:info
            "<1-65535>;;Seconds between hello transmissions";
          range "1..65535";
        }
      }
      leaf hold-time {
        tailf:info
          "Configures hold time";
        type uint16 {
          tailf:info
            "<1-65535>;;Seconds before neighbor is considered down";
          range "1..65535";
        }
      }
      leaf next-hop-self {
        tailf:info
          "Configures EIGRP next-hop-self";
        tailf:cli-boolean-no;
        tailf:cli-full-command;
        type boolean;
        default "true";
      }
      leaf passive-interface {
        tailf:info
          "Suppress address updates on an interface";
        tailf:cli-show-no;
        type empty;
      }
      leaf split-horizon {
        tailf:info
          "Perform split horizon";
        tailf:cli-boolean-no;
        tailf:cli-full-command;
        type boolean;
        default "true";
      }
      container stub-site {
        tailf:info
          "Stub-Site";
        leaf wan-interface {
          tailf:info
            "Wan Interface";
          type empty;
        }
      }
    }
    container topology {
      tailf:info
        "Topology configuration mode";
      container base {
        tailf:info
          "Base Topology";
        tailf:cli-add-mode;
        tailf:cli-mode-name "config-router-af-topology";
        tailf:cli-exit-command "exit-af-topology" {
          tailf:info
            "Exit from Address Family Topology configuration mode";
        }
        presence "true";
        uses ncs_rpc_notif_router-eigrp-base-grouping;
      }
    }
    uses ncs_rpc_notif_router-eigrp-grouping;
  }

  grouping ncs_rpc_notif_narrow-wide-transition-grouping {
    leaf transition {
      tailf:info
        "Accept both styles of TLVs during transition";
      type empty;
    }
    leaf level {
      tailf:cli-drop-node-name;
      tailf:cli-full-command;
      type isis-level-type;
    }
  }

  grouping ncs_rpc_notif_spf-intervals-grouping {
    leaf interval {
      tailf:cli-drop-node-name;
      type uint8 {
        tailf:info
          "<1-120>;;Interval between consecutive SPFs in seconds";
        range "1..120";
      }
    }
    leaf initial-wait {
      tailf:cli-drop-node-name;
      type uint32 {
        tailf:info
          "<1-120000>;;Initial wait before first SPF in milliseconds";
        range "1..120000";
      }
    }
    leaf minimum-wait {
      tailf:cli-drop-node-name;
      type uint32 {
        tailf:info
          "<1-120000>;;Minimum wait between first and second SPF in milliseconds";
        range "1..120000";
      }
    }
  }

  grouping ncs_rpc_notif_router-isis-authenticate-snp-grouping {
    leaf authenticate {
      tailf:info
        "Authentication";
      tailf:cli-incomplete-command;
      type empty;
    }
    leaf snp {
      tailf:info
        "SNP PDUs";
      type enumeration {
        enum "send-only" {
          tailf:info
            "Send but do not check PDUs on receiving";
        }
        enum "validate" {
          tailf:info
            "Send and check PDUs on receiving";
        }
      }
    }
  }

  grouping ncs_rpc_notif_lsp-gen-interval-grouping {
    leaf interval {
      tailf:cli-drop-node-name;
      type uint32 {
        range "1..120";
        tailf:info
          "<1-120>;;Interval in seconds";
      }
    }
    leaf initial-wait {
      tailf:cli-drop-node-name;
      type uint32 {
        range "1..120000";
        tailf:info
          "<1-120000>;;Initial wait in milliseconds";
      }
    }
    leaf wait {
      tailf:cli-drop-node-name;
      type uint32 {
        range "1..120000";
        tailf:info
          "<1-120000>;;Wait between first and second lsp generation in milliseconds";
      }
    }
  }

  grouping ncs_rpc_notif_set-overload-bit-suppress-grouping {
    leaf external {
      tailf:info
        "If overload-bit set, don't advertise IP prefixes learned from other protocols";
      tailf:cli-break-sequence-commands;
      type empty;
    }
    leaf interlevel {
      tailf:info
        "If overload-bit set, don't advertise IP prefixes learned from another ISIS level";
      type empty;
    }
  }

  grouping ncs_rpc_notif_authentication-level-grouping {
    leaf level {
      tailf:cli-drop-node-name;
      type authentication-level-type;
    }
  }

  grouping ncs_rpc_notif_redist-level-grouping {
    leaf level {
      tailf:cli-drop-node-name;
      tailf:cli-break-sequence-commands;
      type isis-level-type;
    }
  }

  grouping ncs_rpc_notif_router-isis-redistribute-grouping {
    leaf metric {
      tailf:info
        "ISIS default metric";
      type uint32 {
        tailf:info
          "<0-4294967295>;;ISIS default metric";
        range "0..4294967295";
      }
    }
    leaf route-map {
      tailf:info
        "Route map reference";
      type string {
        tailf:info
          "WORD;;Pointer to route-map entries";
      }
    }
    leaf metric-type {
      tailf:info
        "OSPF/IS-IS exterior metric type for redistributed routes";
      type enumeration {
        enum "external" {
          tailf:info
            "Set IS-IS External metric type";
        }
        enum "internal" {
          tailf:info
            "Set IS-IS Internal metric type";
        }
      }
      default "internal";
    }
    uses ncs_rpc_notif_router-isis-level-grouping;
  }

  grouping ncs_rpc_notif_router-isis-af-redistribute-grouping {
    leaf metric {
      tailf:info
        "ISIS default metric";
      type uint32 {
        tailf:info
          "<0-4294967295>;;ISIS default metric";
        range "0..4294967295";
      }
    }
    leaf metric-type {
      tailf:info
        "OSPF/IS-IS exterior metric type for redistributed routes";
      type enumeration {
        enum "external" {
          tailf:info
            "Set IS-IS External metric type";
        }
        enum "internal" {
          tailf:info
            "Set IS-IS Internal metric type";
        }
      }
    }
    uses ncs_rpc_notif_router-isis-level-grouping;
    leaf route-map {
      tailf:info
        "Route map reference";
      type string {
        tailf:info
          "WORD;;Pointer to route-map entries";
      }
    }
    leaf include-connected {
      tailf:info
        "Include connected";
      type empty;
    }
  }

  grouping ncs_rpc_notif_isis-redist-ospf-match-grouping {
    uses ncs_rpc_notif_redist-level-grouping;
    leaf metric {
      tailf:info
        "ISIS default metric";
      type uint32 {
        tailf:info
          "<0-4294967295>;;ISIS default metric";
        range "0..4294967295";
      }
    }
    leaf route-map {
      tailf:info
        "Route map reference";
      type string {
        tailf:info
          "WORD;;Pointer to route-map entries";
      }
    }
  }

  grouping ncs_rpc_notif_router-isis-interface-grouping {
    container authentication {
      tailf:info
        "ISIS authentication for LSPs";
      container mode {
        tailf:info
          "Authentication mode";
        container md5 {
          tailf:info
            "Keyed message digest";
          presence "true";
          uses ncs_rpc_notif_authentication-level-grouping;
        }
        container text {
          tailf:info
            "Clear text password";
          presence "true";
          uses ncs_rpc_notif_authentication-level-grouping;
        }
      }
      container key-chain {
        tailf:info
          "Authentication key-chain";
        tailf:cli-compact-syntax;
        tailf:cli-sequence-commands;
        leaf name {
          tailf:cli-drop-node-name;
          type string {
            tailf:info
              "WORD;;Name of key-chain";
          }
        }
        uses ncs_rpc_notif_authentication-level-grouping;
      }
      container send-only {
        tailf:info
          "Authentication send only, receive ignore";
        presence "true";
        uses ncs_rpc_notif_authentication-level-grouping;
      }
    }
  }

  grouping ncs_rpc_notif_router-isis-af-grouping {
    leaf adjacency-check {
      tailf:info
        "Check ISIS neighbor protocol support";
      tailf:cli-boolean-no;
      tailf:cli-full-command;
      type boolean;
      default "true";
    }
    container set-overload-bit {
      tailf:info
        "Signal other routers not to use us in SPF";
      tailf:cli-delete-when-empty;
      tailf:cli-reset-container;
      presence "true";
      choice set-overload-bit-choice {
        container on-startup {
          tailf:info
            "Set overload-bit only temporarily after reboot";
          choice on-startup-choice {
            container time {
              tailf:cli-drop-node-name;
              tailf:cli-compact-syntax;
              tailf:cli-sequence-commands;
              leaf time {
                tailf:cli-drop-node-name;
                type uint32 {
                  tailf:info
                    "<5-86400>;;Time in seconds to advertise ourself as overloaded after reboot";
                  range "5..86400";
                }
              }
              leaf suppress {
                tailf:info
                  "If overload-bit set, suppress the following types of IP prefixes";
                tailf:cli-incomplete-command;
                type empty;
              }
              uses ncs_rpc_notif_set-overload-bit-suppress-grouping;
            }
            container wait-for-bgp {
              tailf:info
                "Let BGP decide when to unset the overload bit";
              presence "Let BGP decide when to unset the overload bitW";
              container suppress {
                tailf:info
                  "If overload-bit set, suppress the following types of IP prefixes";
                tailf:cli-compact-syntax;
                tailf:cli-sequence-commands;
                uses ncs_rpc_notif_set-overload-bit-suppress-grouping;
              }
            }
          }
        }
        container suppress {
          tailf:info
            "If overload-bit set, suppress the following types of IP prefixes";
          tailf:cli-compact-syntax;
          tailf:cli-sequence-commands;
          uses ncs_rpc_notif_set-overload-bit-suppress-grouping;
        }
      }
    }
    container spf-interval {
      tailf:info
        "Minimum interval between SPF calculations";
      tailf:cli-compact-syntax;
      choice spf-interval-choice {
        list level-1-2 {
          tailf:cli-drop-node-name;
          tailf:cli-suppress-mode;
          tailf:cli-delete-when-empty;
          tailf:cli-compact-syntax;
          tailf:cli-sequence-commands;
          tailf:cli-incomplete-command;
          key "level";
          leaf level {
            type enumeration {
              enum "level-1" {
                tailf:info
                  "Set interval for level 1 only";
              }
              enum "level-2" {
                tailf:info
                  "Set interval for level 2 only";
              }
            }
          }
          uses ncs_rpc_notif_spf-intervals-grouping;
        }
        container intervals {
          tailf:cli-drop-node-name;
          tailf:cli-compact-syntax;
          tailf:cli-sequence-commands;
          uses ncs_rpc_notif_spf-intervals-grouping;
        }
      }
    }
    container prc-interval {
      tailf:info
        "Minimum interval between partial route calculations";
      tailf:cli-compact-syntax;
      tailf:cli-sequence-commands;
      leaf interval {
        tailf:cli-drop-node-name;
        type uint32 {
          tailf:info
            "<1-120>;;PRC interval in seconds";
          range "1..120";
        }
      }
      leaf initial-wait {
        tailf:cli-drop-node-name;
        type uint32 {
          tailf:info
            "<1-120000>;;Initial wait for PRC in milliseconds";
          range "1..120000";
        }
      }
      leaf minimum-wait {
        tailf:cli-drop-node-name;
        type uint32 {
          tailf:info
            "<1-120000>;;Minimum wait between first and second PRC in milliseconds";
          range "1..120000";
        }
      }
    }
    container metric-style {
      tailf:info
        "Use old-style (ISO 10589) or new-style packet formats";
      choice metric-style-choice {
        container narrow {
          tailf:info
            "Use old style of TLVs with narrow metric";
          presence "true";
          uses ncs_rpc_notif_narrow-wide-transition-grouping;
        }
        container transition {
          tailf:info
            "Send and accept both styles of TLVs during transition";
          presence "true";
          leaf level {
            tailf:cli-drop-node-name;
            type isis-level-type;
          }
        }
        container wide {
          tailf:info
            "Use new style of TLVs to carry wider metric";
          presence "true";
          uses ncs_rpc_notif_narrow-wide-transition-grouping;
        }
      }
    }
    choice metric-choice {
      case default-case {
        container metric {
          tailf:info
            "Set ISIS metric for all interfaces";
          tailf:cli-diff-dependency "../metric-style" {
            tailf:xpath-root 3;
          }
          leaf default {
            tailf:cli-drop-node-name;
            type uint32 {
              tailf:info
                "<1-16777214>;;Default metric";
              range "1..16777214";
            }
          }
        }
      }
      case level-case {
        container metric-level {
          tailf:cli-drop-node-name;
          tailf:cli-diff-dependency "../metric-style" {
            tailf:xpath-root 3;
          }
          list metric {
            tailf:cli-suppress-mode;
            tailf:cli-delete-when-empty;
            tailf:cli-compact-syntax;
            tailf:cli-sequence-commands;
            key "level";
            leaf level {
              type enumeration {
                enum "level-1" {
                  tailf:info
                    "Apply metric to level-1 links";
                }
                enum "level-2" {
                  tailf:info
                    "Apply metric to level-2 links";
                }
              }
            }
            leaf default {
              tailf:cli-drop-node-name;
              tailf:cli-prefix-key;
              type uint32 {
                tailf:info
                  "<1-16777214>;;Default metric";
                range "1..16777214";
              }
            }
          }
        }
      }
    }
    leaf maximum-paths {
      tailf:info
        "Forward packets over multiple paths";
      tailf:cli-full-command;
      type uint32 {
        tailf:info
          "<1-32>;;Number of paths";
        range "1..32";
      }
    }
    container default-information {
      tailf:info
        "Control distribution of default information";
      tailf:cli-incomplete-no;
      container originate {
        tailf:info
          "Distribute a default route";
        presence "true";
        leaf route-map {
          tailf:info
            "Route-map reference";
          type string {
            tailf:info
              "WORD;;Route map name";
          }
        }
      }
    }
  }

  grouping ncs_rpc_notif_router-isis-grouping {
    container protocol {
      tailf:info
        "Set protocol's administrative state";
      leaf shutdown {
        tailf:info
          "Set protocol's administrative state to disable";
        type empty;
      }
    }
    leaf max-area-addresses {
      tailf:info
        "Allow configuration of more manual area addresses";
      tailf:cli-full-command;
      type uint32 {
        tailf:info
          "<3-254>;;Max number of manual area addresses";
        range "3..254";
      }
    }
    list net {
      tailf:info
        "A Network Entity Title for this process (OSI only)";
      tailf:cli-suppress-mode;
      tailf:cli-delete-when-empty;
      key "tag";
      leaf tag {
        type string {
          tailf:info
            "XX.XXXX. ... .XXX.XX;;Network entity title (NET)";
        }
      }
    }
    leaf is-type {
      tailf:info
        "IS Level for this routing process (OSI only)";
      tailf:cli-full-command;
      type enumeration {
        enum "level-1" {
          tailf:info
            "Act as a station router only";
        }
        enum "level-1-2" {
          tailf:info
            "Act as both a station router and an area router";
        }
        enum "level-2-only" {
          tailf:info
            "Act as an area router only";
        }
      }
    }
    container advertise {
      tailf:info
        "Control which IP routes flow in L1 and L2 LSPs";
      leaf passive-only {
        tailf:info
          "only interface address of passive interfaces";
        type empty;
      }
    }
    uses ncs_rpc_notif_router-isis-interface-grouping;
    container area-password {
      tailf:info
        "Configure the authentication password for an area";
      tailf:cli-compact-syntax;
      tailf:cli-sequence-commands;
      leaf name {
        tailf:cli-drop-node-name;
        type string {
          tailf:info
            "WORD;;Area password";
        }
      }
      uses ncs_rpc_notif_router-isis-authenticate-snp-grouping;
    }
    container ispf {
      tailf:info
        "Configure execution of incremental SPF";
      tailf:cli-compact-syntax;
      tailf:cli-sequence-commands;
      leaf level {
        tailf:cli-drop-node-name;
        type enumeration {
          enum "level-1" {
            tailf:info
              "Do incremental SPF for level-1";
          }
          enum "level-1-2" {
            tailf:info
              "Do incremental SPF for both levels";
          }
          enum "level-2" {
            tailf:info
              "Do incremental SPF for level-2";
          }
        }
      }
      leaf number {
        tailf:cli-drop-node-name;
        type uint32 {
          range "1..600";
          tailf:info
            "<1-600>;;Number of seconds before activating incremental-spf";
        }
      }
    }
    container fast-flood {
      tailf:info
        "Flood LSPs (that triggered SPF) before running SPF";
      presence "Flood LSPs (that triggered SPF) before running SPF";
      leaf number {
        tailf:cli-drop-node-name;
        type uint32 {
          range "1..15";
          tailf:info
            "<1-15>;;number of LSPs to be flooded before starting SPF";
        }
      }
    }
    container ip {
      tailf:info
        "IP specific commands";
      container route {
        tailf:info
          "ISIS IP routes";
        container priority {
          tailf:info
            "Assign priority to IP prefixes";
          container high {
            tailf:info
              "Assign high priority to important IP prefixes in ISIS IP local RIB";
            leaf tag {
              tailf:info
                "Assign high priority to IP prefixes with a specific route tag";
              type uint32 {
                range "1..4294967295";
                tailf:info
                  "<1-4294967295>;;tag value";
              }
            }
          }
        }
      }
    }
    container set-attached-bit {
      tailf:info
        "Conditionally advertise us as attached to L2";
      leaf route-map {
        tailf:info
          "Route-map reference";
        type string {
          tailf:info
            "WORD;;Route map name";
        }
      }
    }
    leaf max-lsp-lifetime {
      tailf:info
        "Set maximum LSP lifetime";
      tailf:cli-full-command;
      type uint32 {
        range "1..65535";
        tailf:info
          "<1-65535>;;Maximum LSP lifetime in seconds";
      }
    }
    leaf lsp-refresh-interval {
      tailf:info
        "Set LSP refresh interval";
      tailf:cli-full-command;
      type uint32 {
        range "1..65535";
        tailf:info
          "<1-65535>;;LSP refresh time in seconds";
      }
    }
    container lsp-gen-interval {
      tailf:info
        "Minimum interval between regenerating same LSP";
      choice lsp-gen-interval-choice {
        container intervals {
          tailf:cli-drop-node-name;
          tailf:cli-compact-syntax;
          tailf:cli-sequence-commands;
          uses ncs_rpc_notif_lsp-gen-interval-grouping;
        }
        container intervals-levels {
          tailf:cli-drop-node-name;
          container intervals-level-1 {
            tailf:cli-drop-node-name;
            tailf:cli-compact-syntax;
            tailf:cli-sequence-commands;
            leaf level-1 {
              tailf:info
                "Set interval for level 1 only";
              type empty;
            }
            uses ncs_rpc_notif_lsp-gen-interval-grouping;
          }
          container intervals-level-2 {
            tailf:cli-drop-node-name;
            tailf:cli-compact-syntax;
            tailf:cli-sequence-commands;
            leaf level-2 {
              tailf:info
                "Set interval for level 2 only";
              type empty;
            }
            uses ncs_rpc_notif_lsp-gen-interval-grouping;
          }
        }
      }
    }
    container use {
      tailf:info
        "Use different algorithms during SPF";
      leaf external-metrics {
        tailf:info
          "Honour external metrics during SPF";
        type empty;
      }
    }
    leaf ignore-lsp-errors {
      tailf:info
        "Ignore LSPs with bad checksums";
      tailf:cli-boolean-no;
      tailf:cli-full-command;
      type boolean;
      default "true";
    }
    container hostname {
      tailf:info
        "Dynamic hostname for IS-IS";
      leaf dynamic {
        tailf:info
          "Dynamic hostname";
        tailf:cli-boolean-no;
        type boolean;
        default "true";
      }
    }
    container log-adjacency-changes {
      tailf:info
        "Log changes in adjacency state";
      presence "true";
      leaf all {
        tailf:info
          "Include changes generated by non-IIH event";
        type empty;
      }
    }
    container partition {
      tailf:info
        "CLNS area partition";
      leaf avoidance {
        tailf:info
          "Withdraw area prefix if partition detected";
        type empty;
      }
    }
    leaf lsp-mtu {
      tailf:info
        "Set maximum LSP size";
      tailf:cli-full-command;
      type uint32 {
        range "128..4352";
        tailf:info
          "<128-4352>;;Max LSP size in bytes";
      }
    }
    container lsp-full {
      tailf:info
        "If we run out of LSP fragments";
      container suppress {
        tailf:info
          "suppress the following types of IP prefixes";
        choice lsp-full-choince {
          container external-interlevel-container {
            tailf:cli-drop-node-name;
            tailf:cli-compact-syntax;
            leaf external {
              tailf:info
                "don't advertise IP prefixes learned from other protocols";
              type empty;
            }
            leaf interlevel {
              tailf:info
                "don't advertise IP prefixes learned from another ISIS level";
              type empty;
            }
          }
          leaf none {
            tailf:info
              "don't suppress any prefixes";
            type empty;
          }
        }
      }
    }
    leaf update-queue-depth {
      tailf:info
        "Set Update process queue depth";
      type uint32 {
        tailf:info
          "<1-2147483647>;;Max queue depth";
        range "1..2147483647";
      }
    }
    container nsf {
      tailf:info
        "Non-stop forwarding";
      leaf cisco {
        tailf:info
          "Checkpoint method";
        type empty;
      }
      leaf ietf {
        tailf:info
          "IETF method";
        type empty;
      }
    }
    container bfd {
      tailf:info
        "BFD configuration commands";
      leaf all-interfaces {
        tailf:info
          "Enable BFD on all interfaces";
        type empty;
      }
    }
    container distance {
      tailf:info
        "Define an administrative distance";
      container distance-ip {
        tailf:cli-drop-node-name;
        tailf:cli-compact-syntax;
        tailf:cli-sequence-commands;
        leaf distance {
          tailf:cli-drop-node-name;
          tailf:cli-incomplete-command;
          type uint8 {
            tailf:info
              "<1-255>;;Administrative distance";
            range "1..255";
          }
        }
        leaf ip {
          tailf:info
            "Distance applied for IP derived routes";
          type empty;
        }
      }
      list distance-network-list {
        tailf:cli-drop-node-name;
        tailf:cli-suppress-mode;
        tailf:cli-delete-when-empty;
        tailf:cli-compact-syntax;
        tailf:cli-sequence-commands {
          tailf:cli-reset-siblings;
        }
        key "ip-address wildcard-mask";
        leaf ip-address {
          type inet:ipv4-address {
            tailf:info
              "A.B.C.D;;IP Source address";
          }
        }
        leaf wildcard-mask {
          type inet:ipv4-address {
            tailf:info
              "A.B.C.D;;Wildcard bits";
          }
        }
        leaf distance {
          tailf:cli-drop-node-name;
          tailf:cli-prefix-key;
          type uint8 {
            tailf:info
              "<1-255>;;Administrative distance";
            range "1..255";
          }
        }
        leaf access-list {
          tailf:cli-drop-node-name;
          type std-ip-acl-type;
        }
      }
      container distance-clns {
        tailf:cli-drop-node-name;
        tailf:cli-compact-syntax;
        tailf:cli-sequence-commands;
        leaf distance {
          tailf:cli-drop-node-name;
          tailf:cli-incomplete-command;
          type uint8 {
            tailf:info
              "<1-255>;;OSPF Administrative distance";
            range "1..255";
          }
        }
        leaf clns {
          tailf:info
            "Distance applied for CLNS derived routes";
          type empty;
        }
      }
    }
    container domain-password {
      tailf:info
        "Set the authentication password for a routing domain";
      tailf:cli-sequence-commands;
      tailf:cli-compact-syntax;
      leaf name {
        tailf:cli-drop-node-name;
        type string {
          tailf:info
            "WORD;;Routing domain password";
        }
      }
      uses ncs_rpc_notif_router-isis-authenticate-snp-grouping;
    }
    choice hello-padding-choice {
      container hello {
        tailf:info
          "Pad ISIS hello PDUs to full MTU";
        leaf padding {
          tailf:info
            "Pad hello PDU";
          tailf:cli-boolean-no;
          tailf:cli-full-command;
          type boolean;
          default "true";
        }
      }
      container conf {
        tailf:cli-drop-node-name;
        container hello {
          tailf:info
            "Pad ISIS hello PDUs to full MTU";
          tailf:cli-incomplete-no;
          tailf:cli-incomplete-command;
          leaf padding {
            tailf:info
              "Pad hello PDU";
            type enumeration {
              enum "multi-point" {
                tailf:info
                  "Pad LAN hello PDUs";
              }
              enum "point-to-point" {
                tailf:info
                  "Pad point-to-point hello PDUs";
              }
            }
          }
        }
      }
    }
    container traffic-share {
      tailf:info
        "How to compute traffic share over alternate paths";
      container min {
        tailf:info
          "All traffic shared among min metric paths";
        leaf across-interfaces {
          tailf:info
            "Use different interfaces for equal-cost paths";
          type empty;
        }
      }
    }
    container microloop {
      tailf:info
        "Enable microloop protection configuration commands";
      container avoidance {
        tailf:info
          "Enable local microloop avoidance";
        tailf:cli-delete-when-empty;
        tailf:cli-reset-container;
        presence "true";
        choice avoidance-choice {
          leaf protected {
            tailf:info
              "Microloop avoidance for protected link or prefix only";
            type empty;
          }
          leaf disable {
            tailf:info
              "Disable Microloop avoidance";
            type empty;
          }
        }
      }
    }
    container segment-routing {
      tailf:info
        "Enable Segment Routing Feature";
      leaf mpls {
        tailf:info
          "Enable Segment Routing Feature using MPLS encapsulation";
        type empty;
      }
    }
    container fast-reroute {
      tailf:info
        "Configure Fast-Reroute";
      container per-prefix {
        tailf:info
          "Enable Fast-Reroute Per-Prefix";
        container level-1 {
          tailf:info
            "Apply to level-1";
          choice level-choice {
            leaf route-map {
              tailf:info
                "route-map for selecting primary paths for protection";
              type string {
                tailf:info
                  "WORD;;route-map name";
              }
            }
            leaf all {
              tailf:info
                "Enable Fast-Reroute for primary paths";
              type empty;
            }
          }
        }
        container level-2 {
          tailf:info
            "Apply to level-2";
          choice level-choice {
            leaf route-map {
              tailf:info
                "route-map for selecting primary paths for protection";
              type string {
                tailf:info
                  "WORD;;route-map name";
              }
            }
            leaf all {
              tailf:info
                "Enable Fast-Reroute for primary paths";
              type empty;
            }
          }
        }
      }
      container remote-lfa {
        tailf:info
          "Configuring fast-reroute remote-lfa";
        container level-1 {
          tailf:info
            "Apply to level-1";
          container mpls-ldp {
            tailf:info
              "Use mpls-ldp tunnel type";
            tailf:cli-delete-when-empty;
            presence "true";
            leaf maximum-metric {
              tailf:info
                "maximum metric to reach release node";
              type uint32 {
                tailf:info
                  "<1-4294967295>;;metric value";
              }
            }
          }
        }
        container level-2 {
          tailf:info
            "Apply to level-2";
          container mpls-ldp {
            tailf:info
              "Use mpls-ldp tunnel type";
            tailf:cli-delete-when-empty;
            presence "true";
            leaf maximum-metric {
              tailf:info
                "maximum metric to reach release node";
              type uint32 {
                tailf:info
                  "<1-4294967295>;;metric value";
              }
            }
          }
        }
      }
    }
    container mpls {
      tailf:info
        "Configure MPLS routing protocol parameters";
      container ldp {
        tailf:info
          "routing protocol commands for MPLS LDP";
        leaf sync {
          tailf:info
            "Configure LDP-IGP Synchronization";
          type empty;
        }
      }
      container traffic-eng {
        tailf:info
          "routing protocol commands for MPLS Traffic Engineering";
        leaf level-1 {
          tailf:info
            "Run MPLS TE on IS-IS level 1 only";
          tailf:cli-full-command;
          type empty;
        }
        leaf level-2 {
          tailf:info
            "Run MPLS TE on IS-IS level 2 only";
          tailf:cli-full-command;
          type empty;
        }
        leaf multicast-intact {
          tailf:info
            "MPLS TE and PIM interaction";
          tailf:cli-full-command;
          type empty;
        }
        container router-id {
          tailf:info
            "Traffic Engineering stable IP address for system";
          uses ncs_rpc_notif_interface-name-grouping;
        }
        container scanner {
          tailf:info
            "Timer parameters for TE database";
          presence "Timer parameters for TE database";
          tailf:cli-compact-syntax;
          leaf interval {
            tailf:info
              "time (secs) between LSPDB walks for TE";
            type uint32 {
              range "1..60";
              tailf:info
                "<1-60>;;interval between LSPDB walks for TE TLVs extraction";
            }
          }
          leaf max-flash {
            tailf:info
              "Number of ISIS LSPs to be processed with no delay";
            type uint32 {
              range "0..200";
              tailf:info
                "<0-200>;;Max. number of LSPs ISIS may send to TE db without delay";
            }
          }
        }
      }
    }
    uses ncs_rpc_notif_passive-interface-grouping;
    uses ncs_rpc_notif_router-distribute-list-grouping;
    container redistribute {
      tailf:info
        "Redistribute information from another routing protocol";
      container maximum-prefix {
        tailf:info
          "Maximum number of prefixes redistributed to protocol";
        tailf:cli-compact-syntax;
        tailf:cli-sequence-commands;
        leaf number {
          tailf:cli-drop-node-name;
          type uint32 {
            tailf:info
              "<1-4294967295>;;Maximum number of IP prefixes redistributed";
            range "1..4294967295";
          }
        }
        leaf threshold-value {
          tailf:cli-drop-node-name;
          tailf:cli-break-sequence-commands;
          type uint32 {
            tailf:info
              "<1-100>;;Threshold value (%) at which to generate a warning message";
            range "1..100";
          }
        }
        leaf warning-only {
          tailf:info
            "Only give warning message when limit is exceeded";
          tailf:cli-full-command;
          type empty;
        }
        leaf withdraw {
          tailf:info
            "Withdraw redistibuted prefixes";
          tailf:cli-full-command;
          type empty;
        }
      }
      container connected {
        tailf:info
          "Connected";
        tailf:cli-compact-syntax;
        tailf:cli-delete-when-empty;
        presence "Connected";
        uses ncs_rpc_notif_router-isis-redistribute-grouping;
      }
      container static {
        tailf:info
          "Static routes";
        tailf:cli-compact-syntax;
        tailf:cli-delete-when-empty;
        presence "Static routes";
        container clns {
          tailf:info
            "Redistribution of BGP NSAP routes";
          tailf:cli-delete-when-empty;
          presence "true";
          leaf route-map {
            tailf:info
              "Route map reference";
            type string {
              tailf:info
                "WORD;;Pointer to route-map entries";
            }
          }
        }
        container ip {
          tailf:info
            "Redistribution of IP static routes";
          tailf:cli-compact-syntax;
          tailf:cli-delete-when-empty;
          presence "true";
          uses ncs_rpc_notif_router-isis-redistribute-grouping;
        }
      }
      container odr {
        tailf:info
          "On Demand stub Routes";
        tailf:cli-compact-syntax;
        presence "On Demand stub Routes";
        uses ncs_rpc_notif_router-isis-redistribute-grouping;
      }
      container rip {
        tailf:info
          "Routing Information Protocol (RIP)";
        tailf:cli-compact-syntax;
        presence "Routing Information Protocol (RIP)";
        uses ncs_rpc_notif_router-isis-redistribute-grouping;
      }
      list bgp {
        tailf:info
          "Border Gateway Protocol (BGP)";
        tailf:cli-suppress-mode;
        tailf:cli-delete-when-empty;
        tailf:cli-compact-syntax;
        tailf:cli-incomplete-command;
        key "as-no";
        leaf as-no {
          tailf:cli-suppress-range;
          type bgp-as-no-type;
        }
        container clns {
          tailf:info
            "Redistribution of BGP NSAP routes";
          tailf:cli-delete-when-empty;
          presence "true";
          leaf route-map {
            tailf:info
              "Route map reference";
            type string {
              tailf:info
                "WORD;;Pointer to route-map entries";
            }
          }
        }
        uses ncs_rpc_notif_router-isis-redistribute-grouping;
      }
      list ospf {
        tailf:info
          "Open Shortest Path First (OSPF)";
        tailf:cli-suppress-mode;
        tailf:cli-delete-when-empty;
        tailf:cli-compact-syntax;
        key "id";
        leaf id {
          tailf:cli-suppress-range;
          type uint16 {
            tailf:info
              "<1-65535>;;Process ID";
            range "1..65535";
          }
        }
        uses ncs_rpc_notif_redistribute-ospf-match-grouping;
        uses ncs_rpc_notif_router-isis-redistribute-grouping;
      }
      container isis {
        tailf:info
          "ISO IS-IS";
        tailf:cli-compact-syntax;
        list isis-area-list {
          tailf:cli-drop-node-name;
          tailf:cli-suppress-mode;
          tailf:cli-delete-when-empty;
          tailf:cli-compact-syntax;
          tailf:cli-incomplete-command;
          key "area-tag";
          leaf area-tag {
            tailf:cli-disallow-value "ip";
            type string {
              tailf:info
                "WORD;;ISO routing area tag";
            }
          }
          leaf ip {
            tailf:info
              "Redistribution of IP routes between levels or processes";
            type empty;
          }
          leaf metric {
            tailf:info
              "ISIS default metric";
            type uint32 {
              tailf:info
                "<0-4294967295>;;ISIS default metric";
              range "0..4294967295";
            }
          }
          leaf route-map {
            tailf:info
              "Route map reference";
            type string {
              tailf:info
                "WORD;;Pointer to route-map entries";
            }
          }
        }
        list ip {
          tailf:info
            "Redistribution of IP routes between levels";
          tailf:cli-suppress-mode;
          tailf:cli-delete-when-empty;
          tailf:cli-compact-syntax;
          tailf:cli-incomplete-command;
          key "from into";
          leaf from {
            type enumeration {
              enum "level-1" {
                tailf:info
                  "Inter-area routes from level-1";
              }
              enum "level-2" {
                tailf:info
                  "Inter-area routes from level-2";
              }
            }
          }
          leaf into {
            tailf:info
              "from level-n into level-m";
            tailf:cli-expose-key-name;
            type enumeration {
              enum "level-1" {
                tailf:info
                  "Inter-area routes from level-1";
              }
              enum "level-2" {
                tailf:info
                  "Inter-area routes from level-2";
              }
            }
          }
          leaf distribute-list {
            tailf:info
              "select routes";
            type uint8 {
              tailf:info
                "<100-199>;;IP extended acces-list number";
              range "100..199";
            }
          }
          leaf route-map {
            tailf:info
              "Route map for route matching";
            type string {
              tailf:info
                "WORD;;Name of the route-map";
            }
          }
        }
      }
      list eigrp {
        tailf:info
          "Enhanced Interior Gateway Routing Protocol (EIGRP)";
        tailf:cli-suppress-mode;
        tailf:cli-delete-when-empty;
        tailf:cli-compact-syntax;
        key "as-no";
        leaf as-no {
          type eigrp-as-no-type;
        }
        uses ncs_rpc_notif_router-isis-redistribute-grouping;
      }
      container iso-igrp {
        tailf:info
          "IGRP for OSI networks";
        presence "IGRP for OSI networks";
        tailf:cli-compact-syntax;
        tailf:cli-sequence-commands;
        choice iso-igrp-choice {
          container area-tag-route-map-container {
            tailf:cli-drop-node-name;
            tailf:cli-flatten-container;
            tailf:cli-compact-syntax;
            tailf:cli-sequence-commands;
            leaf area-tag {
              tailf:cli-drop-node-name;
              tailf:cli-disallow-value "route-map";
              type string {
                tailf:info
                  "WORD;;ISO routing area tag";
              }
            }
            leaf route-map {
              tailf:info
                "Route map reference";
              type string {
                tailf:info
                  "WORD;;Pointer to route-map entries";
              }
            }
          }
          leaf route-map {
            tailf:info
              "Route map reference";
            type string {
              tailf:info
                "WORD;;Pointer to route-map entries";
            }
          }
        }
        uses ncs_rpc_notif_redist-level-grouping;
        leaf metric {
          tailf:info
            "ISIS default metric";
          type uint32 {
            tailf:info
              "<0-4294967295>;;ISIS default metric";
            range "0..4294967295";
          }
        }
        leaf metric-type {
          tailf:info
            "OSPF/IS-IS exterior metric type for redistributed routes";
          type enumeration {
            enum "external" {
              tailf:info
                "Set IS-IS External metric type";
            }
            enum "internal" {
              tailf:info
                "Set IS-IS Internal metric type";
            }
          }
        }
      }
      container mobile {
        tailf:info
          "Mobile routes";
        tailf:cli-compact-syntax;
        presence "Mobile routes";
        uses ncs_rpc_notif_router-isis-redistribute-grouping;
      }
    }
    list summary-address {
      tailf:info
        "Configure IP address summaries";
      tailf:cli-suppress-mode;
      tailf:cli-delete-when-empty;
      tailf:cli-compact-syntax;
      key "ip mask";
      leaf ip {
        type inet:ipv4-address {
          tailf:info
            "A.B.C.D;;IP summary address";
        }
      }
      leaf mask {
        type inet:ipv4-address {
          tailf:info
            "A.B.C.D;;Summary mask";
        }
      }
      leaf level {
        tailf:cli-drop-node-name;
        type enumeration {
          enum "level-1" {
            tailf:info
              "Summarize into level-1 area";
          }
          enum "level-1-2" {
            tailf:info
              "Summarize into both area and sub-domain";
          }
          enum "level-2" {
            tailf:info
              "Summarize into level-2 sub-domain";
          }
        }
      }
      leaf tag {
        tailf:info
          "Set tag";
        type uint32 {
          tailf:info
            "<1-4294967295>;;32-bit tag value";
          range "1..4294967295";
        }
      }
      leaf metric {
        tailf:info
          "Set metric for summay route";
        type uint32 {
          tailf:info
            "<1-4294967295>;;metric";
          range "1..4294967295";
        }
      }
    }
    uses ncs_rpc_notif_router-isis-af-grouping;
    container address-family {
      tailf:info
        "Enter Address Family command mode";
      container ipv6 {
        tailf:info
          "Address family";
        tailf:cli-add-mode;
        tailf:cli-mode-name "config-router-af";
        tailf:cli-exit-command "exit-address-family" {
          tailf:info
            "Exit from Address Family configuration mode";
        }
        leaf af {
          tailf:cli-drop-node-name;
          tailf:cli-hide-in-submode;
          tailf:cli-full-command;
          type enumeration {
            enum "unicast" {
              tailf:info
                "Address Family Modifier";
            }
          }
          default "unicast";
        }
        uses ncs_rpc_notif_router-isis-af-grouping;
        list summary-prefix {
          tailf:info
            "Configure IPv6 summary prefix";
          tailf:cli-suppress-mode;
          tailf:cli-delete-when-empty;
          tailf:cli-compact-syntax;
          key "prefix";
          leaf prefix {
            type ipv6-prefix {
              tailf:info
                "X:X:X:X::X/<0-128>;;IPv6 prefix x:x::y/<z>";
            }
          }
          leaf level {
            tailf:cli-drop-node-name;
            type enumeration {
              enum "level-1" {
                tailf:info
                  "Summarize into level-1 area";
              }
              enum "level-1-2" {
                tailf:info
                  "Summarize into both area and sub-domain";
              }
              enum "level-2" {
                tailf:info
                  "Summarize into level-2 sub-domain";
              }
            }
          }
          leaf tag {
            tailf:info
              "Set tag";
            type uint32 {
              tailf:info
                "<1-4294967295>;;32-bit tag value";
            }
          }
        }
        leaf distance {
          tailf:info
            "Administrative distance";
          tailf:cli-full-command;
          type uint32 {
            tailf:info
              "<1-255>;;OSPF Administrative distance";
            range "1..255";
          }
        }
        container multi-topology {
          tailf:info
            "Enable multi-topology mode";
          presence "Enable multi-topology mode";
          leaf transition {
            tailf:info
              "Accept and generate both IS-IS IPv6 and Multi-topology IPv6 TLVs";
            type empty;
          }
        }
        container redistribute {
          tailf:info
            "Redistribute IPv6 prefixes from another routing protocol";
          container connected {
            tailf:info
              "Connected";
            tailf:cli-compact-syntax;
            tailf:cli-delete-when-empty;
            presence "Connected";
            uses ncs_rpc_notif_router-isis-af-redistribute-grouping;
          }
          container static {
            tailf:info
              "Static routes";
            tailf:cli-compact-syntax;
            tailf:cli-delete-when-empty;
            presence "Static routes";
            uses ncs_rpc_notif_router-isis-redistribute-grouping;
          }
          container bgp {
            tailf:info
              "Border Gateway Protocol (BGP)";
            tailf:cli-compact-syntax;
            leaf as-no {
              tailf:cli-drop-node-name;
              type bgp-as-no-type;
            }
            uses ncs_rpc_notif_router-isis-af-redistribute-grouping;
          }
          list ospf {
            tailf:info
              "Open Shortest Path First (OSPF)";
            tailf:cli-suppress-mode;
            tailf:cli-delete-when-empty;
            tailf:cli-compact-syntax;
            key "id";
            leaf id {
              tailf:cli-suppress-range;
              type uint16 {
                tailf:info
                  "<1-65535>;;Process ID";
                range "1..65535";
              }
            }
            uses ncs_rpc_notif_redistribute-ospf-match-grouping;
            uses ncs_rpc_notif_router-isis-af-redistribute-grouping;
          }
          list rip {
            tailf:info
              "IPv6 Routing Information Protocol (RIPv6)";
            tailf:cli-suppress-mode;
            tailf:cli-delete-when-empty;
            tailf:cli-compact-syntax;
            key "process";
            leaf process {
              type string {
                tailf:info
                  "WORD;;User selected string identifying this process";
              }
            }
            uses ncs_rpc_notif_router-isis-af-redistribute-grouping;
          }
          list eigrp {
            tailf:info
              "Enhanced Interior Gateway Routing Protocol (EIGRP)";
            tailf:cli-suppress-mode;
            tailf:cli-delete-when-empty;
            tailf:cli-compact-syntax;
            key "as-no";
            leaf as-no {
              type eigrp-as-no-type;
            }
            uses ncs_rpc_notif_router-isis-af-redistribute-grouping;
          }
          container isis {
            tailf:info
              "ISO IS-IS";
            tailf:cli-compact-syntax;
            list isis-list {
              tailf:cli-drop-node-name;
              tailf:cli-suppress-mode;
              tailf:cli-delete-when-empty;
              tailf:cli-compact-syntax;
              tailf:cli-incomplete-command;
              key "from into";
              leaf from {
                type enumeration {
                  enum "level-1" {
                    tailf:info
                      "Inter-area routes from level-1";
                  }
                  enum "level-2" {
                    tailf:info
                      "Inter-area routes from level-2";
                  }
                }
              }
              leaf into {
                tailf:info
                  "from level-n into level-m";
                tailf:cli-expose-key-name;
                type enumeration {
                  enum "level-1" {
                    tailf:info
                      "Inter-area routes from level-1";
                  }
                  enum "level-2" {
                    tailf:info
                      "Inter-area routes from level-2";
                  }
                }
              }
              leaf distribute-list {
                tailf:info
                  "select routes";
                type string {
                  tailf:info
                    "WORD;;IPv6 prefix-list name";
                }
              }
              leaf route-map {
                tailf:info
                  "Route map for route matching";
                type string {
                  tailf:info
                    "WORD;;Name of the route-map";
                }
              }
            }
          }
          container nemo {
            tailf:info
              "Network Mobility (NEMO)";
            tailf:cli-compact-syntax;
            tailf:cli-delete-when-empty;
            uses ncs_rpc_notif_router-isis-af-redistribute-grouping;
          }
        }
      }
    }
  }

  grouping ncs_rpc_notif_router-lisp-database-mapping-grouping {
    list database-mapping {
      tailf:info
        "Configures Locator addresses for an ETR";
      tailf:cli-incomplete-command;
      tailf:cli-suppress-mode;
      tailf:cli-delete-when-empty;
      tailf:cli-compact-syntax;
      tailf:cli-sequence-commands;
      key "prefix";
      max-elements 100;
      leaf prefix {
        type union {
          type ios:ipv4-prefix {
            tailf:info
              "A.B.C.D/nn;;EID-prefix to advertise locators for (max 100 prefixes)";
          }
          type ios:ipv6-prefix {
            tailf:info
              "X:X:X:X::X/<0-128>;;EID-prefix to advertise locators for (max 100 prefixes)";
          }
        }
      }
      choice rloc-choice {
        leaf ipv4-address {
          tailf:cli-drop-node-name;
          tailf:cli-incomplete-command;
          type inet:ipv4-address {
            tailf:info
              "A.B.C.D;;IPv4 Address of loopback or other ETR interface";
          }
        }
        container IPv4-interface {
          tailf:info
            "Use IPv4 address of interface as locator";
          tailf:cli-flatten-container;
          tailf:cli-compact-syntax;
          tailf:cli-incomplete-command;
          uses ncs_rpc_notif_interface-name-grouping;
        }
        container IPv6-interface {
          tailf:info
            "Use IPv6 address of interface as locator";
          tailf:cli-flatten-container;
          tailf:cli-compact-syntax;
          tailf:cli-incomplete-command;
          uses ncs_rpc_notif_interface-name-grouping;
        }
        leaf ipv6-address {
          tailf:cli-drop-node-name;
          tailf:cli-incomplete-command;
          type inet:ipv6-address {
            tailf:info
              "X:X:X:X::X;;IPv6 Address of loopback or other ETR interface";
          }
        }
        leaf auto-discover-rlocs {
          tailf:info
            "Auto discover locators registered by other xTRs";
          tailf:cli-full-command;
          type empty;
        }
        leaf locator-set {
          tailf:info
            "Use locators defined by locator-set";
          tailf:cli-full-command;
          type string {
            tailf:info
              "WORD;;Existing locator set";
          }
        }
      }
      leaf priority {
        tailf:info
          "Configures which Locators from a set are preferred";
        tailf:cli-incomplete-command;
        type uint8 {
          tailf:info
            "<0-255>;;Lower priority Locator takes preference";
        }
      }
      leaf weight {
        tailf:info
          "Traffic load-spreading among Locators";
        type uint8 {
          tailf:info
            "<0-100>;;Relative weight of locator";
        }
      }
    }
  }

  grouping ncs_rpc_notif_router-lisp-af4-common-grouping {
    leaf map-request-source {
      tailf:info
        "Configures inner header source address in Map-Request message";
      type inet:ipv4-address {
        tailf:info
          "A.B.C.D;;IPv4 Source address of inner header in Map-Request message";
      }
    }
    container proxy-itr {
      tailf:info
        "Configures a LISP Proxy Ingress Tunnel Router (PITR)";
      tailf:cli-compact-syntax;
      tailf:cli-sequence-commands {
        tailf:cli-reset-siblings;
      }
      leaf ipv4-local-locator {
        tailf:cli-drop-node-name;
        tailf:cli-optional-in-sequence;
        type inet:ipv4-address {
          tailf:info
            "A.B.C.D;;IPv4 address in ITR-RLOC field of map-request";
        }
      }
      leaf ipv6-local-locator {
        tailf:cli-drop-node-name;
        type inet:ipv6-address {
          tailf:info
            "X:X:X:X::X;;IPv6 address in ITR-RLOC field of map-request";
        }
      }
    }
  }

  grouping ncs_rpc_notif_router-lisp-af6-common-grouping {
    leaf map-request-source {
      tailf:info
        "Configures inner header source address in Map-Request message";
      type inet:ipv6-address {
        tailf:info
          "X:X:X:X::X;;IPv6 Source address of inner header in Map-Request message";
      }
    }
    container proxy-itr {
      tailf:info
        "Configures a LISP Proxy Ingress Tunnel Router (PITR)";
      tailf:cli-compact-syntax;
      leaf ipv6-local-locator {
        tailf:cli-drop-node-name;
        tailf:cli-reset-container;
        type inet:ipv6-address {
          tailf:info
            "X:X:X:X::X;;IPv6 address in ITR-RLOC field of map-request";
        }
      }
      leaf ipv4-local-locator {
        tailf:cli-drop-node-name;
        type inet:ipv4-address {
          tailf:info
            "A.B.C.D;;IPv4 address in ITR-RLOC field of map-request";
        }
      }
    }
  }

  grouping ncs_rpc_notif_router-lisp-af-grouping {
    leaf map-resolver {
      tailf:info
        "Configures a LISP Map Resolver (MR)";
      type empty;
    }
    container map-resolver-conf {
      tailf:cli-drop-node-name;
      container map-resolver {
        tailf:info
          "Configures a LISP Map Resolver (MR)";
        tailf:cli-incomplete-command;
        tailf:cli-incomplete-no;
        container map-request {
          tailf:info
            "Map-Request processing options";
          container validate {
            tailf:info
              "Validation options";
            container source {
              tailf:info
                "Influence which source RLOCs map requests are accepted from";
              tailf:cli-compact-syntax;
              tailf:cli-reset-container;
              leaf registered {
                tailf:info
                  "...from RLOCs that register EID-prefixes in the same IID on a co-located MapServer";
                tailf:cli-optional-in-sequence;
                type empty;
              }
              container list {
                tailf:info
                  "Define allowed prefixes using an ip[v6] prefix list";
                choice list-choice {
                  leaf ipv4 {
                    tailf:info
                      "IPv4 prefixes";
                    type string {
                      tailf:info
                        "WORD;;IPv4 prefix-list name";
                    }
                  }
                  leaf ipv6 {
                    tailf:info
                      "IPv6 prefixes";
                    type string {
                      tailf:info
                        "WORD;;IPv6 prefix-list name";
                    }
                  }
                }
              }
            }
          }
        }
      }
    }
    container itr {
      tailf:info
        "Configures a LISP Ingress Tunnel Router (ITR)";
      tailf:cli-incomplete-command;
      tailf:cli-incomplete-no;
      list map-resolver {
        tailf:cli-suppress-mode;
        tailf:cli-delete-when-empty;
        key "address";
        leaf address {
          type union {
            type inet:ipv4-address {
              tailf:info
                "IPv4 Address of map resolver";
            }
            type inet:ipv6-address {
              tailf:info
                "IPv6 Address of map resolver";
            }
          }
        }
      }
      leaf enable {
        tailf:cli-drop-node-name;
        type empty;
      }
    }
    container etr {
      tailf:info
        "Configures a LISP Egress Tunnel Router (ETR)";
      tailf:cli-incomplete-command;
      tailf:cli-incomplete-no;
      list map-server {
        tailf:cli-suppress-mode;
        tailf:cli-delete-when-empty;
        tailf:cli-incomplete-command;
        tailf:cli-incomplete-no;
        key "address";
        leaf address {
          type union {
            type inet:ipv4-address {
              tailf:info
                "IPv4 Address of map server";
            }
            type inet:ipv6-address {
              tailf:info
                "IPv6 Address of map server";
            }
          }
        }
        container key {
          tailf:info
            "Authentication key used with map server";
          tailf:cli-compact-syntax;
          tailf:cli-sequence-commands;
          uses ncs_rpc_notif_crypto-key-grouping;
          leaf hash-function {
            tailf:info
              "Map-Register authentication type";
            type enumeration {
              enum "sha1" {
                tailf:info
                  "Use the SHA-1-96 hash function";
              }
              enum "sha2" {
                tailf:info
                  "Use the SHA-256-128 hash function";
              }
            }
          }
        }
      }
      leaf enable {
        tailf:cli-drop-node-name;
        type empty;
      }
    }
    leaf map-cache-limit {
      tailf:info
        "Configures maximum size of map-cache";
      type uint32 {
        tailf:info
          "<0-100000>;;Maximum number of map-cache entries";
        range "0..100000";
      }
    }
    container map-cache-persistent {
      tailf:info
        "Dump map-cache onto flash, making it persistent across reboots";
      tailf:meta-data "suppress-delete-error-invalid";
      presence "true";
      leaf interval {
        tailf:info
          "Interval in minutes of how often the map-cache is saved";
        type uint16 {
          tailf:info
            "<1-1440>;;Interval in minutes, default 60";
          range "1..1440";
        }
      }
    }
    container route-import {
      tailf:info
        "Import RIB routes by a routing protocol into LISP";
      container database {
        tailf:info
          "Use RIB routes to define local EID database entries";
        list static-list {
          tailf:cli-drop-node-name;
          tailf:cli-suppress-mode;
          tailf:cli-delete-when-empty;
          tailf:cli-compact-syntax;
          tailf:cli-sequence-commands {
            tailf:cli-reset-siblings;
          }
          tailf:cli-incomplete-command;
          key "protocol";
          leaf protocol {
            type enumeration {
              enum "connected" {
                tailf:info
                  "Connected";
              }
              enum "static" {
                tailf:info
                  "Static routes";
              }
              enum "rip" {
                tailf:info
                  "Routing Information Protocol (RIP)";
              }
            }
          }
          leaf route-map {
            tailf:info
              "Route map for route selection filtering";
            tailf:cli-optional-in-sequence;
            type string {
              tailf:info
                "WORD;;Route map name";
            }
          }
          leaf locator-set {
            tailf:info
              "Locator set to use with created database mapping entries";
            type string {
              tailf:info
                "WORD;;Locator set name";
            }
          }
        }
        list id-list {
          tailf:cli-drop-node-name;
          tailf:cli-suppress-mode;
          tailf:cli-delete-when-empty;
          tailf:cli-compact-syntax;
          tailf:cli-sequence-commands {
            tailf:cli-reset-siblings;
          }
          tailf:cli-incomplete-command;
          key "protocol id";
          leaf protocol {
            type enumeration {
              enum "bgp" {
                tailf:info
                  "Border Gateway Protocol (BGP)";
              }
              enum "eigrp" {
                tailf:info
                  "Enhanced Interior Gateway Routing Protocol (EIGRP)";
              }
              enum "isis" {
                tailf:info
                  "ISO IS-IS";
              }
              enum "ospf" {
                tailf:info
                  "Open Shortest Path First (OSPF)";
              }
              enum "ospfv3" {
                tailf:info
                  "OSPFv3";
              }
              enum "rip" {
                tailf:info
                  "Routing Information Protocol (RIP)";
              }
            }
          }
          leaf id {
            tailf:cli-disallow-value "route-map";
            type string {
              tailf:info
                "WORD;;Process id";
            }
          }
          leaf route-map {
            tailf:info
              "Route map for route selection filtering";
            tailf:cli-optional-in-sequence;
            type string {
              tailf:info
                "WORD;;Route map name";
            }
          }
          leaf locator-set {
            tailf:info
              "Locator set to use with created database mapping entries";
            type string {
              tailf:info
                "WORD;;Locator set name";
            }
          }
        }
      }
    }
    container route-export {
      tailf:info
        "Export routes into RIB from LISP";
      leaf site-registration {
        tailf:info
          "Export LISP site registrations to RIB";
        type empty;
      }
    }
    container map-cache {
      tailf:info
        "Address family specific map cache configuration";
      leaf site-registration {
        tailf:info
          "Install map cache to map request for site registrations";
        type empty;
      }
    }
    leaf proxy-etr {
      tailf:info
        "Configures a LISP Proxy Engress Tunnel Router (PETR)";
      tailf:cli-full-command;
      type empty;
    }
    list use-petr {
      tailf:info
        "Encapsulate to Proxy ETR when matching forward-native entry";
      tailf:cli-suppress-mode;
      tailf:cli-delete-when-empty;
      tailf:cli-compact-syntax;
      tailf:cli-sequence-commands;
      key "address";
      leaf address {
        type union {
          type inet:ipv4-address {
            tailf:info
              "A.B.C.D;;IPv4 locator address of PETR";
          }
          type inet:ipv6-address {
            tailf:info
              "X:X:X:X::X;;IPv6 locator address of PETR";
          }
        }
      }
      leaf priority {
        tailf:info
          "Configures which Locators from a set are preferred";
        tailf:cli-incomplete-command;
        type uint8 {
          tailf:info
            "<0-255>;;Lower priority Locator takes preference";
        }
      }
      leaf weight {
        tailf:info
          "Traffic load-spreading among Locators";
        type uint8 {
          tailf:info
            "<0-100>;;Relative weight of locator";
          range "0..100";
        }
      }
    }
    leaf map-server {
      tailf:info
        "Configures a LISP Map Server (MS)";
      type empty;
    }
  }

  grouping ncs_rpc_notif_router-lisp-eid-table-grouping {
    leaf instance-id {
      tailf:info
        "EID instance-ID";
      tailf:cli-hide-in-submode;
      type uint32 {
        tailf:info
          "<0-16777214>;;Instance-ID";
        range "0..16777214";
      }
    }
    list map-cache {
      tailf:cli-suppress-mode;
      tailf:cli-delete-when-empty;
      tailf:cli-compact-syntax;
      tailf:cli-sequence-commands;
      tailf:cli-incomplete-command;
      key "prefix";
      leaf prefix {
        type union {
          type ios:ipv4-prefix {
            tailf:info
              "A.B.C.D/nn;;IPv4 EID-prefix for RLOC static mapping";
          }
          type ios:ipv6-prefix {
            tailf:info
              "X:X:X:X::X/<0-128>;;IPv6 EID-prefix for RLOC static mapping";
          }
        }
      }
      choice map-cache-choice {
        case locator {
          leaf locator {
            tailf:cli-drop-node-name;
            tailf:cli-incomplete-command;
            type union {
              type inet:ipv4-address {
                tailf:info
                  "A.B.C.D;;IPv4 Address of loopback or other ETR interface";
              }
              type inet:ipv6-address {
                tailf:info
                  "X:X:X:X::X;;IPv6 Address of loopback or other ETR interface";
              }
            }
          }
          leaf priority {
            tailf:info
              "Lower priority Locator takes preference";
            tailf:cli-incomplete-command;
            type uint8 {
              tailf:info
                "<0-255>;;Lower priority Locator takes preference";
            }
          }
          leaf weight {
            tailf:info
              "Traffic load-spreading among Locators";
            type uint8 {
              tailf:info
                "<0-100>;;Relative weight of locator";
              range "0..100";
            }
          }
        }
        leaf map-request {
          tailf:info
            "Send Map-Request for LISP destination EID";
          tailf:cli-full-command;
          type empty;
        }
        leaf native-forward {
          tailf:info
            "Natively forward packets that match this map-cache entry";
          tailf:cli-full-command;
          type empty;
        }
        leaf drop {
          tailf:info
            "Drop packets that match this map-cache entry";
          tailf:cli-full-command;
          type empty;
        }
      }
    }
    uses ncs_rpc_notif_router-lisp-database-mapping-grouping;
    container loc-reach-algorithm {
      tailf:info
        "Configure locator reachability algorithm";
      leaf lsb-reports {
        tailf:info
          "Configure data packet LSB report handling";
        type enumeration {
          enum "ignore" {
            tailf:info
              "Ignore data packet LSB reports";
          }
        }
      }
      leaf rloc-probing {
        tailf:info
          "Probe high priority RLOCs with Map-Requests as last resort";
        type empty;
      }
    }
    container ipv4 {
      tailf:info
        "IPv4 address family";
      uses ncs_rpc_notif_router-lisp-af-grouping;
      uses ncs_rpc_notif_router-lisp-af4-common-grouping;
    }
    container ipv6 {
      tailf:info
        "IPv6 address family";
      uses ncs_rpc_notif_router-lisp-af-grouping;
      uses ncs_rpc_notif_router-lisp-af6-common-grouping;
    }
  }

  grouping ncs_rpc_notif_router-lisp-service-af-grouping {
    container eid-table {
      tailf:info
        "Bind an eid-table";
      leaf default {
        tailf:info
          "Default VRF";
        type empty;
      }
      leaf vrf {
        tailf:info
          "VRF name";
        tailf:cli-diff-dependency "/ios:vrf/definition" {
          tailf:xpath-root 3;
        }
        type string {
          tailf:info
            "WORD;;VRF name";
        }
      }
    }
    uses ncs_rpc_notif_router-lisp-database-mapping-grouping;
    leaf encapsulation {
      tailf:info
        "Select encapsulation type for data packets";
      type enumeration {
        enum "lisp" {
          tailf:info
            "Use LISP encapsulation for data packets";
        }
        enum "vxlan" {
          tailf:info
            "Use VXLAN encapsulation for data packets";
        }
      }
    }
  }

  grouping ncs_rpc_notif_router-lisp-service-grouping {
    container service {
      tailf:info
        "Select service type";
      container ipv4 {
        tailf:info
          "Select service type as IPv4";
        tailf:cli-add-mode;
        tailf:cli-mode-name "config-router-lisp-serv-ipv4";
        tailf:cli-exit-command "exit-service-ipv4" {
          tailf:info
            "Exit from LISP service-ipv4 configuration mode";
        }
        presence "true";
        uses ncs_rpc_notif_router-lisp-service-af-grouping;
        uses ncs_rpc_notif_router-lisp-af-grouping;
        uses ncs_rpc_notif_router-lisp-af4-common-grouping;
      }
      container ipv6 {
        tailf:info
          "Select service type as IPv6";
        tailf:cli-add-mode;
        tailf:cli-mode-name "config-router-lisp-serv-ipv6";
        tailf:cli-exit-command "exit-service-ipv6" {
          tailf:info
            "Exit from LISP service-ipv6 configuration mode";
        }
        presence "true";
        uses ncs_rpc_notif_router-lisp-service-af-grouping;
        uses ncs_rpc_notif_router-lisp-af-grouping;
        uses ncs_rpc_notif_router-lisp-af6-common-grouping;
      }
    }
  }

  grouping ncs_rpc_notif_router-lisp-grouping {
    container syslog {
      tailf:info
        "Configure syslog option";
      leaf verbose {
        tailf:info
          "Enable verbose syslog";
        type empty;
      }
      container session {
        tailf:info
          "Enable session syslog";
        leaf changes {
          tailf:info
            "Enable session change syslog";
          type empty;
        }
      }
    }
    container etr {
      tailf:info
        "Configures a LISP Egress Tunnel Router (ETR)";
      container map-server {
        tailf:info
          "Configures map server for ETR registration";
        container source-address {
          tailf:info
            "Configures map server source address";
          uses ncs_rpc_notif_interface-name-grouping;
        }
      }
    }
    container locator-table {
      tailf:info
        "Specify the RLOC table";
      choice locator-table-choice {
        leaf default {
          tailf:info
            "Default VRF";
          type empty;
        }
        leaf vrf {
          tailf:info
            "VRF name";
          type string {
            tailf:info
              "WORD;;VRF name";
          }
        }
      }
    }
    list locator-set {
      tailf:info
        "Configure a named locator set";
      tailf:cli-mode-name "config-router-lisp-locator-set";
      tailf:cli-full-command;
      key "name";
      leaf name {
        type string {
          tailf:info
            "Configure a named locator set";
        }
      }
      list IPv4-address {
        tailf:cli-drop-node-name;
        tailf:cli-suppress-mode;
        tailf:cli-delete-when-empty;
        tailf:cli-compact-syntax;
        tailf:cli-sequence-commands;
        tailf:cli-incomplete-command;
        key "name";
        leaf name {
          type inet:ipv4-address {
            tailf:info
              "A.B.C.D;;IP address";
          }
        }
        leaf priority {
          tailf:info
            "Configures which Locators from a set are preferred";
          tailf:cli-incomplete-command;
          type uint8 {
            tailf:info
              "<0-255>;;Lower priority Locator takes preference";
          }
        }
        leaf weight {
          tailf:info
            "Traffic load-spreading among Locators";
          type uint8 {
            tailf:info
              "<0-100>;;Relative weight of locator";
            range "0..100";
          }
        }
      }
      list IPv6-address {
        tailf:cli-drop-node-name;
        tailf:cli-suppress-mode;
        tailf:cli-delete-when-empty;
        tailf:cli-compact-syntax;
        tailf:cli-sequence-commands;
        tailf:cli-incomplete-command;
        key "name";
        leaf name {
          type inet:ipv6-address {
            tailf:info
              "X:X:X:X::X;;Address of loopback or other ETR interface";
          }
        }
        leaf priority {
          tailf:info
            "Configures which Locators from a set are preferred";
          tailf:cli-incomplete-command;
          type uint8 {
            tailf:info
              "<0-255>;;Lower priority Locator takes preference";
          }
        }
        leaf weight {
          tailf:info
            "Traffic load-spreading among Locators";
          type uint8 {
            tailf:info
              "<0-100>;;Relative weight of locator";
            range "0..100";
          }
        }
      }
      list IPv4-interface {
        tailf:info
          "Use IPv4 address of interface as locator";
        tailf:cli-suppress-mode;
        tailf:cli-delete-when-empty;
        tailf:cli-compact-syntax;
        tailf:cli-sequence-commands;
        tailf:cli-incomplete-command;
        key "name";
        leaf name {
          type string {
            tailf:info
              "WORD;;Interface name";
          }
        }
        leaf priority {
          tailf:info
            "Configures which Locators from a set are preferred";
          tailf:cli-incomplete-command;
          type uint8 {
            tailf:info
              "<0-255>;;Lower priority Locator takes preference";
          }
        }
        leaf weight {
          tailf:info
            "Traffic load-spreading among Locators";
          type uint8 {
            tailf:info
              "<0-100>;;Relative weight of locator";
            range "0..100";
          }
        }
      }
      list IPv6-interface {
        tailf:info
          "Use IPv6 address of interface as locator";
        tailf:cli-suppress-mode;
        tailf:cli-delete-when-empty;
        tailf:cli-compact-syntax;
        tailf:cli-sequence-commands;
        tailf:cli-incomplete-command;
        key "name";
        leaf name {
          type string {
            tailf:info
              "WORD;;Interface name";
          }
        }
        leaf priority {
          tailf:info
            "Configures which Locators from a set are preferred";
          tailf:cli-incomplete-command;
          type uint8 {
            tailf:info
              "<0-255>;;Lower priority Locator takes preference";
          }
        }
        leaf weight {
          tailf:info
            "Traffic load-spreading among Locators";
          type uint8 {
            tailf:info
              "<0-100>;;Relative weight of locator";
            range "0..100";
          }
        }
      }
      leaf auto-discover-rlocs {
        tailf:info
          "Auto discover locators registered by other xTRs";
        type empty;
      }
    }
    uses ncs_rpc_notif_router-lisp-service-grouping {
      refine "service/ipv4" {
        tailf:cli-diff-dependency "../../locator-set" {
          tailf:xpath-root 3;
        }
      }
      refine "service/ipv6" {
        tailf:cli-diff-dependency "../../locator-set" {
          tailf:xpath-root 3;
        }
      }
      refine "service/ipv4/etr/map-server/key/secret" {
        tailf:meta-data "secret-password" {
          tailf:meta-value "router lisp<NL><*>service ipv4<NL><*> ::  etr map-server <map-server> key <PASSWORD>";
        }
      }
      refine "service/ipv6/etr/map-server/key/secret" {
        tailf:meta-data "secret-password" {
          tailf:meta-value "router lisp<NL><*>service ipv6<NL><*> ::  etr map-server <map-server> key <PASSWORD>";
        }
      }
    }
    container map-request {
      tailf:info
        "Configure map-request handling";
      leaf itr-rlocs {
        tailf:info
          "Configure to use the specified RLOC set as ITR RLOC in map-request";
        type string {
          tailf:info
            "WORD;;Existing locator set";
        }
        tailf:non-strict-leafref {
          path "../../locator-set/name";
        }
      }
    }
    container eid-table {
      tailf:info
        "Configure an EID instance for a VRF";
      tailf:cli-diff-dependency "../locator-set" {
        tailf:xpath-root 3;
      }
      list default-vrf {
        tailf:cli-drop-node-name;
        tailf:cli-mode-name "config-router-lisp-eid-table";
        tailf:cli-explicit-exit;
        tailf:cli-incomplete-command;
        key "name";
        leaf name {
          type enumeration {
            enum "default" {
              tailf:info
                "Default VRF";
            }
          }
        }
        uses ncs_rpc_notif_router-lisp-eid-table-grouping;
      }
      list vrf {
        tailf:info
          "VRF name";
        tailf:cli-mode-name "config-router-lisp-eid-table";
        tailf:cli-explicit-exit;
        tailf:cli-incomplete-command;
        key "name";
        leaf name {
          tailf:cli-suppress-range;
          type string {
            tailf:info
              "WORD;;VRF name";
          }
        }
        uses ncs_rpc_notif_router-lisp-eid-table-grouping;
      }
    }
    container loc-reach-algorithm {
      tailf:info
        "Configure locator reachability algorithm";
      leaf rloc-probing {
        tailf:info
          "Probe high priority RLOCs with Map-Requests as last resort";
        type empty;
      }
    }
    list site {
      tailf:info
        "Configure a LISP site on a map server (MS)";
      tailf:cli-mode-name "config-router-lisp-site";
      tailf:cli-full-command;
      key "name";
      leaf name {
        type string {
          tailf:info
            "WORD;;The site name";
        }
      }
      leaf description {
        tailf:info
          "Provide a description string for the LISP site";
        tailf:cli-multi-value;
        tailf:cli-preformatted;
        tailf:cli-full-command;
        type string {
          tailf:info
            "LINE;;Site description";
        }
      }
      container authentication-key {
        tailf:info
          "Authentication key used by LISP site";
        tailf:cli-compact-syntax;
        tailf:cli-sequence-commands;
        uses ncs_rpc_notif_crypto-key-grouping;
      }
      list eid-prefix {
        tailf:info
          "Site EID address prefix";
        tailf:cli-suppress-mode;
        tailf:cli-delete-when-empty;
        tailf:cli-compact-syntax;
        key "prefix";
        leaf prefix {
          type union {
            type ios:ipv4-prefix {
              tailf:info
                "A.B.C.D/nn;;IPv4 EID prefix belonging to the SITE";
            }
            type ios:ipv6-prefix {
              tailf:info
                "X:X:X:X::X/<0-128>;;IPv6 EID prefix belonging to the SITE";
            }
          }
        }
        leaf route-tag {
          tailf:info
            "ALT RIB route tag for EID prefix";
          type uint32 {
            tailf:info
              "<0-4294967295>;;RIB route tag";
          }
        }
        leaf accept-more-specifics {
          tailf:info
            "Accept registrations for more specific EID prefixes";
          type empty;
        }
      }
      container eid-prefix-instance {
        tailf:cli-drop-node-name;
        list eid-prefix {
          tailf:cli-suppress-mode;
          tailf:cli-delete-when-empty;
          tailf:cli-compact-syntax;
          key "instance-id prefix";
          leaf instance-id {
            tailf:info
              "EID instance-ID";
            tailf:cli-expose-key-name;
            type uint32 {
              tailf:info
                "<1-16777214>;;Instance-ID";
              range "1..16777214";
            }
          }
          leaf prefix {
            type union {
              type ios:ipv4-prefix {
                tailf:info
                  "A.B.C.D/nn;;IPv4 EID prefix belonging to the SITE";
              }
              type ios:ipv6-prefix {
                tailf:info
                  "X:X:X:X::X/<0-128>;;IPv6 EID prefix belonging to the SITE";
              }
            }
          }
          leaf route-tag {
            tailf:info
              "ALT RIB route tag for EID prefix";
            type uint32 {
              tailf:info
                "<0-4294967295>;;RIB route tag";
            }
          }
          leaf accept-more-specifics {
            tailf:info
              "Accept registrations for more specific EID prefixes";
            type empty;
          }
        }
      }
      list allowed-locator {
        tailf:info
          "Locator from LISP site";
        tailf:cli-suppress-mode;
        tailf:cli-delete-when-empty;
        key "rloc";
        leaf rloc {
          type union {
            type inet:ipv4-address {
              tailf:info
                "A.B.C.D;;IPv4 locator allowed in registered locator-set";
            }
            type inet:ipv6-address {
              tailf:info
                "X:X:X:X::X;;IPv6 locator allowed in registered locator-set";
            }
          }
        }
      }
    }
    container ipv4 {
      tailf:info
        "IPv4 address family";
      uses ncs_rpc_notif_router-lisp-af-grouping {
        refine "map-cache-persistent" {
          tailf:cli-show-no;
        }
      }
      uses ncs_rpc_notif_router-lisp-af4-common-grouping;
    }
    container ipv6 {
      tailf:info
        "IPv6 address family";
      uses ncs_rpc_notif_router-lisp-af-grouping {
        refine "map-cache-persistent" {
          tailf:cli-show-no;
        }
      }
      uses ncs_rpc_notif_router-lisp-af6-common-grouping;
    }
    list instance-id {
      tailf:info
        "EID instance-ID";
      tailf:cli-mode-name "config-router-lisp-inst";
      tailf:cli-diff-dependency "../locator-set" {
        tailf:xpath-root 3;
      }
      tailf:cli-diff-dependency "/ios:vrf/definition" {
        tailf:xpath-root 3;
      }
      key "id";
      leaf id {
        tailf:cli-suppress-range;
        type uint32 {
          tailf:info
            "<0-16777214>;;Instance-ID";
          range "0..16777214";
        }
      }
      uses ncs_rpc_notif_router-lisp-service-grouping {
        refine "service/ipv4/etr/map-server/key/secret" {
          tailf:meta-data "secret-password" {
            tailf:meta-value "router lisp<NL><*> instance-id <instance-id><NL><*>  service ipv4<NL><*> ::  etr map-server <map-server> key <PASSWORD>";
          }
        }
        refine "service/ipv6/etr/map-server/key/secret" {
          tailf:meta-data "secret-password" {
            tailf:meta-value "router lisp<NL><*> instance-id <instance-id><NL><*>  service ipv6<NL><*> ::  etr map-server <map-server> key <PASSWORD>";
          }
        }
      }
    }
  }

  grouping ncs_rpc_notif_ip-nat-outside-source-grouping {
    leaf redundancy {
      tailf:cli-break-sequence-commands;
      tailf:info
        "NAT redundancy operation";
      type uint8 {
        tailf:info
          "<1-2>;IP redundancy ID";
      }
    }
    leaf mapping-id {
      when "../redundancy" {
        tailf:xpath-root 3;
        tailf:dependency "../redundancy";
      }
      tailf:info
        "Associate a mapping id to this mapping";
      type uint32 {
        tailf:info
          "<1-2147483647>;;Stateful NAT mapping id";
        range "1..2147483647";
      }
    }
    leaf add-route {
      tailf:info
        "Add a static route for outside local address";
      type empty;
    }
    leaf no-payload {
      tailf:info
        "No translation of embedded address/port in the payload";
      type empty;
    }
  }

  grouping ncs_rpc_notif_ip-nat-source-static-grouping {
    leaf redundancy {
      tailf:cli-break-sequence-commands;
      tailf:info
        "NAT redundancy operation";
      type union {
        type uint8 {
          tailf:info
            "<1-2>;IP redundancy ID";
        }
        type string {
          tailf:info
            "WORD;;IP redundancy name";
        }
      }
    }
    leaf mapping-id {
      when "../redundancy" {
        tailf:xpath-root 3;
        tailf:dependency "../redundancy";
      }
      tailf:info
        "Associate a mapping id to this mapping";
      type uint32 {
        tailf:info
          "<1-2147483647>;;Stateful NAT mapping id";
        range "1..2147483647";
      }
    }
    leaf extendable {
      tailf:info
        "Extend this translation when used";
      type empty;
    }
    leaf no-alias {
      tailf:info
        "Do not create an alias for the global address";
      type empty;
    }
    leaf no-payload {
      tailf:info
        "No translation of embedded address/port in the payload";
      type empty;
    }
    leaf add-route {
      tailf:info
        "Add a static route for outside local address";
      type empty;
    }
    leaf route-map {
      tailf:info
        "Specify route-map";
      type string {
        tailf:info
          "WORD;;Route-map name";
      }
    }
    leaf reversible {
      when "../route-map" {
        tailf:xpath-root 3;
        tailf:dependency "../route-map";
      }
      type empty;
    }
    leaf match-in-vrf {
      tailf:info
        "Match incoming vrf";
      type empty;
    }
    leaf forced {
      tailf:info
        "Delete this entry and its children, even if in use";
      type empty;
    }
    leaf overload {
      tailf:info
        "Overload an address translation";
      type empty;
    }
  }

  grouping ncs_rpc_notif_ip-nat-inside-options-grouping {
    leaf no-payload {
      tailf:cli-break-sequence-commands;
      tailf:info
        "No translation of embedded address/port in the payload";
      type empty;
    }
    leaf reversible {
      tailf:info
        "Allow out->in traffic";
      type empty;
    }
    leaf overload {
      tailf:info
        "Overload an address translation";
      type empty;
    }
    leaf oer {
      tailf:info
        "Use with vtemplate only. On new translation, if OER BR is UP, OER will select IP from outgoing Interface. All packets matching translation are forwarded over Interface for duration of translation.";
      type empty;
    }
  }

  grouping ncs_rpc_notif_ip-nat-inside-grouping {
    leaf pool {
      tailf:info
        "Name pool of global addresses";
      tailf:cli-optional-in-sequence;
      // NCS drop tailf-common:non-strict-leafref statement
      type string {
        tailf:info
          "WORD;;Pool name for global addresses";
      }
    }
    leaf redundancy {
      tailf:info
        "NAT redundancy operation";
      tailf:cli-optional-in-sequence;
      type uint8 {
        tailf:info
          "<1-2>;;IP redundancy ID";
        range "1..2";
      }
    }
    leaf mapping-id {
      tailf:info
        "Associate a mapping id to this mapping";
      tailf:cli-optional-in-sequence;
      type uint32 {
        tailf:info
          "<1-2147483647>;;Stateful NAT mapping id";
        range "1..2147483647";
      }
    }
    leaf interface {
      when "not(../pool)" {
        tailf:xpath-root 3;
        tailf:dependency "../pool";
      }
      tailf:info
        "Specify interface for global address";
      tailf:cli-optional-in-sequence;
      tailf:cli-diff-dependency "../../../../../../interface" {
        tailf:xpath-root 3;
      }
      type string {
        tailf:info
          "WORD;;Interface name";
      }
    }
  }

  grouping ncs_rpc_notif_ip-nat-inside-vrf-grouping {
    leaf pool {
      tailf:info
        "Name pool of global addresses";
      tailf:cli-prefix-key {
        tailf:cli-before-key 2;
      }
      tailf:cli-optional-in-sequence;
      type string {
        tailf:info
          "WORD;;Pool name for global addresses";
      }
      // NCS drop tailf-common:non-strict-leafref statement
    }
    leaf redundancy {
      tailf:info
        "NAT redundancy operation";
      tailf:cli-prefix-key {
        tailf:cli-before-key 2;
      }
      tailf:cli-optional-in-sequence;
      type uint8 {
        tailf:info
          "<1-2>;;IP redundancy ID";
        range "1..2";
      }
    }
    leaf mapping-id {
      tailf:info
        "Associate a mapping id to this mapping";
      tailf:cli-prefix-key {
        tailf:cli-before-key 2;
      }
      tailf:cli-optional-in-sequence;
      type uint32 {
        tailf:info
          "<1-2147483647>;;Stateful NAT mapping id";
        range "1..2147483647";
      }
    }
    leaf interface {
      when "not(../pool)" {
        tailf:xpath-root 3;
        tailf:dependency "../pool";
      }
      tailf:info
        "Specify interface for global address";
      tailf:cli-prefix-key {
        tailf:cli-before-key 2;
      }
      tailf:cli-optional-in-sequence;
      tailf:cli-diff-dependency "../../../../../../../interface" {
        tailf:xpath-root 3;
      }
      type string {
        tailf:info
          "WORD;;Interface name";
      }
    }
    leaf vrf {
      tailf:info
        "Specify vrf";
      tailf:cli-expose-key-name;
      type string {
        tailf:info
          "WORD;;vrf name";
      }
    }
    leaf match-in-vrf {
      tailf:info
        "Match incoming vrf";
      tailf:cli-optional-in-sequence;
      type empty;
    }
  }

  grouping ncs_rpc_notif_mobile-ip-spi-grouping {
    choice spi-type-choice {
      leaf hex {
        tailf:cli-drop-node-name;
        type string {
          tailf:info
            "<100-FFFFFFFF>;;SPI hex value";
        }
      }
      leaf decimal {
        tailf:info
          "decimal Security parameter index - bidirectional";
        type uint32 {
          tailf:info
            "<256-4294967295>;;SPI decimal value";
          range "256..4294967295";
        }
      }
    }
  }

  grouping ncs_rpc_notif_xconnect-interface-grouping {
    choice xconnect-choice {
      container xconnect {
        tailf:cli-add-mode;
        tailf:cli-mode-name "config-xconn";
        tailf:cli-compact-syntax;
        tailf:cli-sequence-commands;
        tailf:cli-diff-dependency "../encapsulation" {
          tailf:xpath-root 3;
        }
        leaf address {
          tailf:cli-drop-node-name;
          tailf:cli-incomplete-command;
          tailf:cli-hide-in-submode;
          type inet:ipv4-address {
            tailf:info
              "A.B.C.D;;IP address of peer";
          }
        }
        leaf vcid {
          tailf:cli-drop-node-name;
          tailf:cli-incomplete-command;
          tailf:cli-hide-in-submode;
          type uint32 {
            tailf:info
              "<1-4294967295>;;Enter VC ID value";
            range "1..4294967295";
          }
        }
        leaf encapsulation {
          tailf:info
            "Data encapsulation method";
          tailf:cli-hide-in-submode;
          type enumeration {
            enum "mpls" {
              tailf:info
                "Use MPLS encapsulation";
            }
            enum "l2tpv3" {
              tailf:info
                "Use L2TPv3 encapsulation";
            }
          }
        }
        leaf manual {
          tailf:info
            "Manually configure session parameters";
          tailf:cli-optional-in-sequence;
          tailf:cli-hide-in-submode;
          type empty;
        }
        leaf pw-class {
          tailf:info
            "Optional pseudowire-class to use for advanced configuration";
          tailf:cli-optional-in-sequence;
          tailf:cli-hide-in-submode;
          type string {
            tailf:info
              "WORD;;Pseudowire-class name";
          }
          // NCS drop tailf-common:non-strict-leafref statement
        }
        leaf sequencing {
          tailf:info
            "Configure sequencing options for xconnect";
          tailf:cli-full-command;
          tailf:cli-hide-in-submode;
          when "../encapsulation = 'l2tpv3'" {
            tailf:xpath-root 3;
            tailf:dependency "../encapsulation";
          }
          type enumeration {
            enum "both" {
              tailf:info
                "Transmit and receive sequence numbers";
            }
            enum "receive" {
              tailf:info
                "Receive sequence numbers";
            }
            enum "transmit" {
              tailf:info
                "Transmit sequence numbers";
            }
          }
        }
        container backup {
          tailf:cli-break-sequence-commands;
          tailf:info
            "Xconnect backup configuration commands";
          container peer {
            tailf:info
              "Backup pseudowire";
            tailf:cli-compact-syntax;
            tailf:cli-sequence-commands {
              tailf:cli-reset-siblings;
            }
            leaf peer-router-ip-addr {
              tailf:cli-drop-node-name;
              tailf:cli-incomplete-command;
              type inet:ipv4-address {
                tailf:info
                  "A.B.C.D;;IP address of peer";
              }
            }
            leaf vcid {
              tailf:cli-drop-node-name;
              type uint32 {
                tailf:info
                  "<1-4294967295>;;Enter VC ID value";
                range "1..4294967295";
              }
            }
            leaf pw-class {
              tailf:cli-optional-in-sequence;
              type string {
                tailf:info
                  "Optional Pseudowire-class to use for backup pseudowire";
              }
              // NCS drop tailf-common:non-strict-leafref statement
            }
            leaf priority {
              tailf:info
                "Optional priority to use for backup pseudowire.";
              type uint8 {
                tailf:info
                  "Peer priority";
                range "1..10";
              }
            }
          }
          container delay {
            tailf:info
              "Backup delay";
            tailf:cli-compact-syntax;
            tailf:cli-sequence-commands;
            leaf enable-delay {
              tailf:cli-drop-node-name;
              tailf:cli-incomplete-command;
              type uint8 {
                tailf:info
                  "<0-180>;;Enable delay";
                range "0..180";
              }
              default "0";
            }
            leaf disable-delay {
              tailf:cli-drop-node-name;
              type union {
                type uint8 {
                  tailf:info
                    "<0-180>;;Disable delay";
                  range "0..180";
                }
                type enumeration {
                  enum "never" {
                    tailf:info
                      "Disallow disable";
                  }
                }
              }
              default "0";
            }
          }
        }
        container mpls {
          tailf:info
            "MPLS manual configuration commands";
          leaf control-word {
            tailf:info
              "Include control-word in pseudowire packets";
            type empty;
          }
        }
        leaf mtu {
          tailf:info
            "set XCONNECT Maximum Transfer Unit";
          tailf:cli-full-command;
          type uint16 {
            tailf:info
              "<64-9100>;;per Xconnect MTU size in bytes";
            range "64..9100";
          }
        }
        container remote {
          tailf:info
            "Xconnect remote peer configuration commands";
          container link {
            tailf:info
              "Link information";
            container failure {
              tailf:info
                "Failure information";
              leaf notification {
                tailf:info
                  "Notify in case of remote link failure";
                tailf:cli-boolean-no;
                tailf:cli-full-command;
                type boolean;
                default "true";
              }
            }
          }
        }
      }
      container xconnect-pw-class {
        tailf:cli-drop-node-name;
        container xconnect {
          tailf:info
            "Xconnect commands";
          tailf:cli-compact-syntax;
          tailf:cli-sequence-commands;
          leaf address {
            tailf:cli-drop-node-name;
            tailf:cli-incomplete-command;
            type inet:ipv4-address {
              tailf:info
                "A.B.C.D;;IP address of peer";
            }
          }
          leaf vcid {
            tailf:cli-drop-node-name;
            tailf:cli-incomplete-command;
            type uint32 {
              tailf:info
                "<1-4294967295>;;Enter VC ID value";
              range "1..4294967295";
            }
          }
          leaf pw-class {
            tailf:info
              "Pseudowire-class to use for encapsulation and protocol configuration";
            tailf:cli-full-command;
            type string {
              tailf:info
                "WORD;;Pseudowire-class name";
            }
            // NCS drop tailf-common:non-strict-leafref statement
          }
        }
      }
      container xconnect-vfi {
        tailf:cli-drop-node-name;
        container xconnect {
          tailf:info
            "Xconnect commands";
          tailf:cli-incomplete-command;
          leaf vfi {
            tailf:info
              "connect to a virtual forwarding instance";
            tailf:cli-diff-dependency "/ios:l2/vfi" {
              tailf:xpath-root 3;
              tailf:cli-trigger-on-set;
            }
            // NCS drop tailf-common:non-strict-leafref statement
            type string {
              tailf:info
                "WORD;VFI name";
            }
          }
        }
      }
    }
  }

  grouping ncs_rpc_notif_xconnect-grouping {
    choice xconnect-choice {
      container xconnect {
        tailf:cli-break-sequence-commands;
        tailf:cli-add-mode;
        tailf:cli-mode-name "config-xconn";
        tailf:cli-compact-syntax;
        tailf:cli-sequence-commands;
        tailf:cli-incomplete-command;
        tailf:cli-delete-when-empty;
        presence "true";
        leaf address {
          tailf:cli-drop-node-name;
          tailf:cli-incomplete-command;
          tailf:cli-hide-in-submode;
          type inet:ipv4-address {
            tailf:info
              "A.B.C.D;;IP address of peer";
          }
        }
        leaf vcid {
          tailf:cli-drop-node-name;
          tailf:cli-incomplete-command;
          tailf:cli-hide-in-submode;
          type uint32 {
            tailf:info
              "<1-4294967295>;;Enter VC ID value";
            range "1..4294967295";
          }
        }
        leaf encapsulation {
          tailf:info
            "Data encapsulation method";
          tailf:cli-hide-in-submode;
          type enumeration {
            enum "mpls" {
              tailf:info
                "Use MPLS encapsulation";
            }
            enum "l2tpv3" {
              tailf:info
                "Use L2TPv3 encapsulation";
            }
          }
        }
        leaf manual {
          tailf:info
            "Manually configure session parameters";
          tailf:cli-optional-in-sequence;
          tailf:cli-hide-in-submode;
          type empty;
        }
        leaf pw-class {
          tailf:info
            "Optional pseudowire-class to use for advanced configuration";
          tailf:cli-optional-in-sequence;
          tailf:cli-hide-in-submode;
          // NCS drop tailf-common:non-strict-leafref statement
          type string {
            tailf:info
              "WORD;;Pseudowire-class name";
          }
        }
        leaf sequencing {
          when "../encapsulation = 'l2tpv3'" {
            tailf:xpath-root 3;
            tailf:dependency "../encapsulation";
          }
          tailf:info
            "Configure sequencing options for xconnect";
          tailf:cli-full-command;
          tailf:cli-hide-in-submode;
          type enumeration {
            enum "both" {
              tailf:info
                "Transmit and receive sequence numbers";
            }
            enum "receive" {
              tailf:info
                "Receive sequence numbers";
            }
            enum "transmit" {
              tailf:info
                "Transmit sequence numbers";
            }
          }
        }
        container backup {
          tailf:cli-break-sequence-commands;
          tailf:info
            "Xconnect backup configuration commands";
          container peer {
            tailf:info
              "Backup pseudowire";
            tailf:cli-compact-syntax;
            tailf:cli-sequence-commands {
              tailf:cli-reset-siblings;
            }
            leaf peer-router-ip-addr {
              tailf:cli-drop-node-name;
              tailf:cli-incomplete-command;
              type inet:ipv4-address {
                tailf:info
                  "A.B.C.D;;IP address of peer";
              }
            }
            leaf vcid {
              tailf:cli-drop-node-name;
              type uint32 {
                tailf:info
                  "<1-4294967295>;;Enter VC ID value";
                range "1..4294967295";
              }
            }
            leaf pw-class {
              tailf:cli-optional-in-sequence;
              // NCS drop tailf-common:non-strict-leafref statement
              type string {
                tailf:info
                  "Optional Pseudowire-class to use for backup pseudowire";
              }
            }
            leaf priority {
              tailf:info
                "Optional priority to use for backup pseudowire.";
              type uint8 {
                tailf:info
                  "Peer priority";
                range "1..10";
              }
            }
          }
          container delay {
            tailf:info
              "Backup delay";
            tailf:cli-compact-syntax;
            tailf:cli-sequence-commands;
            leaf enable-delay {
              tailf:cli-drop-node-name;
              tailf:cli-incomplete-command;
              type uint8 {
                tailf:info
                  "<0-180>;;Enable delay";
                range "0..180";
              }
              default "0";
            }
            leaf disable-delay {
              tailf:cli-drop-node-name;
              type union {
                type uint8 {
                  tailf:info
                    "<0-180>;;Disable delay";
                  range "0..180";
                }
                type enumeration {
                  enum "never" {
                    tailf:info
                      "Disallow disable";
                  }
                }
              }
              default "0";
            }
          }
        }
        container mpls {
          tailf:info
            "MPLS manual configuration commands";
          leaf control-word {
            tailf:info
              "Include control-word in pseudowire packets";
            type empty;
          }
        }
        leaf mtu {
          tailf:info
            "set XCONNECT Maximum Transfer Unit";
          tailf:cli-full-command;
          type uint16 {
            tailf:info
              "<64-9100>;;per Xconnect MTU size in bytes";
            range "64..9100";
          }
        }
        container remote {
          tailf:info
            "Xconnect remote peer configuration commands";
          container link {
            tailf:info
              "Link information";
            container failure {
              tailf:info
                "Failure information";
              leaf notification {
                tailf:info
                  "Notify in case of remote link failure";
                tailf:cli-boolean-no;
                tailf:cli-full-command;
                type boolean;
                default "true";
              }
            }
          }
        }
      }
      container xconnect-pw-class {
        tailf:cli-drop-node-name;
        container xconnect {
          tailf:info
            "Xconnect commands";
          tailf:cli-compact-syntax;
          tailf:cli-sequence-commands;
          tailf:cli-incomplete-command;
          leaf address {
            tailf:cli-drop-node-name;
            tailf:cli-incomplete-command;
            type inet:ipv4-address {
              tailf:info
                "A.B.C.D;;IP address of peer";
            }
          }
          leaf vcid {
            tailf:cli-drop-node-name;
            tailf:cli-incomplete-command;
            type uint32 {
              tailf:info
                "<1-4294967295>;;Enter VC ID value";
              range "1..4294967295";
            }
          }
          leaf pw-class {
            tailf:info
              "Pseudowire-class to use for encapsulation and protocol configuration";
            tailf:cli-full-command;
            // NCS drop tailf-common:non-strict-leafref statement
            type string {
              tailf:info
                "WORD;;Pseudowire-class name";
            }
          }
        }
      }
    }
  }

  grouping ncs_rpc_notif_ip-pim-grouping {
    container ssm {
      tailf:info
        "Configure Source Specific Multicast";
      choice ip-pim-ssm-choice {
        leaf default {
          tailf:info
            "Use 232/8 group range for SSM";
          type empty;
        }
        leaf range {
          tailf:info
            "ACL for group range to be used for SSM";
          type union {
            type uint16 {
              tailf:info
                "<1-99>;;Access list number";
              range "1..99";
            }
            type string {
              tailf:info
                "WORD;;IP named access list";
              pattern '[a-zA-Z].*';
            }
          }
        }
      }
    }
    container register-source {
      tailf:info
        "Source address for PIM Register";
      uses ncs_rpc_notif_interface-name-grouping;
    }
    leaf snooping {
      tailf:info
        "Global PIM Snooping enable for Catalyst Vlans";
      type empty;
    }
    list bsr-candidate {
      tailf:info
        "Candidate bootstrap router (candidate BSR)";
      tailf:cli-suppress-mode;
      tailf:cli-delete-when-empty;
      tailf:cli-compact-syntax;
      tailf:cli-sequence-commands;
      key "name";
      leaf name {
        type string {
          tailf:info
            "WORD;;Interface name";
        }
      }
      leaf hash-mask-length {
        tailf:cli-drop-node-name;
        type uint8 {
          tailf:info
            "<0-32>;;Hash Mask length for RP selection";
          range "0..32";
        }
      }
      leaf priority {
        tailf:cli-drop-node-name;
        type uint8 {
          tailf:info
            "<0-255>;;Priority value for candidate bootstrap router";
        }
      }
      leaf accept-rp-candidate {
        tailf:info
          "BSR RP candidate filter";
        type exp-ip-acl-type;
      }
    }
    container send-rp-announce {
      tailf:info
        "Auto-RP send RP announcement";
      tailf:cli-compact-syntax;
      container interface {
        tailf:cli-drop-node-name;
        tailf:cli-flatten-container;
        tailf:cli-compact-syntax;
        uses ncs_rpc_notif_interface-name-grouping;
      }
      leaf scope {
        tailf:info
          "RP announcement scope";
        type uint8 {
          tailf:info
            "<1-255>;;TTL of the RP announce packet ";
          range "1..255";
        }
      }
      leaf group-list {
        tailf:info
          "Group access-list";
        type union {
          type uint16 {
            tailf:info
              "<1-99>;;Access list number";
            range "1..99";
          }
          type string {
            tailf:info
              "WORD;;IP named access list";
            pattern '[a-zA-Z].*';
          }
        }
      }
      leaf interval {
        tailf:info
          "RP announcement interval";
        type uint16 {
          tailf:info
            "<1-16383>;;number of seconds";
          range "1..16383";
        }
      }
    }
    container send-rp-discovery {
      tailf:info
        "Auto-RP send RP discovery message (as RP-mapping agent)";
      container scope {
        tailf:info
          "Scope of the RP discovery packets";
        tailf:cli-compact-syntax;
        tailf:cli-sequence-commands {
          tailf:cli-reset-siblings;
        }
        leaf ttl {
          tailf:cli-drop-node-name;
          type uint8 {
            tailf:info
              "<1-255>;;TTL";
            range "1..255";
          }
        }
        leaf interval {
          tailf:info
            "RP discovery interval";
          type uint16 {
            tailf:info
              "<1-16383>;;number of seconds";
            range "1..16383";
          }
        }
      }
    }
    list rp-address {
      tailf:info
        "PIM RP-address (Rendezvous Point)";
      tailf:cli-suppress-mode;
      tailf:cli-delete-when-empty;
      tailf:cli-compact-syntax;
      tailf:cli-sequence-commands {
        tailf:cli-reset-siblings;
      }
      key "address";
      leaf address {
        type inet:ipv4-address {
          tailf:info
            "A.B.C.D;;IP address of Rendezvous-point for group";
        }
      }
      leaf access-list {
        tailf:cli-drop-node-name;
        tailf:cli-optional-in-sequence;
        tailf:cli-disallow-value "override";
        type std-acl-type;
      }
      leaf override {
        tailf:info
          "Overrides dynamically learnt RP mappings";
        type empty;
      }
    }
    list rp-candidate {
      tailf:info
        "To be a PIMv2 RP candidate";
      tailf:cli-suppress-mode;
      tailf:cli-delete-when-empty;
      tailf:cli-compact-syntax;
      key "name";
      leaf name {
        type string {
          tailf:info
            "WORD;;Interface name";
        }
      }
      leaf bidir {
        type empty;
      }
      leaf group-list {
        tailf:info
          "group-list";
        type union {
          type uint8 {
            tailf:info
              "<1-99>;;Access-list reference for group prefixes";
            range "1..99";
          }
          type string {
            tailf:info
              "WORD;;Named access list";
          }
        }
      }
      leaf interval {
        tailf:info
          "RP candidate advertisement interval";
        type uint16 {
          tailf:info
            "<1-16383>;;number of seconds";
          range "1..16383";
        }
      }
      leaf priority {
        tailf:info
          "RP candidate priority";
        type uint8 {
          tailf:info
            "<0-255>;;Priority value";
        }
      }
    }
    container spt-threshold {
      tailf:info
        "Source-tree switching threshold";
      leaf value {
        tailf:cli-drop-node-name;
        tailf:cli-full-command;
        type union {
          type enumeration {
            enum "infinity" {
              tailf:info
                "Never switch to source-tree";
            }
          }
          type uint32 {
            tailf:info
              "<0-4294967>;;Traffic rate in kilobits per second";
            range "0..4294967";
          }
        }
      }
      list group-list {
        tailf:cli-drop-node-name;
        tailf:cli-suppress-mode;
        tailf:cli-delete-when-empty;
        tailf:cli-compact-syntax;
        tailf:cli-sequence-commands;
        key "group-list";
        leaf value {
          tailf:cli-drop-node-name;
          tailf:cli-prefix-key;
          type union {
            type enumeration {
              enum "infinity" {
                tailf:info
                  "Never switch to source-tree";
              }
            }
            type uint32 {
              tailf:info
                "<0-4294967>;;Traffic rate in kilobits per second";
              range "0..4294967";
            }
          }
        }
        leaf group-list {
          tailf:info
            "Group address access-list";
          tailf:cli-expose-key-name;
          type std-acl-type;
        }
      }
    }
    choice autorp-choice {
      leaf autorp {
        tailf:info
          "Configure AutoRP global operations";
        tailf:cli-boolean-no;
        tailf:cli-full-command;
        type boolean;
        default "true";
      }
      container conf {
        tailf:cli-drop-node-name;
        container autorp {
          tailf:info
            "Configure AutoRP global operations";
          tailf:cli-incomplete-no;
          tailf:cli-incomplete-command;
          leaf listener {
            tailf:info
              "Allow AutoRP packets across sparse mode interface";
            type empty;
          }
        }
      }
    }
    leaf dm-fallback {
      tailf:info
        "Fallback group mode is Dense";
      tailf:cli-full-command;
      type empty;
    }
  }

  grouping ncs_rpc_notif_event-manager-applet-event-grouping {
    container none {
      tailf:info
        "Manually run policy event";
      leaf maxrun {
        tailf:info
          "Maximum runtime of applet";
        type uint32 {
          tailf:info
            "<0-31536000>;;Enter seconds[.milliseconds] value";
        }
      }
    }
    container snmp-notification {
      tailf:info
        "SNMP Notification Event";
      tailf:cli-compact-syntax;
      tailf:cli-reset-container;
      leaf oid {
        tailf:info
          "Object ID of data element";
        type string {
          tailf:info
            "WORD;;OID string";
        }
      }
      leaf oid-val {
        tailf:info
          "Comparison value";
        type string {
          tailf:info
            "WORD;;Comparision value";
        }
      }
      leaf op {
        tailf:info
          "Operator";
        type operator-type;
      }
      leaf src-ip-address {
        tailf:info
          "Source ip address";
        type union {
          type inet:ipv4-address {
            tailf:info
              "A.B.C.D;;Source ip address value";
          }
          type inet:ipv6-address {
            tailf:info
              "X:X:X:X::X;;Source ip address value";
          }
        }
      }
      leaf dest-ip-address {
        tailf:info
          "Destination ip address";
        type union {
          type inet:ipv4-address {
            tailf:info
              "A.B.C.D;;Destination ip address value";
          }
          type inet:ipv6-address {
            tailf:info
              "X:X:X:X::X;;Destination ip address value";
          }
        }
      }
    }
    container syslog {
      tailf:info
        "Syslog event";
      leaf pattern {
        tailf:info
          "Pattern match string for the entire message";
        type string {
          tailf:info
            "WORD;;Pattern match string for the entire message";
        }
      }
    }
    container cli {
      tailf:info
        "CLI event";
      tailf:cli-compact-syntax;
      container pattern {
        tailf:info
          "CLI command pattern match";
        tailf:cli-compact-syntax;
        tailf:cli-sequence-commands {
          tailf:cli-reset-siblings;
        }
        leaf regular-expression {
          tailf:cli-drop-node-name;
          type string {
            tailf:info
              "WORD;;Pattern match string";
          }
        }
        leaf sync {
          tailf:info
            "CLI and EEM policy execution sync or async";
          tailf:cli-optional-in-sequence;
          type enumeration {
            enum "no" {
              tailf:info
                "Policy and CLI will run asynchronously";
            }
            enum "yes" {
              tailf:info
                "Run policy and the result determines whether to run CLI";
            }
          }
        }
        leaf skip {
          tailf:info
            "Whether to skip CLI command execution";
          type enumeration {
            enum "no" {
              tailf:info
                "CLI command should be executed";
            }
            enum "yes" {
              tailf:info
                "CLI command should not be executed";
            }
          }
        }
      }
    }
    container track {
      tailf:info
        "Tracking object event";
      tailf:cli-compact-syntax;
      tailf:cli-sequence-commands;
      leaf object-number {
        tailf:cli-drop-node-name;
        type uint16 {
          tailf:info
            "<1-1000>;;Tracking object number";
        }
      }
      leaf state {
        tailf:info
          "State of tracking object";
        tailf:cli-optional-in-sequence;
        type enumeration {
          enum "any" {
            tailf:info
              "Any state";
          }
          enum "down" {
            tailf:info
              "Down state";
          }
          enum "up" {
            tailf:info
              "Up state";
          }
        }
      }
      leaf maxrun {
        tailf:info
          "Maximum runtime of applet";
        type uint32 {
          tailf:info
            "<0-31536000>;;Enter seconds[.milliseconds] value";
          range "0..31536000";
        }
      }
    }
    container neighbor-discovery {
      tailf:info
        "Neighbor Discovery event";
      tailf:cli-compact-syntax;
      container interface {
        tailf:info
          "Interface name";
        tailf:cli-flatten-container;
        leaf regexp {
          tailf:info
            "Specify a regexp for interfaces";
          type string {
            tailf:info
              "WORD;;interface name string";
          }
        }
      }
      leaf cdp {
        tailf:info
          "Monitor CDP events";
        type enumeration {
          enum "add" {
            tailf:info
              "Monitor only CDP add events";
          }
          enum "all" {
            tailf:info
              "Monitor all CDP events";
          }
          enum "delete" {
            tailf:info
              "Monitor only CDP delete events";
          }
          enum "update" {
            tailf:info
              "Monitor CDP add and update events";
          }
        }
      }
    }
    container timer {
      tailf:info
        "Timer event";
      tailf:cli-compact-syntax;
      tailf:cli-reset-container;
      leaf trigger {
        tailf:cli-drop-node-name;
        tailf:cli-incomplete-command;
        type enumeration {
          enum "absolute" {
            tailf:info
              "Absolute timer event";
          }
          enum "countdown" {
            tailf:info
              "Countdown timer event";
          }
          enum "watchdog" {
            tailf:info
              "Watchdog timer event";
          }
          enum "cron" {
            tailf:info
              "Cron timer event";
          }
        }
      }
      leaf name {
        tailf:info
          "Name of the timer";
        type string {
          tailf:info
            "WORD;;Timer name string";
        }
      }
      leaf cron-entry {
        tailf:info
          "Cron entry for cron timer";
        type string {
          tailf:info
            "WORD;;Cron entry string";
        }
      }
      leaf time {
        tailf:info
          "Time period for watchdog / countdown / absolute timer";
        type uint32 {
          tailf:info
            "<1-4294967295>;;Enter seconds[.milliseconds] value";
          range "1..4294967295";
        }
      }
      leaf maxrun {
        tailf:info
          "Maximum runtime of applet";
        type uint32 {
          tailf:info
            "<0-31536000>;;Enter seconds[.milliseconds] value";
          range "0..31536000";
        }
      }
      leaf ratelimit {
        tailf:info
          "Limit trigger to once per given time period";
        type uint32 {
          tailf:info
            "<0-31536000>;;Enter seconds[.milliseconds] value";
          range "0..31536000";
        }
      }
    }
    container snmp {
      tailf:info
        "SNMP event";
      tailf:cli-compact-syntax;
      tailf:cli-sequence-commands {
        tailf:cli-reset-siblings;
      }
      leaf oid {
        tailf:info
          "Object ID of data element";
        type string {
          tailf:info
            "WORD;;OID string";
        }
      }
      leaf get-type {
        tailf:cli-break-sequence-commands;
        tailf:info
          "Type of SNMP get operation";
        type enumeration {
          enum "exact" {
            tailf:info
              "Exact oid specified";
          }
          enum "next" {
            tailf:info
              "Next available oid";
          }
        }
      }
      leaf entry-op {
        tailf:info
          "Entry comparison operator";
        type operator-type;
      }
      leaf entry-val {
        tailf:info
          "Entry comparison value";
        type string {
          tailf:info
            "WORD;;Entry value";
        }
      }
      leaf exit-op {
        tailf:info
          "Exit operator";
        type operator-type;
      }
      leaf exit-val {
        tailf:info
          "Exit comparison value";
        type string {
          tailf:info
            "WORD;;Entry value";
        }
      }
      leaf poll-interval {
        tailf:info
          "Poll interval value";
        type uint32 {
          tailf:info
            "<0-4294967295>;;Enter seconds[.milliseconds] value";
        }
      }
    }
    container ipsla {
      tailf:info
        "IPSLA Event";
      tailf:cli-compact-syntax;
      tailf:cli-reset-container;
      leaf operation-id {
        tailf:info
          "IPSLA Operation ID";
        type uint32 {
          tailf:info
            "<1-2147483647>;;Operation ID value";
          range "1..2147483647";
        }
      }
      leaf reaction-type {
        tailf:info
          "IPSLA Reaction Type";
        type string {
          tailf:info
            "WORD;;Reaction Type";
        }
      }
      leaf maxrun {
        tailf:info
          "Maximum runtime of applet";
        type uint32 {
          tailf:info
            "<0-31536000>;;Enter seconds[.milliseconds] value";
          range "0..31536000";
        }
      }
    }
  }

  grouping ncs_rpc_notif_route-target-grouping {
    list export {
      tailf:info
        "Export Target-VPN community";
      tailf:cli-suppress-mode;
      tailf:cli-delete-when-empty;
      key "asn-ip";
      leaf asn-ip {
        type asn-ip-type {
          tailf:info
            "ASN:nn or IP-address:nn;;Target VPN Extended Community";
        }
      }
    }
    list import {
      tailf:info
        "Import Target-VPN community";
      tailf:cli-suppress-mode;
      tailf:cli-delete-when-empty;
      key "asn-ip";
      leaf asn-ip {
        type asn-ip-type {
          tailf:info
            "ASN:nn or IP-address:nn;;Target VPN Extended Community";
        }
      }
    }
  }

  grouping ncs_rpc_notif_vrf-definition-af-grouping {
    container export {
      tailf:info
        "VRF export";
      leaf map {
        tailf:info
          "Route-map based VRF export";
        type string {
          tailf:info
            "WORD;;Route-map reference";
        }
      }
    }
    container route-target {
      tailf:info
        "Specify Target VPN Extended Communities";
      uses ncs_rpc_notif_route-target-grouping;
    }
    container maximum {
      tailf:info
        "Set a limit";
      container routes {
        tailf:info
          "Maximum number of routes allowed in this routing table";
        tailf:cli-compact-syntax;
        tailf:cli-sequence-commands {
          tailf:cli-reset-siblings;
        }
        leaf limit {
          tailf:cli-drop-node-name;
          tailf:cli-incomplete-command;
          type uint32 {
            tailf:info
              "<1-4294967294>;;Maximum number of routes allowed";
          }
        }
        choice action {
          case a {
            leaf warning-only {
              tailf:info
                "Only give a warning message if limit is exceeded";
              type empty;
            }
          }
          case b {
            leaf warn-threshold {
              tailf:cli-drop-node-name;
              type uint8 {
                tailf:info
                  "<1-100>;;Threshold value (%) at which to generate a warning msg";
                range "1..100";
              }
            }
            leaf reinstall {
              tailf:info
                "Reinstall previous rejected route due to over maximum route limit";
              type uint8 {
                tailf:info
                  "<1-100>;;Threshold value (%) at which to reinstall routes back to VRF";
                range "1..100";
              }
            }
          }
        }
      }
    }
  }

  grouping ncs_rpc_notif_snmp-server-host-grouping {
    leaf message-type {
      tailf:cli-optional-in-sequence;
      tailf:cli-drop-node-name;
      tailf:cli-incomplete-command;
      type enumeration {
        enum "informs" {
          tailf:info
            "Send Inform messages to this host";
        }
        enum "traps" {
          tailf:info
            "Send Trap messages to this host";
        }
      }
      default "traps";
    }
    container version {
      tailf:info
        "SNMP version to use for notification messages";
      tailf:cli-optional-in-sequence;
      tailf:cli-flatten-container;
      tailf:cli-compact-syntax;
      tailf:cli-incomplete-command;
      leaf version {
        tailf:cli-drop-node-name;
        type enumeration {
          enum "1" {
            tailf:info
              "Use SNMPv1";
          }
          enum "2c" {
            tailf:info
              "Use SNMPv2c";
          }
          enum "3" {
            tailf:info
              "Use SNMPv3";
          }
        }
      }
      leaf security-level {
        tailf:cli-drop-node-name;
        when "../version = '3'" {
          tailf:xpath-root 3;
          tailf:dependency "../version";
        }
        type enumeration {
          enum "auth" {
            tailf:info
              "Use the SNMPv3 authNoPriv Security Level";
          }
          enum "noauth" {
            tailf:info
              "Use the SNMPv3 noAuthNoPriv Security Level";
          }
          enum "priv" {
            tailf:info
              "Use the SNMPv3 authPriv Security Level";
          }
        }
      }
    }
    leaf community-string {
      tailf:cli-drop-node-name;
      tailf:cli-disallow-value "version|informs|traps|vrf";
      type string {
        tailf:info
          "WORD;;SNMPv1/v2c community string or SNMPv3 user name";
      }
    }
    leaf-list allowed-traps {
      tailf:cli-drop-node-name;
      tailf:cli-flat-list-syntax {
        tailf:cli-replace-all;
      }
      type enumeration {
        enum "aaa_server" {
          tailf:info
            "Allow SNMP AAA traps";
        }
        enum "alarms" {
          tailf:info
            "Allow SNMP alarms traps";
        }
        enum "atm" {
          tailf:info
            "Allow SNMP atm traps";
        }
        enum "bfd" {
          tailf:info
            "Allow SNMP BFD traps";
        }
        enum "bgp" {
          tailf:info
            "Allow BGP state change traps";
        }
        enum "bstun" {
          tailf:info
            "Allow bstun event traps";
        }
        enum "bulkstat" {
          tailf:info
            "Allow Data-Collection-MIB traps";
        }
        enum "cable" {
          tailf:info
            "Allow SNMP cable traps";
        }
        enum "call-home" {
          tailf:info
            "Allow SNMP CISCO-CALLHOME-MIB traps";
        }
        enum "casa" {
          tailf:info
            "Allow casa event traps";
        }
        enum "cef" {
          tailf:info
            "Allows cef traps";
        }
        enum "cnpd" {
          tailf:info
            "Allow NBAR Protocol Discovery traps";
        }
        enum "config" {
          tailf:info
            "Allow SNMP config traps";
        }
        enum "config-copy" {
          tailf:info
            "Allow SNMP config-copy traps";
        }
        enum "config-ctid" {
          tailf:info
            "Allow SNMP config-ctid traps";
        }
        enum "cpu" {
          tailf:info
            "Allow cpu related traps";
        }
        enum "dhcp" {
          tailf:info
            "Allow dhcp traps";
        }
        enum "dlsw" {
          tailf:info
            "Allow dlsw traps";
        }
        enum "ds1" {
          tailf:info
            "Allow SNMP ds1 traps";
        }
        enum "dsp" {
          tailf:info
            "Allow SNMP DSP traps";
        }
        enum "dspu" {
          tailf:info
            "Allow dspu event traps";
        }
        enum "eigrp" {
          tailf:info
            "Allow SNMP EIGRP traps";
        }
        enum "entity" {
          tailf:info
            "Allow SNMP entity traps";
        }
        enum "entity-diag" {
          tailf:info
            "Allow SNMP CISCO-ENTITY-DIAG-MIB traps";
        }
        enum "entity-qfp" {
          tailf:info
            "Allow SNMP CISCO-ENTITY-QFP-MIB traps";
        }
        enum "entity-state" {
          tailf:info
            "Allow ENTITY-STATE-MIB traps";
        }
        enum "envmon" {
          tailf:info
            "Allow environmental monitor traps";
        }
        enum "ethernet-cfm" {
          tailf:info
            "Allow SNMP Ethernet CFM traps";
        }
        enum "evc" {
          tailf:info
            "Allow SNMP EVC traps";
        }
        enum "event-manager" {
          tailf:info
            "Allow SNMP Embedded Event Manager traps";
        }
        enum "firewall" {
          tailf:info
            "Allow SNMP Firewall traps";
        }
        enum "flash" {
          tailf:info
            "Allow SNMP FLASH traps";
        }
        enum "flowmon" {
          tailf:info
            "Allow SNMP flow monitor notifications";
        }
        enum "frame-relay" {
          tailf:info
            "Allow SNMP frame-relay traps";
        }
        enum "fru-ctrl" {
          tailf:info
            "Allow entity FRU control traps";
        }
        enum "gdoi" {
          tailf:info
            "Allows gdoi traps";
        }
        enum "hsrp" {
          tailf:info
            "Allow SNMP HSRP traps";
        }
        enum "iplocalpool" {
          tailf:info
            "Allow SNMP IP Local Pool traps";
        }
        enum "ipmulticast" {
          tailf:info
            "Allow SNMP ipmulticast traps";
        }
        enum "ipsec" {
          tailf:info
            "Allow SNMP IPsec traps";
        }
        enum "ipsla" {
          tailf:info
            "Allow SNMP Host IP SLA traps";
        }
        enum "isakmp" {
          tailf:info
            "Allow SNMP ISAKMP traps";
        }
        enum "isg-mib" {
          tailf:info
            "Allow SNMP isgmib traps";
        }
        enum "isis" {
          tailf:info
            "Allow IS-IS traps";
        }
        enum "l2tun-pseudowire-status" {
          tailf:info
            "Allow SNMP L2 pseudowire status traps";
        }
        enum "l2tun-session" {
          tailf:info
            "Allow SNMP L2 session traps";
        }
        enum "license" {
          tailf:info
            "Allow license traps";
        }
        enum "mac-notification" {
          tailf:info
            "Allow SNMP MAC Notification Traps";
        }
        enum "memory" {
          tailf:info
            "Allow SNMP Mempool traps";
        }
        enum "mpls-fast-reroute" {
          tailf:info
            "Allow SNMP MPLS traffic engineering fast reroute traps";
        }
        enum "mpls-ldp" {
          tailf:info
            "Allow SNMP MPLS label distribution protocol traps";
        }
        enum "mpls-traffic-eng" {
          tailf:info
            "Allow SNMP MPLS traffic engineering traps";
        }
        enum "mpls-vpn" {
          tailf:info
            "Allow SNMP MPLS Virtual Private Network traps";
        }
        enum "msdp" {
          tailf:info
            "Allow SNMP MSDP traps";
        }
        enum "mvpn" {
          tailf:info
            "Allow Multicast Virtual Private Network traps";
        }
        enum "nhrp" {
          tailf:info
            "Allow SNMP NHRP traps";
        }
        enum "ospf" {
          tailf:info
            "Allow OSPF traps";
        }
        enum "ospfv3" {
          tailf:info
            "Allow OSPFv3 traps";
        }
        enum "pfr" {
          tailf:info
            "Allow SNMP PfR traps";
        }
        enum "pim" {
          tailf:info
            "Allow SNMP PIM traps";
        }
        enum "pw-vc" {
          tailf:info
            "Allow SNMP Pseudowire VC traps";
        }
        enum "resource-policy" {
          tailf:info
            "Enable CISCO-ERM-MIB notifications";
        }
        enum "rf" {
          tailf:info
            "Allow all SNMP traps defined in CISCO-RF-MIB";
        }
        enum "rsrb" {
          tailf:info
            "Allow rsrb event traps";
        }
        enum "rsvp" {
          tailf:info
            "Allow RSVP flow change traps";
        }
        enum "sdlc" {
          tailf:info
            "Allow sdlc event traps";
        }
        enum "sdllc" {
          tailf:info
            "Allow sdllc event traps";
        }
        enum "snmp" {
          tailf:info
            "Allow SNMP-type notifications";
        }
        enum "sonet" {
          tailf:info
            "Allow SNMP SONET traps";
        }
        enum "srp" {
          tailf:info
            "Allow SRP protocol traps";
        }
        enum "stun" {
          tailf:info
            "Allow stun event traps";
        }
        enum "syslog" {
          tailf:info
            "Allow SNMP syslog traps";
        }
        enum "trustsec-sxp" {
          tailf:info
            "Allow SNMP CISCO-TRUSTSEC-SXP-MIB traps";
        }
        enum "tty" {
          tailf:info
            "Allow TCP connection traps";
        }
        enum "udp-port" {
          tailf:info
            "The notification host's UDP port number (default port 162)";
        }
        enum "voice" {
          tailf:info
            "Allow SNMP Voice traps";
        }
        enum "vrfmib" {
          tailf:info
            "Allow SNMP vrfmib traps";
        }
        enum "vrrp" {
          tailf:info
            "Allow SNMP vrrp traps";
        }
        enum "x25" {
          tailf:info
            "Allow x25 event traps";
        }
      }
    }
  }

  grouping ncs_rpc_notif_aaa-authentication-method-grouping {
    leaf cache {
      tailf:info
        "Use Cached-group";
      type aaa-group-type;
    }
    leaf group {
      tailf:info
        "Use Server-group";
      type aaa-group-type;
    }
    container group2 {
      when "../group" {
        tailf:xpath-root 3;
        tailf:dependency "../group";
      }
      tailf:cli-drop-node-name;
      tailf:cli-flatten-container;
      tailf:cli-compact-syntax;
      leaf group {
        tailf:info
          "Use Server-group 2";
        type aaa-group-type;
      }
    }
    leaf krb5 {
      tailf:info
        "Use Kerberos 5 authentication.";
      type empty;
    }
    choice local-choice {
      leaf local {
        tailf:info
          "Use local username authentication.";
        type empty;
      }
      leaf local-case {
        tailf:info
          "Use case-sensitive local username authentication.";
        type empty;
      }
    }
    leaf tacacsplus {
      tailf:alt-name "tacacs+";
      tailf:info
        "Use enable password for authentication.";
      type empty;
    }
    leaf line {
      tailf:info
        "Use line password for authentication.";
      type empty;
    }
    leaf enable {
      tailf:info
        "Use enable password for authentication.";
      type empty;
    }
    leaf none {
      tailf:info
        "NO authentication.";
      tailf:cli-full-command;
      type empty;
    }
  }

  grouping ncs_rpc_notif_aaa-authorization-method-grouping {
    leaf cache {
      tailf:info
        "Use Cached-group";
      type aaa-group-type;
    }
    leaf group {
      tailf:info
        "Use server-group.";
      type aaa-group-type;
    }
    leaf krb5-instance {
      tailf:info
        "Use Kerberos instance privilege maps.";
      type empty;
    }
    leaf tacacsplus {
      tailf:alt-name "tacacs+";
      tailf:info
        "Use enable password for authorization.";
      type empty;
    }
    leaf local {
      tailf:info
        "Use local database.";
      type empty;
    }
    leaf if-authenticated {
      tailf:info
        "Succeed if user has authenticated.";
      type empty;
    }
    leaf none {
      tailf:info
        "No authorization (always succeeds).";
      tailf:cli-full-command;
      type empty;
    }
  }

  grouping ncs_rpc_notif_aaa-accounting-method-grouping {
    leaf action-type {
      tailf:cli-drop-node-name;
      tailf:cli-no-value-on-delete;
      type enumeration {
        enum "none" {
          tailf:info
            "No accounting.";
        }
        enum "start-stop" {
          tailf:info
            "Record start and stop without waiting";
        }
        enum "stop-only" {
          tailf:info
            "Record stop when service terminates.";
        }
      }
    }
    leaf broadcast {
      tailf:info
        "Use Broadcast for Accounting";
      tailf:cli-no-name-on-delete;
      type empty;
    }
    leaf group {
      tailf:info
        "Use Server-group";
      tailf:cli-no-name-on-delete;
      tailf:cli-no-value-on-delete;
      type aaa-group-type;
    }
  }

  grouping ncs_rpc_notif_cable-modulation-profile-grouping {
    leaf fec-tbytes {
      tailf:cli-drop-node-name;
      tailf:cli-incomplete-command;
      type uint8 {
        tailf:info
          "<0-16>;;FEC tbytes";
      }
    }
    leaf fec-len {
      tailf:cli-drop-node-name;
      tailf:cli-incomplete-command;
      type uint8 {
        tailf:info
          "<16-253>;;FEC codeword length in k bytes";
      }
    }
    leaf burst-len {
      tailf:cli-drop-node-name;
      tailf:cli-incomplete-command;
      type uint8 {
        tailf:info
          "<0-255>;;max burst size in minislots";
      }
    }
    leaf guard-t {
      tailf:cli-drop-node-name;
      tailf:cli-incomplete-command;
      type uint8 {
        tailf:info
          "<0-255>;;guard time in symbols";
      }
    }
    leaf mod {
      tailf:cli-drop-node-name;
      tailf:cli-incomplete-command;
      type enumeration {
        enum "8qam" {
          tailf:info
            "8-QAM modulation";
        }
        enum "16qam" {
          tailf:info
            "16-QAM modulation";
        }
        enum "32qam" {
          tailf:info
            "32-QAM modulation";
        }
        enum "64qam" {
          tailf:info
            "64-QAM modulation";
        }
        enum "qpsk" {
          tailf:info
            "qpsk modulation";
        }
      }
    }
    leaf scrambler {
      tailf:cli-drop-node-name;
      tailf:cli-incomplete-command;
      type enumeration {
        enum "no-scrambler" {
          tailf:info
            "scrambler disabled";
        }
        enum "scrambler" {
          tailf:info
            "scrambler enabled";
        }
      }
    }
    leaf seed {
      when "../scrambler = 'scrambler'" {
        tailf:xpath-root 3;
        tailf:dependency "../scrambler";
      }
      tailf:cli-drop-node-name;
      tailf:cli-incomplete-command;
      type string {
        tailf:info
          "<0x0-0x7FFF>;;scrambler seed in hex";
      }
    }
    leaf diff {
      tailf:cli-drop-node-name;
      tailf:cli-incomplete-command;
      type enumeration {
        enum "diff" {
          tailf:info
            "diff encoding enabled";
        }
        enum "no-diff" {
          tailf:info
            "diff encoding disabled";
        }
      }
    }
    leaf pre-len {
      tailf:cli-drop-node-name;
      tailf:cli-incomplete-command;
      type uint16 {
        tailf:info
          "<4-1536>;;preamble length in bits";
      }
    }
    leaf last-cw {
      tailf:cli-drop-node-name;
      type enumeration {
        enum "fixed" {
          tailf:info
            "fixed codeword";
        }
        enum "shortened" {
          tailf:info
            "shortened codeword";
        }
      }
    }
    leaf preamble {
      tailf:cli-drop-node-name;
      type enumeration {
        enum "qpsk0" {
          tailf:info
            "QPSK0 preamble";
        }
        enum "qpsk1" {
          tailf:info
            "QPSK1 preamble";
        }
      }
    }
    leaf rs-interleave-depth {
      tailf:cli-drop-node-name;
      type uint8 {
        tailf:info
          "<0-114>;;RS interleave depth";
      }
    }
    leaf rs-interleave-block {
      tailf:cli-drop-node-name;
      type uint16 {
        tailf:info
          "<18-2048>;;RS interleave block size";
      }
    }
  }

  grouping ncs_rpc_notif_cable-modulation-profile-list-grouping {
    container request {
      tailf:info
        "Request Burst";
      tailf:cli-compact-syntax;
      tailf:cli-sequence-commands {
        tailf:cli-reset-all-siblings;
      }
      uses ncs_rpc_notif_cable-modulation-profile-grouping;
    }
    container initial {
      tailf:info
        "Initial Ranging Burst";
      tailf:cli-compact-syntax;
      tailf:cli-sequence-commands {
        tailf:cli-reset-all-siblings;
      }
      uses ncs_rpc_notif_cable-modulation-profile-grouping;
    }
    container station {
      tailf:info
        "Station Ranging Burst";
      tailf:cli-compact-syntax;
      tailf:cli-sequence-commands {
        tailf:cli-reset-all-siblings;
      }
      uses ncs_rpc_notif_cable-modulation-profile-grouping;
    }
    container short {
      tailf:info
        "Short Grant Burst";
      tailf:cli-compact-syntax;
      tailf:cli-sequence-commands {
        tailf:cli-reset-all-siblings;
      }
      uses ncs_rpc_notif_cable-modulation-profile-grouping;
    }
    container long {
      tailf:info
        "Long Grant Burst";
      tailf:cli-compact-syntax;
      tailf:cli-sequence-commands {
        tailf:cli-reset-all-siblings;
      }
      uses ncs_rpc_notif_cable-modulation-profile-grouping;
    }
    container a-short {
      tailf:info
        "Advanced Phy Short Grant Burst";
      tailf:cli-compact-syntax;
      tailf:cli-sequence-commands {
        tailf:cli-reset-all-siblings;
      }
      uses ncs_rpc_notif_cable-modulation-profile-grouping;
    }
    container a-long {
      tailf:info
        "Advanced Phy Long Grant Burst";
      tailf:cli-compact-syntax;
      tailf:cli-sequence-commands {
        tailf:cli-reset-all-siblings;
      }
      uses ncs_rpc_notif_cable-modulation-profile-grouping;
    }
    container a-ugs {
      tailf:info
        "Advanced Phy Unsolicited Grant Burst";
      tailf:cli-compact-syntax;
      tailf:cli-sequence-commands {
        tailf:cli-reset-all-siblings;
      }
      uses ncs_rpc_notif_cable-modulation-profile-grouping;
    }
  }

  grouping ncs_rpc_notif_cable-load-balance-docsis-group-grouping {
    leaf restricted {
      tailf:info
        "Set load balance group as restricted";
      type empty;
    }
    container downstream {
      tailf:info
        "Set downstream RF channels";
      list Modular-Cable {
        tailf:info
          "Modular cable";
        tailf:cli-allow-join-with-key;
        tailf:cli-suppress-mode;
        tailf:cli-delete-when-empty;
        key "name";
        leaf name {
          type string {
            tailf:info
              "<slot>/<card>/<port>;;Enter slot/subslot/bay";
          }
        }
        leaf rf-channel {
          tailf:info
            "RF channel";
          tailf:cli-multi-value;
          type string {
            tailf:info
              "<grouplist>;;List of port numbers and number ranges";
          }
        }
      }
      list Integrated-Cable {
        tailf:info
          "Integrated cable";
        tailf:cli-allow-join-with-key;
        tailf:cli-suppress-mode;
        tailf:cli-delete-when-empty;
        key "name";
        leaf name {
          type string {
            tailf:info
              "<slot>/<card>/<port>;;Enter slot/subslot/bay";
          }
        }
        leaf rf-channel {
          tailf:info
            "RF channel";
          tailf:cli-multi-value;
          type string {
            tailf:info
              "<grouplist>;;List of port numbers and number ranges";
          }
        }
      }
    }
    container upstream {
      tailf:info
        "Set upstream channels";
      list Upstream-Cable {
        tailf:info
          "Upstream Cable Controller";
        tailf:cli-allow-join-with-key;
        tailf:cli-suppress-mode;
        tailf:cli-delete-when-empty;
        key "name";
        leaf name {
          type string {
            tailf:info
              "<slot>/<card>/<port>;;Enter slot/subslot/bay";
          }
        }
        leaf us-channel {
          tailf:info
            "Associate physical us channels";
          tailf:cli-multi-value;
          type string {
            tailf:info
              "<grouplist>;;Physical us channel numbers and number ranges";
          }
        }
      }
      list Cable {
        tailf:info
          "CMTS interface";
        tailf:cli-allow-join-with-key;
        tailf:cli-suppress-mode;
        tailf:cli-delete-when-empty;
        key "name";
        leaf name {
          type string {
            tailf:info
              "<slot>/<card>/<port>;;Enter slot/subslot/bay";
          }
        }
        leaf upstream-list {
          tailf:cli-drop-node-name;
          type string {
            tailf:info
              "<grouplist>;;List of Ranges for upstream channels <0-7>";
          }
        }
      }
    }
    container method {
      tailf:info
        "Set load balancing type/method";
      container utilization {
        tailf:info
          "Interface utilization";
        presence "true";
      }
    }
    container threshold {
      tailf:info
        "Load balancing threshold in %";
      container load {
        tailf:info
          "Interface load threshold settings";
        leaf percentage {
          tailf:cli-drop-node-name;
          type uint8 {
            tailf:info
              "<1-100>;;Threshold value in %";
            range "1..100";
          }
        }
        leaf minimum {
          tailf:info
            "Set minimum number of modems/flows difference before loadbalancing starts";
          type uint8 {
            tailf:info
              "<1-100>;;Minimum number of modems/flows";
            range "1..100";
          }
        }
      }
      leaf stability {
        tailf:info
          "Threshold for stability detection";
        type uint8 {
          tailf:info
            "<0-100>;;Stability condition detection threshold in %";
          range "0..100";
        }
      }
    }
    leaf policy {
      tailf:info
        "Set load balancing policy";
      type enumeration {
        tailf:info
          "pure-ds-load;;Do not count US load when calculating DS utilization";
        enum "pcmm" {
          tailf:info
            "Enable balancing of modems with active PCMM service flows";
        }
        enum "pure-ds-load" {
          tailf:info
            "Do not count US load when calculating DS utilization";
        }
        enum "ugs" {
          tailf:info
            "Enable balancing of modems with active UGS service flows";
        }
        enum "us-across-ds" {
          tailf:info
            "Load balancing on US groups across DS, DS method will be ignored";
        }
      }
    }
    leaf interval {
      tailf:info
        "Set interface polling interval";
      type uint16 {
        tailf:info
          "<1-1000>;;Interface polling interval in seconds";
        range "1..1000";
      }
    }
    container init-tech-list {
      tailf:info
        "Set DCC initialization technique list";
      tailf:cli-compact-syntax;
      tailf:cli-sequence-commands {
        tailf:cli-reset-all-siblings;
      }
      leaf grouplist {
        tailf:cli-drop-node-name;
        type string {
          tailf:info
            "<grouplist> ";
        }
      }
      leaf ucc {
        tailf:info
          "Allow the use of UCC in upstream load balancing";
        type empty;
      }
    }
    leaf docsis-policy {
      tailf:info
        "Enter load balance group policy";
      type uint32 {
        tailf:info
          "<0-4294967295>;;Load balance group policy number";
        range "0..4294967295";
      }
    }
    list tag {
      tailf:info
        "Add tag to load balancing group";
      tailf:cli-suppress-mode;
      tailf:cli-delete-when-empty;
      key "name";
      leaf name {
        type string {
          tailf:info
            "WORD;;tag name";
        }
      }
    }
  }

  grouping ncs_rpc_notif_facility-alarm-grouping {
    container major {
      tailf:info
        "Major warning threshold";
      leaf temperature {
        tailf:cli-drop-node-name;
        type uint8 {
          tailf:info
            "<20-100>;;<##> threshold temperature (degrees C)";
          range "20..100";
        }
      }
    }
    container minor {
      tailf:info
        "Minor warning threshold";
      leaf temperature {
        tailf:cli-drop-node-name;
        type uint8 {
          tailf:info
            "<20-100>;;<##> threshold temperature (degrees C)";
          range "20..100";
        }
      }
    }
    container critical {
      tailf:info
        "Critical warning threshold";
      leaf exceed-action {
        tailf:info
          "Critical outlet temperature exceed action";
        tailf:cli-full-command;
        type enumeration {
          enum "shutdown" {
            tailf:info
              "Auto-shutdown when critical outlet temperature is exceeded";
          }
        }
      }
      leaf temperature {
        tailf:cli-drop-node-name;
        tailf:cli-full-command;
        type uint8 {
          tailf:info
            "<1-255>;;<##> threshold temperature (degrees C)";
          range "1..255";
        }
      }
    }
  }

  grouping ncs_rpc_notif_process-cpu-threshold-grouping {
    leaf rising {
      tailf:info
        "rising threshold";
      tailf:cli-incomplete-command;
      type uint8 {
        tailf:info
          "<1-100>";
        range "1..100";
      }
    }
    leaf interval {
      tailf:info
        "observation interval";
      type uint32 {
        tailf:info
          "<5-86400>";
        range "5..86400";
      }
    }
    leaf falling {
      tailf:info
        "falling threshold ";
      type uint8 {
        tailf:info
          "<1-100>";
        range "1..100";
      }
    }
    container falling-interval {
      tailf:cli-flatten-container;
      tailf:cli-drop-node-name;
      leaf interval {
        tailf:info
          "observation interval";
        type uint32 {
          tailf:info
            "<5-86400>";
          range "5..86400";
        }
      }
    }
  }

  grouping ncs_rpc_notif_cable-submgmt-default-filter-group-grouping {
    leaf upstream {
      tailf:info
        "Default Upstream Group";
      type uint8 {
        tailf:info
          "<1-254>;;Group ID";
        range "1..254";
      }
    }
    leaf downstream {
      tailf:info
        "Default Downstream Group";
      type uint8 {
        tailf:info
          "<1-254>;;Group ID";
        range "1..254";
      }
    }
  }

  grouping ncs_rpc_notif_storm-control-level-bps-pps-grouping {
    container level-bps-pps {
      tailf:cli-drop-node-name;
      container level {
        tailf:info
          "Set storm suppression level on this interface";
        choice level-choice {
          leaf bps {
            tailf:info
              "Enter suppression level in bits per second";
            type string {
              tailf:info
                "<0.0 - 10000000000.0>[k|m|g];;Enter rising threshold";
            }
          }
          leaf pps {
            tailf:info
              "Enter suppression level in packets per second";
            type string {
              tailf:info
                "<0.0 - 10000000000.0>[k|m|g];;Enter rising threshold";
            }
          }
        }
      }
    }
  }

  grouping ncs_rpc_notif_logging-host-grouping {
    leaf discriminator {
      tailf:info
        "Specify a message discriminator identifier for this logging session";
      type string {
        tailf:info
          "WORD;;Message discriminator identifier for this logging session (8 chars. max)";
      }
    }
    container session-id {
      tailf:info
        "Specify syslog message session ID tagging";
      tailf:cli-flatten-container;
      choice session-id-choice {
        leaf hostname {
          tailf:info
            "Include hostname in session ID tag";
          type empty;
        }
        leaf ipv4 {
          tailf:info
            "Include logging source IP address in session ID tag";
          type empty;
        }
        leaf ipv6 {
          tailf:info
            "Include logging source IPV6 address in session ID tag";
          type empty;
        }
        leaf string {
          tailf:info
            "Include custom string in session ID tag";
          type string {
            tailf:info
              "WORD;;Custom string in [s_id=\"custom_string\"] tag";
          }
        }
      }
    }
    leaf transport {
      tailf:info
        "Specify the transport protocol (default=UDP)";
      type enumeration {
        enum "beep" {
          tailf:info
            "Blocks Extensible Exchange Protocol";
        }
        enum "tcp" {
          tailf:info
            "Transport Control Protocol";
        }
        enum "udp" {
          tailf:info
            "User Datagram Protocol";
        }
      }
    }
    leaf port {
      tailf:info
        "Specify the transport port number";
      when "../transport" {
        tailf:xpath-root 3;
        tailf:dependency "../transport";
      }
      type uint16 {
        tailf:info
          "<1-65535>;;Port number";
        range "1..65535";
      }
    }
  }

  grouping ncs_rpc_notif_crypto-ikev2-profile-aaa-authorization-group-list {
    container list {
      tailf:info
        "AAA method list";
      tailf:cli-compact-syntax;
      tailf:cli-sequence-commands {
        tailf:cli-reset-siblings;
      }
      leaf list-name {
        tailf:cli-drop-node-name;
        type string {
          tailf:info
            "WORD;;AAA list name";
        }
      }
      leaf aaa-username {
        tailf:cli-break-sequence-commands;
        tailf:cli-drop-node-name;
        type string {
          tailf:info
            "WORD;;AAA username";
        }
      }
      leaf name-mangler {
        tailf:info
          "Specify the name-mangler to derive AAA username";
        tailf:non-strict-leafref {
          path "../../../../../../../../ikev2/name-mangler/name";
        }
        type string {
          tailf:info
            "WORD;;mangler name";
        }
      }
      container password {
        tailf:info
          "Specify the AAA password";
        tailf:cli-flatten-container;
        tailf:cli-compact-syntax;
        tailf:cli-sequence-commands;
        uses ncs_rpc_notif_crypto-key-grouping;
      }
    }
  }

  grouping ncs_rpc_notif_parameter-map-grouping {
    leaf alert {
      tailf:info
        "Turn on/off alert";
      type enumeration {
        enum "off" {
          tailf:info
            "Turn off alert";
        }
        enum "on" {
          tailf:info
            "Turn on alert";
        }
      }
    }
    leaf audit-trail {
      tailf:info
        "Turn on/off audit trail";
      type enumeration {
        enum "off" {
          tailf:info
            "Turn off audit trail";
        }
        enum "on" {
          tailf:info
            "Turn on audit trail";
        }
      }
    }
    leaf dns-timeout {
      tailf:info
        "Specify timeout for DNS";
      type uint32 {
        tailf:info
          "<1-2147483>;;Timeout in seconds";
        range "1..2147483";
      }
    }
    container icmp {
      tailf:info
        "Config timeout values for icmp";
      tailf:cli-compact-syntax;
      tailf:cli-sequence-commands {
        tailf:cli-reset-siblings;
      }
      leaf idle-time {
        tailf:info
          "Specify timeout for icmp";
        type uint32 {
          tailf:info
            "<1-2147483>;;Timeout in seconds";
          range "1..2147483";
        }
      }
      leaf ageout-time {
        tailf:info
          "Specify aggressive age-out time for icmp";
        type uint32 {
          tailf:info
            "<1-2147483>;;Timeout in seconds";
          range "1..2147483";
        }
      }
    }
    leaf max-destination {
      tailf:info
        "config maximum destination";
      type uint32 {
        tailf:info
          "<1-4294967295>;;maximum destination value";
        range "1..4294967295";
      }
    }
    container max-incomplete {
      tailf:info
        "Specify maximum number of incomplete connections before clamping";
      container half-open-sessions {
        tailf:cli-drop-node-name;
        tailf:cli-compact-syntax;
        tailf:cli-sequence-commands {
          tailf:cli-reset-siblings;
        }
        leaf number {
          tailf:cli-drop-node-name;
          type uint32 {
            tailf:info
              "<1-4294967295>;;half-open sessions";
            range "1..4294967295";
          }
        }
        container aggressive-aging {
          tailf:info
            "Aggressive Aging parameters";
          tailf:cli-flatten-container;
          tailf:cli-compact-syntax;
          tailf:cli-sequence-commands;
          leaf high {
            tailf:info
              "Specify the high watermark for aggressive-aging";
            type uint32 {
              tailf:info
                "<1-4294967295>;;High watermark in absolute values";
              range "1..4294967295";
            }
          }
          leaf low {
            tailf:info
              "Specify the low watermark for aggressive-aging";
            type uint32 {
              tailf:info
                "<1-4294967295>;;Low watermark in absolute values";
              range "1..4294967295";
            }
          }
        }
      }
      leaf high {
        tailf:info
          "Specify high-watermark for clamping";
        tailf:cli-full-command;
        type uint32 {
          tailf:info
            "<1-2147483647>;;Number of connections";
          range "1..2147483647";
        }
      }
      leaf low {
        tailf:info
          "Specify low-watermark for clamping";
        tailf:cli-full-command;
        type uint32 {
          tailf:info
            "<1-2147483647>;;Number of connections";
          range "1..2147483647";
        }
      }
    }
    container one-minute {
      tailf:info
        "Specify one-minute-sample watermarks for clamping";
      leaf high {
        tailf:info
          "Specify high-watermark for clamping";
        type uint32 {
          tailf:info
            "<1-2147483647>;;Number of connections";
          range "1..2147483647";
        }
      }
      leaf low {
        tailf:info
          "Specify low-watermark for clamping";
        type uint32 {
          tailf:info
            "<1-2147483647>;;Number of connections";
          range "1..2147483647";
        }
      }
    }
    container session {
      tailf:info
        "Configure session total";
      container total {
        tailf:cli-compact-syntax;
        tailf:cli-sequence-commands {
          tailf:cli-reset-siblings;
        }
        leaf number {
          tailf:cli-drop-node-name;
          type uint32 {
            tailf:info
              "<1-4294967295>;;session total number";
            range "1..4294967295";
          }
        }
        container aggressive-aging {
          tailf:info
            "Aggressive Aging parameters";
          tailf:cli-flatten-container;
          tailf:cli-compact-syntax;
          tailf:cli-sequence-commands;
          leaf high {
            tailf:info
              "Specify the high watermark for aggressive-aging";
            type uint32 {
              tailf:info
                "<1-4294967295>;;High watermark in absolute values";
              range "1..4294967295";
            }
          }
          leaf low {
            tailf:info
              "Specify the low watermark for aggressive-aging";
            type uint32 {
              tailf:info
                "<1-4294967295>;;Low watermark in absolute values";
              range "1..4294967295";
            }
          }
        }
      }
    }
    container sessions {
      tailf:info
        "Maximum number of inspect sessions";
      leaf maximum {
        tailf:info
          "Maximum sessions";
        type uint32 {
          tailf:info
            "<1-2147483647>;;Number of sessions";
          range "1..2147483647";
        }
      }
    }
    container tcp {
      tailf:info
        "Config timeout values for tcp connections";
      container finwait-time {
        tailf:info
          "Specify timeout for TCP connections after a FIN";
        tailf:cli-compact-syntax;
        tailf:cli-sequence-commands {
          tailf:cli-reset-siblings;
        }
        leaf seconds {
          tailf:cli-drop-node-name;
          type uint32 {
            tailf:info
              "<1-2147483>;;Timeout in seconds";
            range "1..2147483";
          }
        }
        leaf ageout-time {
          tailf:info
            "Specify aggressive age-out time for fin wait=time";
          type uint32 {
            tailf:info
              "<1-2147483>;;Timeout in seconds";
          }
        }
      }
      container idle-time {
        tailf:info
          "Specify idle timeout for tcp connections";
        tailf:cli-compact-syntax;
        tailf:cli-sequence-commands {
          tailf:cli-reset-siblings;
        }
        leaf seconds {
          tailf:cli-drop-node-name;
          type uint32 {
            tailf:info
              "<1-2147483>;;Timeout in seconds";
            range "1..2147483";
          }
        }
        leaf ageout-time {
          tailf:info
            "Specify aggressive age-out time for tcp";
          type uint32 {
            tailf:info
              "<1-2147483>;;Timeout in seconds";
            range "1..2147483";
          }
        }
      }
      container max-incomplete {
        tailf:info
          "Specify max half-open connection per host";
        leaf host {
          tailf:info
            "Specify max half-open connection per host";
          type uint32 {
            tailf:info
              "<1-4294967295>;;half-open sessions";
            range "1..4294967295";
          }
        }
      }
      container synwait-time {
        tailf:info
          "Specify timeout for TCP connections after a SYN and no";
        tailf:cli-compact-syntax;
        tailf:cli-sequence-commands {
          tailf:cli-reset-siblings;
        }
        leaf seconds {
          tailf:cli-drop-node-name;
          type uint32 {
            tailf:info
              "<1-2147483>;;Timeout in seconds";
            range "1..2147483";
          }
        }
        leaf ageout-time {
          tailf:info
            "Specify aggressive age-out time syn wait-time";
          type uint32 {
            tailf:info
              "<1-2147483>;;Timeout in seconds";
            range "1..2147483";
          }
        }
      }
      container syn-flood {
        tailf:info
          "syn-flood config";
        leaf limit {
          tailf:info
            "syn-flood limit";
          type uint32 {
            tailf:info
              "<1-4294967295>;;number of half-open connections that triggers SYN cookie";
            range "1..4294967295";
          }
        }
        container rate {
          tailf:info
            "maximum syn packet rate";
          leaf per-destination {
            tailf:info
              "per destination";
            type uint32 {
              tailf:info
                "<1-1000000000>;;maximum rate of TCP SYN packets";
              range "1..1000000000";
            }
          }
        }
      }
    }
    container udp {
      tailf:info
        "Config timeout values for udp flows";
      container idle-time {
        tailf:info
          "Specify idle timeout for udp";
        tailf:cli-compact-syntax;
        tailf:cli-sequence-commands {
          tailf:cli-reset-siblings;
        }
        leaf seconds {
          tailf:cli-drop-node-name;
          type uint32 {
            tailf:info
              "<1-2147483>;;Timeout in seconds";
            range "1..2147483";
          }
        }
        leaf ageout-time {
          tailf:info
            "Specify aggressive age-out time for udp";
          type uint32 {
            tailf:info
              "<1-2147483>;;Timeout in seconds";
            range "1..2147483";
          }
        }
      }
      container half-open {
        tailf:info
          "Config timeout values for udp half open flow";
        container idle-time {
          tailf:info
            "Specify idle timeout for udp half open";
          tailf:cli-compact-syntax;
          tailf:cli-sequence-commands {
            tailf:cli-reset-siblings;
          }
          leaf seconds {
            tailf:cli-drop-node-name;
            type uint32 {
              tailf:info
                "<1-2147483>;;Timeout in miliseconds";
              range "1..2147483";
            }
          }
          leaf ageout-time {
            tailf:info
              "Specify aggressive age-out time for udp half open";
            type uint32 {
              tailf:info
                "<1-2147483>;;Timeout in miliseconds";
              range "1..2147483";
            }
          }
        }
      }
    }
    container log {
      tailf:info
        "Inspect packet logging";
      leaf dropped-packets {
        tailf:info
          "log packets dropped by the firewall";
        type empty;
      }
    }
    container threat-detection {
      tailf:info
        "Configure Threat Detection";
      leaf basic-threat {
        tailf:info
          "Enable Threat Detection";
        tailf:cli-full-command;
        type empty;
      }
      container rate {
        tailf:info
          "Configure Threat Detection rate";
        container syn-attack {
          tailf:info
            "Configure Threat Detection rate for syn attack events";
          tailf:cli-compact-syntax;
          tailf:cli-sequence-commands {
            tailf:cli-reset-siblings;
          }
          leaf average-time-frame {
            tailf:info
              "Configure Threat Detection average time frame";
            tailf:cli-incomplete-command;
            type uint16 {
              tailf:info
                "<600-3600>;;average time frame in seconds";
              range "6..3600";
            }
          }
          leaf average-threshold {
            tailf:info
              "Configure Threat Detection average threshold";
            tailf:cli-incomplete-command;
            type uint32 {
              tailf:info
                "<1-4294967295>;;average threshold in pkts/sec";
              range "1..4294967295";
            }
          }
          leaf burst-threshold {
            tailf:info
              "Configure Threat Detection burst threshold";
            type uint32 {
              tailf:info
                "<1-1000000000>;;burst threshold in pkts/sec";
              range "1..1000000000";
            }
          }
        }
        container inspect-drop {
          tailf:info
            "Configure Threat Detection rate for firewall inspection based drop events";
          tailf:cli-compact-syntax;
          tailf:cli-sequence-commands {
            tailf:cli-reset-siblings;
          }
          leaf average-time-frame {
            tailf:info
              "Configure Threat Detection average time frame";
            tailf:cli-incomplete-command;
            type uint16 {
              tailf:info
                "<600-3600>;;average time frame in seconds";
              range "6..3600";
            }
          }
          leaf average-threshold {
            tailf:info
              "Configure Threat Detection average threshold";
            tailf:cli-incomplete-command;
            type uint32 {
              tailf:info
                "<1-4294967295>;;average threshold in pkts/sec";
              range "1..4294967295";
            }
          }
          leaf burst-threshold {
            tailf:info
              "Configure Threat Detection burst threshold";
            type uint32 {
              tailf:info
                "<1-1000000000>;;burst threshold in pkts/sec";
              range "1..1000000000";
            }
          }
        }
        container fw-drop {
          tailf:info
            "Configure Threat Detection rate for firewall drop events";
          tailf:cli-compact-syntax;
          tailf:cli-sequence-commands {
            tailf:cli-reset-siblings;
          }
          leaf average-time-frame {
            tailf:info
              "Configure Threat Detection average time frame";
            tailf:cli-incomplete-command;
            type uint16 {
              tailf:info
                "<600-3600>;;average time frame in seconds";
              range "6..3600";
            }
          }
          leaf average-threshold {
            tailf:info
              "Configure Threat Detection average threshold";
            tailf:cli-incomplete-command;
            type uint32 {
              tailf:info
                "<1-4294967295>;;average threshold in pkts/sec";
              range "1..4294967295";
            }
          }
          leaf burst-threshold {
            tailf:info
              "Configure Threat Detection burst threshold";
            type uint32 {
              tailf:info
                "<1-1000000000>;;burst threshold in pkts/sec";
              range "1..1000000000";
            }
          }
        }
      }
    }
    list vrf {
      tailf:info
        "vrf binding with parameter map";
      tailf:cli-suppress-mode;
      tailf:cli-delete-when-empty;
      tailf:cli-incomplete-command;
      key "vrf";
      leaf vrf {
        tailf:cli-diff-dependency "../../../../../ip/vrf" {
          tailf:xpath-root 3;
        }
        tailf:cli-diff-dependency "../../../../../vrf/definition" {
          tailf:xpath-root 3;
        }
        type string {
          tailf:info
            "WORD;;vrf name";
        }
      }
      leaf inspect {
        tailf:info
          "vrf binding with parameter map";
        tailf:non-strict-leafref {
          path "../../../inspect-vrf/name";
        }
        type string {
          tailf:info
            "WORD;;parameter-map name";
        }
      }
    }
  }

  grouping ncs_rpc_notif_dscp-value-0-7-grouping {
    leaf dscp-value0 {
      tailf:cli-drop-node-name;
      tailf:cli-prefix-key;
      type uint8 {
        tailf:info
          "<0-63>;;DSCP values separated by spaces (up to 8 values total)";
        range "0..63";
      }
    }
    leaf dscp-value1 {
      tailf:cli-drop-node-name;
      tailf:cli-optional-in-sequence;
      tailf:cli-prefix-key;
      type uint8 {
        tailf:info
          "<0-63>;;DSCP values separated by spaces (up to 8 values total)";
        range "0..63";
      }
    }
    leaf dscp-value2 {
      tailf:cli-drop-node-name;
      tailf:cli-optional-in-sequence;
      tailf:cli-prefix-key;
      type uint8 {
        tailf:info
          "<0-63>;;DSCP values separated by spaces (up to 8 values total)";
        range "0..63";
      }
    }
    leaf dscp-value3 {
      tailf:cli-drop-node-name;
      tailf:cli-optional-in-sequence;
      tailf:cli-prefix-key;
      type uint8 {
        tailf:info
          "<0-63>;;DSCP values separated by spaces (up to 8 values total)";
        range "0..63";
      }
    }
    leaf dscp-value4 {
      tailf:cli-drop-node-name;
      tailf:cli-optional-in-sequence;
      tailf:cli-prefix-key;
      type uint8 {
        tailf:info
          "<0-63>;;DSCP values separated by spaces (up to 8 values total)";
        range "0..63";
      }
    }
    leaf dscp-value5 {
      tailf:cli-drop-node-name;
      tailf:cli-optional-in-sequence;
      tailf:cli-prefix-key;
      type uint8 {
        tailf:info
          "<0-63>;;DSCP values separated by spaces (up to 8 values total)";
        range "0..63";
      }
    }
    leaf dscp-value6 {
      tailf:cli-drop-node-name;
      tailf:cli-optional-in-sequence;
      tailf:cli-prefix-key;
      type uint8 {
        tailf:info
          "<0-63>;;DSCP values separated by spaces (up to 8 values total)";
        range "0..63";
      }
    }
    leaf dscp-value7 {
      tailf:cli-drop-node-name;
      tailf:cli-optional-in-sequence;
      tailf:cli-prefix-key;
      type uint8 {
        tailf:info
          "<0-63>;;DSCP values separated by spaces (up to 8 values total)";
        range "0..63";
      }
    }
  }

  grouping ncs_rpc_notif_cos-value-0-7-grouping {
    leaf cos-value0 {
      tailf:cli-drop-node-name;
      tailf:cli-prefix-key;
      type uint8 {
        tailf:info
          "<0-7>;;CoS values separated by spaces (up to 8 values total)";
        range "0..7";
      }
    }
    leaf cos-value1 {
      tailf:cli-drop-node-name;
      tailf:cli-optional-in-sequence;
      tailf:cli-prefix-key;
      type uint8 {
        tailf:info
          "<0-7>;;CoS values separated by spaces (up to 8 values total)";
        range "0..7";
      }
    }
    leaf cos-value2 {
      tailf:cli-drop-node-name;
      tailf:cli-optional-in-sequence;
      tailf:cli-prefix-key;
      type uint8 {
        tailf:info
          "<0-7>;;CoS values separated by spaces (up to 8 values total)";
        range "0..7";
      }
    }
    leaf cos-value3 {
      tailf:cli-drop-node-name;
      tailf:cli-optional-in-sequence;
      tailf:cli-prefix-key;
      type uint8 {
        tailf:info
          "<0-7>;;CoS values separated by spaces (up to 8 values total)";
        range "0..7";
      }
    }
    leaf cos-value4 {
      tailf:cli-drop-node-name;
      tailf:cli-optional-in-sequence;
      tailf:cli-prefix-key;
      type uint8 {
        tailf:info
          "<0-7>;;CoS values separated by spaces (up to 8 values total)";
        range "0..7";
      }
    }
    leaf cos-value5 {
      tailf:cli-drop-node-name;
      tailf:cli-optional-in-sequence;
      tailf:cli-prefix-key;
      type uint8 {
        tailf:info
          "<0-7>;;CoS values separated by spaces (up to 8 values total)";
        range "0..7";
      }
    }
    leaf cos-value6 {
      tailf:cli-drop-node-name;
      tailf:cli-optional-in-sequence;
      tailf:cli-prefix-key;
      type uint8 {
        tailf:info
          "<0-7>;;CoS values separated by spaces (up to 8 values total)";
        range "0..7";
      }
    }
    leaf cos-value7 {
      tailf:cli-drop-node-name;
      tailf:cli-optional-in-sequence;
      tailf:cli-prefix-key;
      type uint8 {
        tailf:info
          "<0-7>;;CoS values separated by spaces (up to 8 values total)";
        range "0..7";
      }
    }
  }

  grouping ncs_rpc_notif_controller-modular-cable-rf-channel-grouping {
    list rf-channel {
      tailf:info
        "RF channel configuration";
      tailf:cli-suppress-mode;
      tailf:cli-delete-when-empty;
      key "rf-port";
      leaf rf-port {
        type uint8 {
          tailf:info
            "<0-23>;;RF channel number";
          range "0..23";
        }
      }
      leaf description {
        tailf:info
          "configure RF channel name/description";
        tailf:cli-multi-value;
        tailf:cli-preformatted;
        tailf:cli-full-command;
        type string {
          tailf:info
            "LINE;;Description of this RF channel that will be truncated to 80 characters";
        }
      }
      container cable {
        tailf:info
          "configure RF channel cable downstream channel-id";
        container downstream {
          tailf:info
            "configure RF channel cable downstream channel-id";
          leaf channel-id {
            tailf:info
              "configure RF channel cable downstream channel-id";
            type uint8 {
              tailf:info
                "<1-255>;;RF channel cable downstream channel-id";
              range "1..255";
            }
          }
        }
      }
      container frequency {
        tailf:info
          "configure RF channel frequency in Hz";
        tailf:cli-compact-syntax;
        tailf:cli-sequence-commands {
          tailf:cli-reset-siblings;
        }
        leaf freq {
          tailf:cli-drop-node-name;
          type union {
            type uint32 {
              tailf:info
                "<55000000-1050000000>;;Frequency in Hz";
              range "55000000..1050000000";
            }
            type enumeration {
              enum "none" {
                tailf:info
                  "No Frequency configured";
              }
            }
          }
        }
        leaf annex {
          tailf:info
            "ITU-T J.83 MPEG standard";
          tailf:cli-incomplete-command;
          type enumeration {
            enum "A" {
              tailf:info
                "Annex A, European Standard";
            }
            enum "B" {
              tailf:info
                "Annex B, North American Standard";
            }
          }
        }
        leaf modulation {
          tailf:info
            "configure RF channel modulation type";
          type enumeration {
            enum "256qam" {
              tailf:info
                "256-QAM modulation";
            }
            enum "64qam" {
              tailf:info
                "64-QAM modulation";
            }
          }
        }
        leaf interleave {
          tailf:info
            "Interleave depth";
          type enumeration {
            enum "128" {
              tailf:info
                "R/S Interleave I=128, J=1";
            }
            enum "16" {
              tailf:info
                "R/S Interleave I=16, J=8";
            }
            enum "32" {
              tailf:info
                "R/S Interleave I=32, J=4";
            }
            enum "64" {
              tailf:info
                "R/S Interleave I=64, J=2";
            }
            enum "8" {
              tailf:info
                "R/S Interleave I=8, J=16";
            }
            enum "12" {
              tailf:info
                "R/S Interleave I=12, J=17";
            }
          }
        }
      }
      container ip-address {
        tailf:info
          "configure IP address of edge QAM";
        tailf:cli-compact-syntax;
        tailf:cli-sequence-commands {
          tailf:cli-reset-siblings;
        }
        leaf ip-address {
          tailf:cli-drop-node-name;
          tailf:cli-incomplete-command;
          type inet:ipv4-address {
            tailf:info
              "A.B.C.D;;IP address of edge QAM";
          }
        }
        leaf mac-address {
          tailf:info
            "MAC address of edge QAM";
          tailf:cli-incomplete-command;
          type string {
            tailf:info
              "H.H.H;;MAC address of edge QAM";
          }
        }
        leaf depi-remote-id {
          tailf:info
            "configure DEPI session ID for edge QAM";
          type uint32 {
            tailf:info
              "<1-4294967295>;;DEPI remote ID";
            range "1..4294967295";
          }
        }
        leaf eqam-headroom {
          tailf:info
            "Headroom for Edge QAM channel";
          type uint8 {
            tailf:info
              "<0-28>;;EdgeQAM Headroom";
            range "0..28";
          }
        }
      }
      container network-delay {
        tailf:info
          "Delay through Converged Interconnect Network (CIN) to EQAM";
        choice network-delay-choice {
          leaf usec {
            tailf:cli-drop-node-name;
            type uint16 {
              tailf:info
                "<0-3000>;;CIN delay in usec";
              range "0..3000";
            }
          }
          container auto {
            tailf:info
              "CIN Delay via DLM Measurements";
            tailf:cli-delete-when-empty;
            presence "true";
            leaf sampling-rate {
              tailf:info
                "Sampling Rate for DLM Request";
              type uint16 {
                tailf:info
                  "<1-500>;;DLM Sampling Rate in sec";
                range "1..500";
              }
            }
          }
        }
      }
      container depi-tunnel {
        tailf:info
          "DEPI Data Session Configuration";
        tailf:cli-compact-syntax;
        tailf:cli-sequence-commands {
          tailf:cli-reset-siblings;
        }
        leaf depi-tunnel-name {
          tailf:cli-drop-node-name;
          tailf:cli-incomplete-command;
          type string {
            tailf:info
              "WORD;;depi-tunnel name";
          }
        }
        leaf tsid {
          tailf:info
            "tsid ";
          type uint16 {
            tailf:info
              "<0-65535>;;tsid value";
          }
        }
      }
      leaf rf-power {
        tailf:info
          "Set RF Power";
        type string {
          tailf:info
            "<1-100>;;dBmV (The format is XY.Z; by default, .Z is .0)";
        }
      }
      leaf rf-shutdown {
        tailf:cli-boolean-no;
        tailf:cli-full-command;
        type boolean;
        default "true";
      }
    }
  }

  grouping ncs_rpc_notif_controller-integrated-cable-rf-chan-grouping {
    leaf type {
      tailf:info
        "QAM Data Type";
      type enumeration {
        enum "DOCSIS" {
          tailf:info
            "DOCSIS";
        }
        enum "VIDEO" {
          tailf:info
            "VIDEO";
        }
      }
    }
    leaf frequency {
      tailf:info
        "RF Channel Frequency";
      type uint32 {
        tailf:info
          "<93000000-861000000>;;frequency";
        range "93000000..861000000";
      }
    }
    leaf rf-output {
      tailf:info
        "QAM Output Mode";
      type enumeration {
        enum "ALT" {
          tailf:info
            "ALT";
        }
        enum "CW" {
          tailf:info
            "CW";
        }
        enum "NORMAL" {
          tailf:info
            "NORMAL";
        }
        enum "PRBS" {
          tailf:info
            "PRBS";
        }
      }
    }
    leaf power-adjust {
      tailf:info
        "Channel Power Adjust";
      type string {
        tailf:info
          "WORD;;Power Adjust Range:  -8.0 -  0.0 dBmV";
      }
    }
    leaf qam-profile {
      tailf:info
        "QAM Profile Number";
      type uint8 {
        tailf:info
          "<0-31>;;qam profile number";
        range "0..31";
      }
    }
    leaf docsis-channel-id {
      tailf:info
        "Docsis Channel Id";
      type uint8 {
        tailf:info
          "<1-255>;;dcid";
        range "1..255";
      }
    }
  }

  grouping ncs_rpc_notif_object-group-service-protocol-match {
    choice match-choice {
      leaf eq {
        tailf:info
          "Match only packets on a given port number";
        tailf:cli-prefix-key {
          tailf:cli-before-key 1;
        }
        type empty;
      }
      leaf gt {
        tailf:info
          "Match only packets with a greater port number";
        tailf:cli-prefix-key {
          tailf:cli-before-key 1;
        }
        type empty;
      }
      leaf lt {
        tailf:info
          "Match only packets with a lower port number";
        tailf:cli-prefix-key {
          tailf:cli-before-key 1;
        }
        type empty;
      }
    }
  }

  grouping ncs_rpc_notif_arp-grouping {
    list arp-list {
      tailf:cli-drop-node-name;
      tailf:cli-suppress-mode;
      tailf:cli-delete-when-empty;
      tailf:cli-incomplete-command;
      tailf:cli-compact-syntax;
      tailf:cli-sequence-commands {
        tailf:cli-reset-all-siblings;
      }
      key "ip-address";
      leaf ip-address {
        type inet:ipv4-address {
          tailf:info
            "A.B.C.D;;IP address of ARP entry";
        }
      }
      leaf hardware-address {
        tailf:cli-drop-node-name;
        tailf:cli-incomplete-command;
        type string {
          tailf:info
            "H.H.H;;48-bit hardware address of ARP entry";
          pattern '[0-9a-fA-F]+\.[0-9a-fA-F]+\.[0-9a-fA-F]+';
        }
      }
      leaf type {
        tailf:cli-drop-node-name;
        type enumeration {
          enum "ARPA" {
            tailf:info
              "ARP type ARPA";
          }
          enum "SAP" {
            tailf:info
              "ARP type SAP (HP's ARP type)";
          }
          enum "SMDS" {
            tailf:info
              "ARP type SMDS";
          }
          enum "SNAP" {
            tailf:info
              "ARP type SNAP (FDDI and TokenRing)";
          }
          enum "SRP-A" {
            tailf:info
              "ARP type SRP (side A)";
          }
          enum "SRP-B" {
            tailf:info
              "ARP type SRP (side B)";
          }
        }
      }
      leaf alias {
        tailf:info
          "Respond to ARP requests for the IP address";
        type empty;
      }
    }
  }

  grouping ncs_rpc_notif_interface-encryption-mode-grouping {
    container mode {
      tailf:info
        "encryption mode";
      container ciphers {
        tailf:info
          "Optional data ciphers";
        tailf:cli-flatten-container;
        tailf:cli-compact-syntax;
        tailf:cli-reset-container;
        choice suite-choice {
          leaf ckip {
            tailf:info
              "Cisco Per packet key hashing";
            type empty;
          }
          leaf ckip-cmic {
            tailf:info
              "Cisco Per packet key hashing and MIC (MMH)";
            type empty;
          }
          leaf cmic {
            tailf:info
              "Cisco MIC (MMH)";
            type empty;
          }
          case a {
            leaf aes-ccm {
              tailf:info
                "WPA AES CCMP";
              type empty;
            }
            leaf tkip {
              tailf:info
                "WPA Temporal Key encryption";
              type empty;
            }
            leaf wep {
              tailf:cli-drop-node-name;
              type enumeration {
                enum "wep128" {
                  tailf:info
                    "128 bit key";
                }
                enum "wep40" {
                  tailf:info
                    "40 bit key";
                }
              }
            }
          }
        }
      }
    }
  }

  grouping ncs_rpc_notif_ip-ssh-algorithm-grouping {
    container algorithm {
      tailf:info
        "Configure different algorithms used in SSH";
      leaf-list mac {
        tailf:info
          "MAC algorithms advertised to other party";
        tailf:cli-replace-all;
        tailf:cli-flat-list-syntax;
        type enumeration {
          enum "hmac-sha1" {
            tailf:info
              "HMAC-SHA1 (digest length = key length = 160 bits)";
          }
          enum "hmac-sha1-96" {
            tailf:info
              "HMAC-SHA1-96 (digest length = 96 bits, key length = 160 bits)";
          }
        }
      }
      leaf-list encryption {
        tailf:info
          "Encrytption algorithms advertised to other party";
        tailf:cli-replace-all;
        tailf:cli-flat-list-syntax;
        ordered-by user;
        type enumeration {
          enum "3des-cbc" {
            tailf:info
              "Three-key 3DES in CBC mode";
          }
          enum "aes128-cbc" {
            tailf:info
              "AES with 128-bit key in CBC mode";
          }
          enum "aes128-ctr" {
            tailf:info
              "AES with 128-bit key in CTR mode";
          }
          enum "aes192-cbc" {
            tailf:info
              "AES with 192-bit key in CBC mode";
          }
          enum "aes192-ctr" {
            tailf:info
              "AES with 192-bit key in CTR mode";
          }
          enum "aes256-cbc" {
            tailf:info
              "AES with 256-bit key in CBC mode";
          }
          enum "aes256-ctr" {
            tailf:info
              "AES with 256-bit key in CTR mode";
          }
        }
      }
    }
  }

  grouping ncs_rpc_notif_bandwidth-remaining-account-grouping {
    container account {
      tailf:info
        "Overhead Accounting";
      tailf:cli-flatten-container;
      tailf:cli-compact-syntax;
      tailf:cli-sequence-commands;
      choice account-choice {
        case dot1q-qing {
          leaf bras-side {
            tailf:cli-drop-node-name;
            tailf:cli-incomplete-command;
            type enumeration {
              enum "dot1q" {
                tailf:info
                  "dot1Q at BRAS side";
              }
              enum "qinq" {
                tailf:info
                  "QinQ at BRAS side";
              }
            }
          }
          leaf aal {
            tailf:cli-drop-node-name;
            tailf:cli-incomplete-command;
            type enumeration {
              enum "aal3" {
                tailf:info
                  "AAL3 Layer type";
              }
              enum "aal5" {
                tailf:info
                  "AAL5 Layer type";
              }
            }
          }
          leaf subscriber-encapsulation {
            tailf:cli-drop-node-name;
            type enumeration {
              enum "mux-1483routed" {
                tailf:info
                  "Mux 1483 Routed";
              }
              enum "mux-dot1q-rbe" {
                tailf:info
                  "Mux Bridging and dot1Q encapsulation";
              }
              enum "mux-pppoa" {
                tailf:info
                  "Mux PPPoA";
              }
              enum "mux-rbe" {
                tailf:info
                  "Mux Bridging encapsulation";
              }
              enum "snap-1483routed" {
                tailf:info
                  "Snap 1483 Routed";
              }
              enum "snap-dot1q-rbe" {
                tailf:info
                  "Snap Bridging and dot1Q encapsulation";
              }
              enum "snap-pppoa" {
                tailf:info
                  "Snap PPPoA encapsulation";
              }
              enum "snap-rbe" {
                tailf:info
                  "Snap Bridging encapsulation";
              }
            }
          }
        }
        leaf user-defined {
          tailf:info
            "Offset Size";
          type int8 {
            tailf:info
              "<-63 - 63>;;User Defined size";
          }
        }
      }
    }
  }

  grouping ncs_rpc_notif_result-type-method-grouping {
    leaf authoritative {
      tailf:info
        "failure type";
      type empty;
    }
    leaf agent-not-found {
      tailf:info
        "agent not found type";
      type empty;
    }
    leaf none {
      tailf:info
        "no type";
      type empty;
    }
    leaf success {
      tailf:info
        "success type";
      type empty;
    }
    leaf method-timeout {
      tailf:info
        "method_timeout type";
      type empty;
    }
    leaf aaa-timeout {
      tailf:info
        "aaa timeout type";
      type empty;
    }
  }

  grouping ncs_rpc_notif_interface-vrrp-grouping {
    leaf description {
      tailf:info
        "Group specific description";
      tailf:cli-multi-value;
      tailf:cli-preformatted;
      tailf:cli-full-command;
      type string {
        tailf:info
          "LINE;;Up to 80 characters describing this group";
        length "1..80";
      }
    }
    container vrrs {
      tailf:info
        "VRRS related commands";
      list leader {
        tailf:info
          "Name of VRRS Tag for which this group is the leader";
        tailf:cli-suppress-mode;
        tailf:cli-delete-when-empty;
        key "name";
        leaf name {
          type string {
            tailf:info
              "WORD;;Name of the VRRS Tag to lead";
          }
        }
      }
    }
    container preempt {
      tailf:info
        "Enable preemption of lower priority Master";
      container delay {
        tailf:info
          "Wait before preempting";
        leaf minimum {
          tailf:info
            "Delay at least this long";
          type uint16 {
            tailf:info
              "<0-3600>;;Seconds to delay";
            range "0..3600";
          }
        }
      }
    }
    leaf priority {
      tailf:info
        "Priority of this VRRP group";
      tailf:cli-full-command;
      type uint8 {
        tailf:info
          "<1-254>;;Priority level";
        range "1..254";
      }
    }
    container timers {
      tailf:info
        "Set the VRRP timers";
      container advertise {
        tailf:info
          "Set the Advertisement timer";
        leaf seconds {
          tailf:cli-drop-node-name;
          type uint8 {
            tailf:info
              "<1-255>;;Advertisement interval in seconds";
            range "1..255";
          }
        }
        leaf msec {
          tailf:info
            "Specify time in milliseconds";
          tailf:cli-full-command;
          type uint16 {
            tailf:info
              "<50-999>;;Advertisement interval in milliseconds";
            range "50..999";
          }
        }
      }
      leaf learn {
        tailf:info
          "Learn timer values from current Master";
        tailf:cli-full-command;
        type empty;
      }
    }
    list track {
      tailf:info
        "Event Tracking";
      tailf:cli-suppress-mode;
      tailf:cli-delete-when-empty;
      key "name";
      leaf name {
        type uint16 {
          tailf:info
            "<1-1000>;;Tracked object";
          range "1..1000";
        }
      }
      leaf decrement {
        tailf:info
          "Priority decrement";
        tailf:cli-full-command;
        type uint16 {
          tailf:info
            "<1-255>;;Decrement value";
        }
      }
    }
    leaf shutdown {
      tailf:info
        "Disable VRRP Configuration";
      tailf:cli-full-command;
      type empty;
    }
  }

  grouping ncs_rpc_notif_router-bgp-aggregate-address-content-grouping {
    leaf as-set {
      tailf:cli-break-sequence-commands;
      tailf:info
        "Generate AS set path information";
      type empty;
    }
    leaf summary-only {
      tailf:info
        "Filter more specific routes from updates";
      type empty;
    }
    leaf attribute-map {
      tailf:info
        "Set attributes of aggregate";
      type string {
        tailf:info
          "WORD;;Route map for parameter control";
      }
    }
    leaf advertise-map {
      tailf:info
        "Set condition to advertise attribute";
      type string {
        tailf:info
          "WORD;;Route map to control attribute advertisement";
      }
    }
    leaf suppress-map {
      tailf:info
        "Conditionally filter more specific routes from updates";
      type string {
        tailf:info
          "WORD;;Route map for suppression";
      }
    }
    leaf as-override {
      tailf:info
        "Override matching AS-number while sending update";
      type empty;
    }
    leaf route-map {
      tailf:info
        "Set parameters of aggregate";
      type string {
        tailf:info
          "WORD;;Route map for parameter control";
      }
    }
  }

  grouping ncs_rpc_notif_ip-dns-view-grouping {
    container domain {
      tailf:info
        "Configure DNS Resolver parameters";
      container name-server {
        tailf:info
          "Domain server IP address";
        list vrf {
          tailf:cli-suppress-mode;
          tailf:cli-delete-when-empty;
          tailf:cli-show-long-obu-diffs;
          ordered-by user;
          key "name address";
          leaf name {
            type string {
              tailf:info
                "WORD;;VRF name";
            }
          }
          leaf address {
            type union {
              type inet:ipv4-address {
                tailf:info
                  "A.B.C.D;;Host IP address";
              }
              type inet:ipv6-address {
                tailf:info
                  "X:X:X:X::X;;Host IPv6 address";
              }
            }
          }
        }
        container interface {
          tailf:info
            "Gather dynamically from interface address acquisition";
          uses ncs_rpc_notif_interface-name-grouping;
        }
      }
    }
    container dns {
      tailf:info
        "Configure DNS Server parameters";
      container forwarding {
        tailf:info
          "Configure DNS server forwarding";
        container source-interface {
          tailf:info
            "Specify source address when forwarding queries";
          uses ncs_rpc_notif_interface-name-grouping;
        }
      }
    }
  }

  grouping ncs_rpc_notif_ip-igmp-grouping {
    leaf limit {
      tailf:info
        "IGMP limit";
      tailf:cli-full-command;
      type uint16 {
        tailf:info
          "<1-64000>;;Max Allowed State";
        range "1..64000";
      }
    }
    container ssm-map {
      tailf:info
        "SSM mapping commands";
      leaf enable {
        tailf:info
          "Enable SSM group to source mapping";
        type empty;
      }
      container query {
        tailf:info
          "Which database should we query for the source";
        leaf dns {
          tailf:info
            "Use DNS for source lookup";
          tailf:cli-boolean-no;
          type boolean;
          default "true";
        }
      }
      container static {
        tailf:info
          "SSM static group to source mapping";
        tailf:cli-compact-syntax;
        tailf:cli-sequence-commands;
        leaf access-list {
          tailf:cli-drop-node-name;
          tailf:cli-incomplete-command;
          type std-ip-acl-type;
        }
        leaf source-address {
          tailf:cli-drop-node-name;
          type inet:ipv4-address {
            tailf:info
              "A.B.C.D;;SSM source address";
          }
        }
      }
    }
  }

  grouping ncs_rpc_notif_ip-msdp-grouping {
    list peer {
      tailf:info
        "Configure an MSDP peer";
      tailf:cli-suppress-mode;
      tailf:cli-delete-when-empty;
      key "address";
      leaf address {
        type inet:host {
          tailf:info
            "Hostname or A.B.C.D;;Peer name or address";
        }
      }
      container connect-source {
        tailf:info
          "Configure source address used for MSDP connection";
        tailf:cli-flatten-container;
        tailf:cli-compact-syntax;
        uses ncs_rpc_notif_interface-name-grouping;
      }
      leaf remote-as {
        tailf:info
          "Configured AS number";
        type uint16 {
          tailf:info
            "<1-65535>;;Autonomous System Number";
          range "1..65535";
        }
      }
    }
    list description {
      tailf:info
        "Peer specific description";
      tailf:cli-suppress-mode;
      tailf:cli-delete-when-empty;
      tailf:cli-diff-dependency "../peer" {
        tailf:xpath-root 3;
      }
      key "address";
      leaf address {
        type inet:host {
          tailf:info
            "Hostname or A.B.C.D;;Peer name or address";
        }
      }
      leaf text {
        tailf:cli-drop-node-name;
        tailf:cli-multi-value;
        tailf:cli-preformatted;
        type string {
          tailf:info
            "LINE;;Up to 80 characters describing this pee";
        }
      }
    }
    list keepalive {
      tailf:info
        "Configure keepalive parameters for a peer";
      tailf:cli-suppress-mode;
      tailf:cli-delete-when-empty;
      tailf:cli-compact-syntax;
      tailf:cli-incomplete-command;
      tailf:cli-diff-dependency "../peer" {
        tailf:xpath-root 3;
      }
      key "address";
      leaf address {
        type inet:host {
          tailf:info
            "Hostname or A.B.C.D;;Peer name or address";
        }
      }
      leaf keepalive-interval {
        tailf:cli-drop-node-name;
        type uint8 {
          tailf:info
            "<1-60>;;Send keepalive period in seconds";
          range "1..60";
        }
      }
      leaf hold-time-interval {
        tailf:cli-drop-node-name;
        type uint8 {
          tailf:info
            "<1-75>;;Maximum time in seconds to wait for a message";
          range "1..75";
        }
      }
    }
    list sa-filter {
      tailf:info
        "Filter SA messages from peer";
      tailf:cli-suppress-mode;
      tailf:cli-delete-when-empty;
      tailf:cli-compact-syntax;
      tailf:cli-incomplete-command;
      tailf:cli-diff-dependency "../peer" {
        tailf:xpath-root 3;
      }
      key "direction address";
      leaf direction {
        type enumeration {
          enum "in" {
            tailf:info
              "Enable incoming SA filtering";
          }
          enum "out" {
            tailf:info
              "Enable outgoing SA filtering";
          }
        }
      }
      leaf address {
        type inet:host {
          tailf:info
            "Hostname or A.B.C.D;;Peer name or address";
        }
      }
      choice list-choice {
        leaf list {
          tailf:info
            "Access-list";
          type ext-acl-type;
        }
        leaf route-map {
          tailf:info
            "Route-map";
          type string {
            tailf:info
              "WORD;;route-map name";
          }
        }
        leaf rp-list {
          tailf:info
            "Access-list for originating RP";
          type union {
            type uint16 {
              tailf:info
                "<1-99>;;Standard IP access list";
              range "1..99";
            }
            type string {
              tailf:info
                "WORD;;IP Named Standard Access list";
            }
          }
        }
        leaf rp-route-map {
          tailf:info
            "Route-map for originating RP";
          type string {
            tailf:info
              "WORD;;Route-map reference";
          }
        }
      }
    }
    container originator-id {
      tailf:info
        "Configure MSDP Originator ID";
      uses ncs_rpc_notif_interface-name-grouping;
    }
    container mesh-group {
      tailf:info
        "Configure an MSDP mesh-group";
      tailf:cli-compact-syntax;
      tailf:cli-sequence-commands {
        tailf:cli-reset-siblings;
      }
      leaf name {
        tailf:cli-drop-node-name;
        type string {
          tailf:info
            "WORD;;Name of mesh-group";
        }
      }
      leaf address {
        tailf:cli-drop-node-name;
        type inet:host {
          tailf:info
            "Hostname or A.B.C.D;;Peer name or address";
        }
      }
    }
  }

  grouping ncs_rpc_notif_if-srv-encapsulation-dot1q-grouping {
    leaf-list id {
      tailf:cli-drop-node-name;
      tailf:cli-range-list-syntax;
      tailf:cli-replace-all;
      type union {
        type uint16 {
          tailf:info
            "<1-4094>;;VLAN id";
          range "1..4094";
        }
        type enumeration {
          enum "any" {
            tailf:info
              "For all VLANS [1-4094]";
          }
        }
      }
    }
    leaf second-dot1q {
      tailf:cli-break-sequence-commands;
      tailf:info
        "inner 802.1Q Virtual LAN or C-VLAN";
      type union {
        type uint16 {
          tailf:info
            "<1-4094>;;VLAN id";
          range "1..4094";
        }
        type enumeration {
          enum "any" {
            tailf:info
              "For all VLANS [1-4094]";
          }
        }
      }
    }
    leaf cos {
      tailf:info
        "cos Vlan";
      type uint8 {
        tailf:info
          "<0-7>;;cos values";
        range "0..7";
      }
    }
    leaf etype {
      tailf:info
        "payload ethertype after Vlan Field";
      type enumeration {
        enum "ipv4" {
          tailf:info
            "IPv4";
        }
        enum "ipv6" {
          tailf:info
            "IPv6";
        }
        enum "pppoe-all" {
          tailf:info
            "PPPoE ALL";
        }
        enum "pppoe-discovery" {
          tailf:info
            "PPPoE Discovery Stage";
        }
        enum "pppoe-session" {
          tailf:info
            "PPPoE Session Stage";
        }
      }
    }
  }

  grouping ncs_rpc_notif_ip-wccp-grouping {
    container source-interface {
      tailf:info
        "Set source interface for Router ID";
      uses ncs_rpc_notif_interface-name-grouping;
    }
    container web-cache {
      tailf:info
        "Standard web caching service";
      presence "true";
    }
    list wccp-list {
      tailf:cli-drop-node-name;
      tailf:cli-suppress-mode;
      tailf:cli-delete-when-empty;
      tailf:cli-compact-syntax;
      tailf:cli-sequence-commands {
        tailf:cli-reset-all-siblings;
      }
      key "service-number";
      leaf service-number {
        tailf:cli-suppress-range;
        type uint8 {
          tailf:info
            "<0-254>;;Dynamically defined service identifier number";
          range "0..254";
        }
      }
      leaf redirect-list {
        tailf:cli-break-sequence-commands;
        tailf:info
          "Set the access-list used to permit redirection";
        type exp-ip-acl-type;
      }
      leaf group-list {
        tailf:info
          "Set the access-list used to permit group membership";
        type std-acl-type;
      }
      container password {
        tailf:info
          "Authentication password (key)";
        tailf:cli-flatten-container;
        tailf:cli-compact-syntax;
        tailf:cli-sequence-commands;
        uses ncs_rpc_notif_password-grouping;
      }
    }
  }

  grouping ncs_rpc_notif_interface-ip-wccp-grouping {
    list wccp-list {
      tailf:cli-drop-node-name;
      tailf:cli-suppress-mode;
      tailf:cli-delete-when-empty;
      key "service-number";
      leaf service-number {
        tailf:cli-suppress-range;
        type uint8 {
          tailf:info
            "<0-254>;;Dynamically defined service identifier number";
          range "0..254";
        }
      }
      container redirect {
        tailf:info
          "Set packet redirection options for the service";
        leaf in {
          tailf:info
            "Redirect to a Cache Engine appropriate inbound packets";
          type empty;
        }
        leaf out {
          tailf:info
            "Redirect to a Cache Engine appropriate outbound packets";
          type empty;
        }
      }
    }
  }

  grouping ncs_rpc_notif_spanning-tree-portfast-grouping {
    leaf default {
      tailf:info
        "Enable portfast by default on all access ports";
      tailf:cli-full-command;
      type empty;
    }
    container bpdufilter {
      tailf:info
        "Enable portfast bdpu filter on this switch";
      leaf default {
        tailf:info
          "Enable portfast by default on all access ports";
        type empty;
      }
    }
    container bpduguard {
      tailf:info
        "Enable portfast bpdu guard on this switch";
      leaf default {
        tailf:info
          "Enable portfast by default on all access ports";
        type empty;
      }
    }
  }

  grouping ncs_rpc_notif_domain-path-preference-grouping {
    container path-preference {
      tailf:info
        "Specify the preferred provider";
      tailf:cli-compact-syntax;
      tailf:cli-sequence-commands {
        tailf:cli-reset-siblings;
      }
      leaf path1 {
        tailf:cli-drop-node-name;
        tailf:cli-incomplete-command;
        type string {
          tailf:info
            "WORD;;Primary service provider";
        }
      }
      leaf path2 {
        tailf:cli-optional-in-sequence;
        tailf:cli-drop-node-name;
        tailf:cli-incomplete-command;
        tailf:cli-disallow-value "fallback";
        type string {
          tailf:info
            "WORD;;Primary service provider";
        }
      }
      leaf path3 {
        tailf:cli-optional-in-sequence;
        tailf:cli-drop-node-name;
        tailf:cli-incomplete-command;
        tailf:cli-disallow-value "fallback";
        type string {
          tailf:info
            "WORD;;Primary service provider";
        }
      }
      leaf fallback {
        tailf:info
          "Specify the fallback provider's color";
        tailf:cli-incomplete-command;
        type empty;
      }
      leaf fallback-path1 {
        tailf:cli-optional-in-sequence;
        tailf:cli-drop-node-name;
        tailf:cli-disallow-value "blackhole|routing|next-fallback";
        type string {
          tailf:info
            "WORD;;Fallback service provider";
        }
      }
      leaf fallback-path2 {
        tailf:cli-optional-in-sequence;
        tailf:cli-drop-node-name;
        tailf:cli-disallow-value "blackhole|routing|next-fallback";
        type string {
          tailf:info
            "WORD;;Fallback service provider";
        }
      }
      leaf fallback-path3 {
        tailf:cli-optional-in-sequence;
        tailf:cli-drop-node-name;
        tailf:cli-disallow-value "blackhole|routing|next-fallback";
        type string {
          tailf:info
            "WORD;;Fallback service provider";
        }
      }
      leaf next-fallback {
        when "../fallback-path1" {
          tailf:xpath-root 3;
          tailf:dependency "../fallback-path1";
        }
        tailf:info
          "Specify the next-fallback service provider";
        tailf:cli-optional-in-sequence;
        tailf:cli-incomplete-command;
        type empty;
      }
      leaf blackhole {
        tailf:info
          "Drop the packet if primary unavailable";
        tailf:cli-optional-in-sequence;
        tailf:cli-full-command;
        type empty;
      }
      leaf routing {
        tailf:info
          "No Fallback provider";
        tailf:cli-optional-in-sequence;
        tailf:cli-full-command;
        type empty;
      }
      leaf next-fallback-path1 {
        tailf:cli-drop-node-name;
        tailf:cli-disallow-value "blackhole|routing|next-fallback";
        type string {
          tailf:info
            "WORD;;Next-fallback service provider";
        }
      }
      leaf next-fallback-path2 {
        tailf:cli-drop-node-name;
        type string {
          tailf:info
            "WORD;;Next-fallback service provider";
        }
      }
      leaf next-fallback-path3 {
        tailf:cli-drop-node-name;
        type string {
          tailf:info
            "WORD;;Next-fallback service provider";
        }
      }
    }
  }

  grouping ncs_rpc_notif_lifetime-grouping {
    leaf start-time {
      tailf:cli-drop-node-name;
      tailf:cli-incomplete-command;
      type hhmm-type {
        tailf:info
          "hh:mm;;Time to start (hh:mm)";
      }
    }
    leaf start-month {
      tailf:cli-drop-node-name;
      tailf:cli-incomplete-command;
      type month-type {
        tailf:info
          "MONTH;;Month of the year to start";
      }
    }
    leaf start-date {
      tailf:cli-drop-node-name;
      tailf:cli-incomplete-command;
      type uint8 {
        tailf:info
          "<1-31>;;Day of the month to start";
        range "1..31";
      }
    }
    leaf start-year {
      tailf:cli-drop-node-name;
      tailf:cli-incomplete-command;
      type uint16 {
        tailf:info
          "<1993-2035>;;Year to start";
        range "1993..2035";
      }
    }
    leaf duration {
      tailf:info
        "Set key lifetime duration";
      tailf:cli-optional-in-sequence;
      tailf:cli-full-command;
      type uint32 {
        tailf:info
          "<1-2147483646>;;Seconds";
        range "1..2147483646";
      }
    }
    leaf infinite {
      tailf:info
        "Never expires";
      tailf:cli-optional-in-sequence;
      tailf:cli-full-command;
      type empty;
    }
    leaf stop-time {
      tailf:cli-drop-node-name;
      tailf:cli-incomplete-command;
      type hhmm-type {
        tailf:info
          "hh:mm;;Time to stop (hh:mm)";
      }
    }
    leaf stop-month {
      tailf:cli-drop-node-name;
      tailf:cli-incomplete-command;
      type month-type {
        tailf:info
          "MONTH;;Month of the year to stop";
      }
    }
    leaf stop-date {
      tailf:cli-drop-node-name;
      tailf:cli-incomplete-command;
      type uint8 {
        tailf:info
          "<1-31>;;Day of the month to stop";
        range "1..31";
      }
    }
    leaf stop-year {
      tailf:cli-drop-node-name;
      type uint16 {
        tailf:info
          "<1993-2035>;;Year to stop";
        range "1993..2035";
      }
    }
  }

  grouping ncs_rpc_notif_us-channel-grouping {
    list us-channel {
      tailf:info
        "Upstream channel configuration";
      tailf:cli-suppress-mode;
      tailf:cli-delete-when-empty;
      key "id";
      leaf id {
        type uint8 {
          tailf:info
            "<0-11>;;Upstream channel number";
          range "0..11";
        }
      }
      leaf frequency {
        tailf:info
          "Frequency";
        type uint32 {
          tailf:info
            "<5000000-85000000>;;Upstream Frequency in Hz";
          range "5000000..85000000";
        }
      }
      container channel-width {
        tailf:info
          "Channel width in HZ";
        tailf:cli-compact-syntax;
        tailf:cli-sequence-commands {
          tailf:cli-reset-siblings;
        }
        leaf first-choice-width {
          tailf:cli-drop-node-name;
          type uint32 {
            tailf:info
              "Channel width Hz";
          }
        }
        leaf last-choice-width {
          tailf:cli-drop-node-name;
          type uint32 {
            tailf:info
              "Channel width Hz";
          }
        }
      }
      leaf power-level {
        tailf:info
          "Input power level";
        type int8 {
          tailf:info
            "<-13 - 23>;;Power level in dBmV";
          range "-13..23";
        }
      }
      leaf docsis-mode {
        tailf:info
          "Upstream channel DOCSIS mode";
        type enumeration {
          enum "atdma" {
            tailf:info
              "DOCSIS 2.0 ATDMA-only channel";
          }
          enum "scdma" {
            tailf:info
              "DOCSIS 2.0 SCDMA-only channel";
          }
          enum "tdma" {
            tailf:info
              "DOCSIS 1.x-only channel";
          }
          enum "tdma-atdma" {
            tailf:info
              "DOCSIS 1.x and DOCSIS 2.0 mixed channel";
          }
        }
      }
      leaf minislot-size {
        tailf:info
          "Minislot size";
        type uint8 {
          tailf:info
            "Minislot size in time ticks";
          range "1|2|4|8|16|32|64|128";
        }
      }
      container modulation-profile {
        tailf:info
          "Modulation Profile Number";
        tailf:cli-compact-syntax;
        tailf:cli-sequence-commands {
          tailf:cli-reset-siblings;
        }
        leaf primary-profile-number {
          tailf:cli-drop-node-name;
          type uint8 {
            tailf:info
              "VALUE;;modulation number";
          }
        }
        leaf secondary-profile-number {
          tailf:cli-drop-node-name;
          type uint8 {
            tailf:info
              "VALUE;;secondary modulation number";
          }
        }
        leaf tertiary-profile-number {
          tailf:cli-drop-node-name;
          type uint8 {
            tailf:info
              "VALUE;;tertiary modulation number";
          }
        }
      }
      leaf equalization-coefficient {
        tailf:info
          "Enable equalization coefficient";
        type empty;
      }
      leaf shutdown {
        tailf:info
          "Shutdown the upstream channel";
        tailf:cli-show-no;
        type empty;
      }
    }
  }

  grouping ncs_rpc_notif_ip-explicit-path-grouping {
    list index {
      tailf:info
        "Specify entry index ";
      tailf:cli-suppress-mode;
      tailf:cli-delete-when-empty;
      tailf:cli-compact-syntax;
      key "id";
      leaf id {
        type uint16 {
          tailf:info
            "<1-65535>;;Entry index number";
        }
      }
      choice address-choice {
        leaf next-address {
          tailf:info
            "Specify the next address in the path";
          tailf:cli-no-name-on-delete;
          tailf:cli-no-value-on-delete;
          type inet:ipv4-address {
            tailf:info
              "WORD;;Enter IP address (A.B.C.D)";
          }
        }
        container next-address-loose {
          tailf:cli-drop-node-name;
          container next-address {
            tailf:info
              "Specify the next address in the path";
            tailf:cli-incomplete-no;
            tailf:cli-incomplete-command;
            leaf loose {
              tailf:info
                "Target address is loose";
              tailf:cli-no-name-on-delete;
              tailf:cli-no-value-on-delete;
              type inet:ipv4-address {
                tailf:info
                  "WORD;;Enter IP address (A.B.C.D)";
              }
            }
          }
        }
        leaf exclude-address {
          tailf:info
            "Exclude an address from subsequent partial path segments";
          tailf:cli-no-name-on-delete;
          tailf:cli-no-value-on-delete;
          type inet:ipv4-address {
            tailf:info
              "WORD;;Enter IP address (A.B.C.D)";
          }
        }
      }
    }
  }

  grouping ncs_rpc_notif_radius-server-grouping {
    leaf auth-port {
      tailf:info
        "UDP port for RADIUS authentication server (default is 1645)";
      type uint16 {
        tailf:info
          "<0-65535>;;Port number";
        range "0..65535";
      }
    }
    leaf acct-port {
      tailf:info
        "UDP port for RADIUS accounting server (default is 1646)";
      type uint16 {
        tailf:info
          "<0-65535>;;Port number";
        range "0..65535";
      }
    }
    leaf timeout {
      tailf:info
        "Time to wait for this RADIUS server to reply (overrides default)";
      type uint16 {
        tailf:info
          "<1-1000>;;Timeout value in seconds to wait for server to reply";
        range "1..1000";
      }
    }
    leaf retransmit {
      tailf:info
        "Specify the number of retries to active server (overrides default)";
      type uint8 {
        tailf:info
          "<0-100>;;Number of retries to this server for a transaction";
        range "0..100";
      }
    }
    container test {
      tailf:info
        "Configure server automated testing.";
      tailf:cli-flatten-container;
      leaf username {
        tailf:info
          "A name (from local database) that should be used to send requests.";
        type string {
          tailf:info
            "WORD;;User Name";
        }
      }
    }
    container key {
      tailf:info
        "per-server encryption key (overrides default)";
      tailf:cli-flatten-container;
      tailf:cli-compact-syntax;
      uses ncs_rpc_notif_password-grouping;
    }
  }

  grouping ncs_rpc_notif_domain-advanced-smart-probes-grouping {
    container smart-probes {
      tailf:info
        "Smart probes configuration";
      container burst {
        tailf:info
          "Specify smart probe burst profile for channels monitored by general monitor";
        container burst {
          tailf:cli-drop-node-name;
          tailf:cli-compact-syntax;
          tailf:cli-sequence-commands;
          leaf number {
            tailf:cli-drop-node-name;
            tailf:cli-incomplete-command;
            type uint8 {
              tailf:info
                "<1-100>;;Specify number of packets in one burst";
              range "1..100";
            }
          }
          leaf packets {
            tailf:info
              "packet(s) in every burst";
            tailf:cli-incomplete-command;
            type empty;
          }
          leaf every {
            tailf:info
              "every burst interval";
            tailf:cli-incomplete-command;
            type empty;
          }
          leaf interval {
            tailf:cli-drop-node-name;
            tailf:cli-incomplete-command;
            type uint8 {
              tailf:info
                "<1-30>;;Specify the interval between the starts of two adjacent bursts";
              range "1..30";
            }
          }
          leaf seconds {
            tailf:info
              "interval length in the scale of seconds";
            type empty;
          }
        }
        container quick {
          tailf:info
            "Specify smart probe burst profile for channels monitored by quick monitor";
          tailf:cli-compact-syntax;
          tailf:cli-sequence-commands;
          leaf number {
            tailf:cli-drop-node-name;
            tailf:cli-incomplete-command;
            type uint8 {
              tailf:info
                "<1-100>;;Specify number of packets in one burst";
              range "1..100";
            }
          }
          leaf packets {
            tailf:info
              "packet(s) in every burst";
            tailf:cli-incomplete-command;
            type empty;
          }
          leaf every {
            tailf:info
              "every burst interval";
            tailf:cli-incomplete-command;
            type empty;
          }
          leaf interval {
            tailf:cli-drop-node-name;
            tailf:cli-incomplete-command;
            type uint8 {
              tailf:info
                "<1-30>;;Specify the interval between the starts of two adjacent bursts";
              range "1..30";
            }
          }
          leaf seconds {
            tailf:info
              "interval length in the scale of seconds";
            type empty;
          }
        }
      }
    }
  }

  grouping ncs_rpc_notif_domain-master-grouping {
    list master {
      tailf:info
        "Enter master controller configuration submode";
      tailf:cli-mode-name "config-domain-vrf-mc";
      tailf:cli-sequence-commands;
      max-elements 1;
      key "type";
      leaf type {
        type enumeration {
          enum "branch" {
            tailf:info
              "Set master type as branch hub";
          }
          enum "hub" {
            tailf:info
              "Set master type as a hub";
          }
          enum "regional-hub" {
            tailf:info
              "Set master type as a regional hub";
          }
          enum "transit" {
            tailf:info
              "Set master type as a transit hub";
          }
        }
      }
      leaf pop-id {
        when "../type = 'transit'" {
          tailf:xpath-root 3;
          tailf:dependency "../type";
        }
        tailf:cli-drop-node-name;
        tailf:cli-hide-in-submode;
        tailf:cli-full-command;
        type uint8 {
          tailf:info
            "<1-62>;;Pop ID";
          range "1..62";
        }
      }
      container source-interface {
        tailf:info
          "Source Interface for master controller";
        tailf:cli-break-sequence-commands;
        uses ncs_rpc_notif_interface-name-grouping;
      }
      container site-prefixes {
        tailf:info
          "site prefixes configuration";
        leaf prefix-list {
          tailf:info
            "Specify prefix-list with static site prefixes";
          type string {
            tailf:info
              "WORD;;prefix-list containing list of site prefixes";
          }
        }
      }
      leaf hub {
        tailf:info
          "Specify regional-hub master controller to peer with";
        tailf:cli-remove-before-change;
        tailf:cli-full-command;
        type inet:ipv4-address {
          tailf:info
            "A.B.C.D;;IP address of regional-hub master controller";
        }
      }
      container collector {
        tailf:info
          "NMS/v9 collector configuration";
        tailf:cli-compact-syntax;
        tailf:cli-sequence-commands {
          tailf:cli-reset-siblings;
        }
        leaf ip-address {
          tailf:cli-drop-node-name;
          type inet:ipv4-address {
            tailf:info
              "A.B.C.D;;IP address of NMS/v9 collector";
          }
        }
        leaf port {
          tailf:info
            "Specify collector port number";
          type uint16 {
            tailf:info
              "<1-65535>;;Specify collector port number";
            range "1..65535";
          }
        }
      }
      container load-balance {
        tailf:info
          "load balance non-policy traffic";
        tailf:cli-add-mode;
        tailf:cli-mode-name "config-domain-vrf-mc-load-balance";
        leaf option {
          tailf:cli-drop-node-name;
          tailf:cli-hide-in-submode;
          type enumeration {
            enum "advanced" {
              tailf:info
                "Load balancing configuration mode";
            }
          }
          default "advanced";
        }
        uses ncs_rpc_notif_domain-path-preference-grouping;
      }
      container password {
        tailf:info
          "MD5 password to be used with BRs";
        tailf:cli-compact-syntax;
        tailf:cli-sequence-commands;
        uses ncs_rpc_notif_password-grouping;
      }
      container enterprise-prefix {
        tailf:info
          "Enterprise prefix configuration";
        leaf prefix-list {
          tailf:info
            "Specify prefix-list with static site targets";
          type string {
            tailf:info
              "WORD;;prefix-list containing list of site targets";
          }
        }
      }
      list monitor-interval {
        tailf:info
          "Monitoring interval";
        tailf:cli-suppress-mode;
        tailf:cli-delete-when-empty;
        key "seconds dscp";
        leaf seconds {
          type uint16 {
            tailf:info
              "<1-300>;;interval (second)";
          }
        }
        leaf dscp {
          tailf:info
            "specify DSCP";
          tailf:cli-expose-key-name;
          type dscp-type;
        }
      }
      container advanced {
        tailf:info
          "Advanced configuration submode";
        tailf:cli-add-mode;
        tailf:cli-mode-name "config-domain-vrf-mc-advanced";
        presence "true";
        uses ncs_rpc_notif_domain-advanced-smart-probes-grouping;
        leaf channel-unreachable-timer {
          tailf:info
            "Unreach interval detection";
          tailf:cli-full-command;
          type uint16 {
            tailf:info
              "<1-65535>;;Specify new timer interval value in seconds";
            range "1..65535";
          }
        }
      }
      list class {
        tailf:info
          "Create domain class and enter domain class command mode";
        tailf:cli-mode-name "config-domain-vrf-mc-class";
        tailf:cli-sequence-commands;
        tailf:cli-incomplete-command;
        key "name";
        leaf name {
          type string {
            tailf:info
              "WORD;;domain class name";
          }
        }
        leaf sequence {
          tailf:info
            "Set the Sequence for the class";
          tailf:cli-hide-in-submode;
          type uint16 {
            tailf:info
              "<1-65535>;;Sequence number for the class";
            range "1..65535";
          }
        }
        container match {
          tailf:info
            "Specify the applications the policy applies to.";
          tailf:cli-break-sequence-commands;
          list dscp {
            tailf:info
              "specify DSCP";
            tailf:cli-suppress-mode;
            tailf:cli-delete-when-empty;
            tailf:cli-incomplete-command;
            key "services-value";
            leaf services-value {
              type dscp-type;
            }
            leaf policy {
              tailf:info
                "Specify the policy (user defined/predefined)";
              type enumeration {
                enum "best-effort" {
                  tailf:info
                    "domain policy type best effort";
                }
                enum "bulk-data" {
                  tailf:info
                    "domain policy type bulk data";
                }
                enum "custom" {
                  tailf:info
                    "custom user-defined policy";
                }
                enum "low-latency-data" {
                  tailf:info
                    "domain policy type low latency data";
                }
                enum "real-time-video" {
                  tailf:info
                    "domain policy type real-time-video";
                }
                enum "scavenger" {
                  tailf:info
                    "domain policy type scavenger";
                }
                enum "voice" {
                  tailf:info
                    "domain policy type voice";
                }
              }
            }
          }
          list application {
            tailf:info
              "Specify the application names";
            tailf:cli-suppress-mode;
            tailf:cli-delete-when-empty;
            tailf:cli-incomplete-command;
            key "services-value";
            leaf services-value {
              type string {
                tailf:info
                  "WORD;;user-defined application name";
              }
            }
            leaf policy {
              tailf:info
                "Specify the policy (user defined/predefined)";
              type enumeration {
                enum "best-effort" {
                  tailf:info
                    "domain policy type best effort";
                }
                enum "bulk-data" {
                  tailf:info
                    "domain policy type bulk data";
                }
                enum "custom" {
                  tailf:info
                    "custom user-defined policy";
                }
                enum "low-latency-data" {
                  tailf:info
                    "domain policy type low latency data";
                }
                enum "real-time-video" {
                  tailf:info
                    "domain policy type real-time-video";
                }
                enum "scavenger" {
                  tailf:info
                    "domain policy type scavenger";
                }
                enum "voice" {
                  tailf:info
                    "domain policy type voice";
                }
              }
            }
          }
        }
        uses ncs_rpc_notif_domain-path-preference-grouping;
        leaf path-last-resort {
          tailf:info
            "Specify path of last resort provider";
          type string {
            tailf:info
              "Specify path of last resort provider";
          }
        }
      }
    }
  }

  grouping ncs_rpc_notif_domain-border-grouping {
    container border {
      tailf:info
        "Enter border router configuration submode";
      tailf:cli-add-mode;
      tailf:cli-mode-name "config-domain-vrf-br";
      tailf:cli-full-command;
      presence "true";
      leaf master {
        tailf:info
          "Specify IP address of Domain master controller";
        tailf:cli-remove-before-change;
        tailf:cli-full-command;
        type union {
          type inet:ipv4-address {
            tailf:info
              "A.B.C.D;;IP address of Domain master controller";
          }
          type enumeration {
            enum "local" {
              tailf:info
                "local;;Local Domain master controller";
            }
          }
        }
      }
      container source-interface {
        tailf:info
          "Source Interface for border";
        uses ncs_rpc_notif_interface-name-grouping;
      }
      container password {
        tailf:info
          "MD5 password to be used with MC";
        tailf:cli-compact-syntax;
        tailf:cli-sequence-commands;
        uses ncs_rpc_notif_password-grouping;
      }
    }
  }

  grouping ncs_rpc_notif_carrier-delay-grouping {
    choice delay-choice {
      leaf seconds {
        tailf:cli-drop-node-name;
        type uint8 {
          tailf:info
            "<0-60>;;Carrier Transitions delay seconds";
          range "0..60";
        }
      }
      leaf msec {
        tailf:info
          "delay specified in milliseconds";
        type uint16 {
          tailf:info
            "<0-1000>;;Carrier Transitions delay milliseconds";
          range "0..1000";
        }
      }
    }
  }

  grouping description-grouping {
    leaf description {
      tailf:info
        "Description text";
      tailf:cli-multi-value;
      tailf:cli-preformatted;
      tailf:cli-full-command;
      type string {
        tailf:info
          "LINE;;Description";
      }
    }
  }

  grouping password-grouping {
    leaf type {
      tailf:cli-drop-node-name;
      tailf:cli-optional-in-sequence;
      tailf:cli-incomplete-command;
      type enumeration {
        enum "0" {
          tailf:info
            "Specifies an UNENCRYPTED password/key will follow";
        }
        enum "7" {
          tailf:info
            "Specifies a HIDDEN password/key will follow";
        }
      }
    }
    leaf secret {
      tailf:cli-drop-node-name;
      tailf:cli-reset-container;
      tailf:cli-disallow-value "0|7|key-chain";
      tailf:meta-data "secret-password";
      type string {
        tailf:info
          "LINE;;The UNENCRYPTED (cleartext) password/key";
      }
    }
  }

  grouping crypto-key-grouping {
    leaf encryption {
      tailf:cli-drop-node-name;
      tailf:cli-optional-in-sequence;
      tailf:cli-incomplete-command;
      type enumeration {
        enum "0" {
          tailf:info
            "Specifies an UNENCRYPTED password will follow";
        }
        enum "6" {
          tailf:info
            "Specifies an ENCRYPTED password will follow";
        }
        enum "7" {
          tailf:info
            "Specifies an HIDDEN password will follow";
        }
      }
    }
    leaf secret {
      tailf:cli-drop-node-name;
      tailf:cli-reset-container;
      tailf:cli-disallow-value "0|6|7";
      tailf:meta-data "secret-password";
      type string {
        tailf:info
          "LINE;;The UNENCRYPTED (cleartext) user password";
      }
    }
  }

  grouping interface-name-grouping {
    choice interface-choice {
      leaf Null {
        tailf:info
          "Null interface";
        tailf:cli-allow-join-with-value {
          tailf:cli-display-joined;
        }
        tailf:non-strict-leafref {
          path "/ncs:devices/ncs:device/ncs:config/ios:interface/Null/name" {
            tailf:xpath-root 3;
          }
        }
        type uint8 {
          tailf:info
            "<0-0>;;Null interface number";
          range "0";
        }
      }
      leaf Loopback {
        tailf:info
          "Loopback interface";
        tailf:cli-allow-join-with-value {
          tailf:cli-display-joined;
        }
        tailf:non-strict-leafref {
          path "/ncs:devices/ncs:device/ncs:config/ios:interface/Loopback/name" {
            tailf:xpath-root 3;
          }
        }
        type string {
          tailf:info
            "<0-2147483647>;;Loopback interface number";
          pattern '([0-9\.])+';
        }
      }
      leaf VirtualPortGroup {
        tailf:info
          "Virtual Port Group";
        tailf:cli-allow-join-with-value {
          tailf:cli-display-joined;
        }
        tailf:non-strict-leafref {
          path "/ncs:devices/ncs:device/ncs:config/ios:interface/VirtualPortGroup/name" {
            tailf:xpath-root 3;
          }
        }
        type uint8 {
          tailf:info
            "<0-31>;;VirtualPortGroup interface number";
        }
      }
      leaf Embedded-Service-Engine {
        tailf:info
          "cisco embedded service engine module";
        tailf:cli-allow-join-with-value {
          tailf:cli-display-joined;
        }
        tailf:non-strict-leafref {
          path "/ncs:devices/ncs:device/ncs:config/ios:interface/Embedded-Service-Engine/name" {
            tailf:xpath-root 3;
          }
        }
        type string {
          tailf:info
            "<0-2>/<0-0>;;Embedded-Service-Engine interface number";
          pattern '[0-9]+.*';
        }
      }
      leaf Service-Engine {
        tailf:info
          "Cisco service engine module";
        tailf:cli-allow-join-with-value {
          tailf:cli-display-joined;
        }
        tailf:non-strict-leafref {
          path "/ncs:devices/ncs:device/ncs:config/ios:interface/Service-Engine/name" {
            tailf:xpath-root 3;
          }
        }
        type string {
          tailf:info
            "<0-2>/<0-0>;;Service-Engine interface number";
          pattern '[0-9]+.*';
        }
      }
      leaf Tunnel {
        tailf:info
          "Tunnel interface";
        tailf:cli-allow-join-with-value {
          tailf:cli-display-joined;
        }
        tailf:non-strict-leafref {
          path "/ncs:devices/ncs:device/ncs:config/ios:interface/Tunnel/name" {
            tailf:xpath-root 3;
          }
        }
        type uint32 {
          tailf:info
            "<0-2147483647>;;Tunnel interface number";
        }
      }
      leaf Port-channel {
        tailf:info
          "Ethernet Channel of interfaces";
        tailf:cli-allow-join-with-value {
          tailf:cli-display-joined;
        }
        tailf:non-strict-leafref {
          path "/ncs:devices/ncs:device/ncs:config/ios:interface/Port-channel/name" {
            tailf:xpath-root 3;
          }
        }
        type uint32 {
          tailf:info
            "<1-512>;;Port-channel interface number";
          range "1..512";
        }
      }
      container Port-channel-subinterface {
        tailf:cli-drop-node-name;
        tailf:cli-flatten-container;
        tailf:cli-compact-syntax;
        leaf Port-channel {
          tailf:cli-allow-join-with-value {
            tailf:cli-display-joined;
          }
          tailf:non-strict-leafref {
            path "/ncs:devices/ncs:device/ncs:config/ios:interface/Port-channel-subinterface/Port-channel/name" {
              tailf:xpath-root 3;
            }
          }
          type string {
            pattern '[0-9]+\.[0-9]+';
          }
        }
      }
      leaf Multilink {
        tailf:info
          "Multilink-group interface";
        tailf:cli-allow-join-with-value {
          tailf:cli-display-joined;
        }
        tailf:non-strict-leafref {
          path "/ncs:devices/ncs:device/ncs:config/ios:interface/Multilink/name" {
            tailf:xpath-root 3;
          }
        }
        type uint16 {
          tailf:info
            "<1-65535>;;Multilink interface number";
          range "1..65535";
        }
      }
      leaf MFR {
        tailf:info
          "Multilink Frame Relay bundle interface";
        tailf:cli-allow-join-with-value {
          tailf:cli-display-joined;
        }
        tailf:non-strict-leafref {
          path "/ncs:devices/ncs:device/ncs:config/ios:interface/MFR/name" {
            tailf:xpath-root 3;
          }
        }
        type uint32 {
          tailf:info
            "<0-2147483647>;;MFR interface number";
        }
      }
      container MFR-subinterface {
        tailf:cli-drop-node-name;
        tailf:cli-flatten-container;
        tailf:cli-compact-syntax;
        leaf MFR {
          tailf:cli-allow-join-with-value {
            tailf:cli-display-joined;
          }
          tailf:non-strict-leafref {
            path "/ncs:devices/ncs:device/ncs:config/ios:interface/MFR-subinterface/MFR/name" {
              tailf:xpath-root 3;
            }
          }
          type string {
            pattern '[0-9]+\.[0-9]+';
          }
        }
      }
      leaf BRI {
        tailf:info
          "ISDN Basic Rate Interface";
        tailf:cli-allow-join-with-value {
          tailf:cli-display-joined;
        }
        tailf:non-strict-leafref {
          path "/ncs:devices/ncs:device/ncs:config/ios:interface/BRI/name" {
            tailf:xpath-root 3;
          }
        }
        type string {
          tailf:info
            "<slot>/<port>;;BRI interface number";
          pattern '[0-9]+.*';
        }
      }
      leaf Ethernet {
        tailf:info
          "Ethernet";
        tailf:cli-allow-join-with-value {
          tailf:cli-display-joined;
        }
        tailf:non-strict-leafref {
          path "/ncs:devices/ncs:device/ncs:config/ios:interface/Ethernet/name" {
            tailf:xpath-root 3;
          }
        }
        type string {
          tailf:info
            "<slot>/<port>;;Ethernet interface number";
          pattern '[0-9]+.*';
        }
      }
      leaf FastEthernet {
        tailf:info
          "FastEthernet IEEE 802.3";
        tailf:cli-allow-join-with-value {
          tailf:cli-display-joined;
        }
        tailf:non-strict-leafref {
          path "/ncs:devices/ncs:device/ncs:config/ios:interface/FastEthernet/name" {
            tailf:xpath-root 3;
          }
        }
        type string {
          tailf:info
            "<0-66>/<0-128>;;FastEthernet interface number";
          pattern '[0-9]+.*';
        }
      }
      leaf GigabitEthernet {
        tailf:info
          "GigabitEthernet IEEE 802.3z";
        tailf:cli-allow-join-with-value {
          tailf:cli-display-joined;
        }
        tailf:non-strict-leafref {
          path "/ncs:devices/ncs:device/ncs:config/ios:interface/GigabitEthernet/name" {
            tailf:xpath-root 3;
          }
        }
        type string {
          tailf:info
            "<0-66>/<0-128>;;GigabitEthernet interface number";
          pattern '[0-9]+.*';
        }
      }
      leaf TenGigabitEthernet {
        tailf:info
          "Ten Gigabit Ethernet";
        tailf:cli-allow-join-with-value {
          tailf:cli-display-joined;
        }
        tailf:non-strict-leafref {
          path "/ncs:devices/ncs:device/ncs:config/ios:interface/TenGigabitEthernet/name" {
            tailf:xpath-root 3;
          }
        }
        type string {
          tailf:info
            "<0-66>/<0-128>;;TenGigabitEthernet interface number";
          pattern '[0-9]+.*';
        }
      }
      leaf FortyGigabitEthernet {
        tailf:info
          "Forty Gigabit Ethernet";
        tailf:cli-allow-join-with-value {
          tailf:cli-display-joined;
        }
        tailf:non-strict-leafref {
          path "/ncs:devices/ncs:device/ncs:config/ios:interface/FortyGigabitEthernet/name" {
            tailf:xpath-root 3;
          }
        }
        type string {
          tailf:info
            "X/Y/Z;;FortyGigabitEthernet interface id";
          pattern '[0-9]+.*';
        }
      }
      leaf HundredGigE {
        tailf:info
          "Hundred Gigabit Ethernet";
        tailf:cli-allow-join-with-value {
          tailf:cli-display-joined;
        }
        tailf:non-strict-leafref {
          path "/ncs:devices/ncs:device/ncs:config/ios:interface/HundredGigE/name" {
            tailf:xpath-root 3;
          }
        }
        type string {
          tailf:info
            "<0-66>/<0-128>;;HundredGigE interface number";
          pattern '[0-9]+.*';
        }
      }
      leaf Wlan-GigabitEthernet {
        tailf:info
          "Wlan-GigabitEthernet interface";
        tailf:cli-allow-join-with-value {
          tailf:cli-display-joined;
        }
        tailf:non-strict-leafref {
          path "/ncs:devices/ncs:device/ncs:config/ios:interface/Wlan-GigabitEthernet/name" {
            tailf:xpath-root 3;
          }
        }
        type string {
          tailf:info
            "<0-0>;;Wlan-GigabitEthernet interface number";
          pattern '[0-9]+.*';
        }
      }
      leaf wlan-ap {
        tailf:info
          "Service module interface to embedded AP";
        tailf:cli-allow-join-with-value {
          tailf:cli-display-joined;
        }
        tailf:non-strict-leafref {
          path "/ncs:devices/ncs:device/ncs:config/ios:interface/wlan-ap/name" {
            tailf:xpath-root 3;
          }
        }
        type string {
          tailf:info
            "<0-0>;;wlan-ap interface number";
          pattern '[0-9]+.*';
        }
      }
      leaf ATM {
        tailf:info
          "ATM interface";
        tailf:cli-allow-join-with-value {
          tailf:cli-display-joined;
        }
        tailf:non-strict-leafref {
          path "/ncs:devices/ncs:device/ncs:config/ios:interface/ATM/name" {
            tailf:xpath-root 3;
          }
        }
        type string {
          pattern '[0-9]+.*';
        }
      }
      leaf CEM {
        tailf:info
          "Circuit Emulation interface";
        tailf:cli-allow-join-with-value {
          tailf:cli-display-joined;
        }
        tailf:non-strict-leafref {
          path "/ncs:devices/ncs:device/ncs:config/ios:interface/CEM/name" {
            tailf:xpath-root 3;
          }
        }
        type string {
          pattern '[0-9]+.*';
        }
      }
      leaf BDI {
        tailf:info
          "Bridge-Domain interface";
        tailf:cli-allow-join-with-value {
          tailf:cli-display-joined;
        }
        tailf:non-strict-leafref {
          path "/ncs:devices/ncs:device/ncs:config/ios:interface/BDI/name" {
            tailf:xpath-root 3;
          }
        }
        type uint16 {
          tailf:info
            "<1-4095>;;BDI interface number";
          range "1..4095";
        }
      }
      leaf BVI {
        tailf:info
          "Bridge-Group Virtual Interface";
        tailf:cli-allow-join-with-value {
          tailf:cli-display-joined;
        }
        tailf:non-strict-leafref {
          path "/ncs:devices/ncs:device/ncs:config/ios:interface/BVI/name" {
            tailf:xpath-root 3;
          }
        }
        type string {
          tailf:info
            "<1-255>;;BVI interface number";
          pattern '[0-9]+.*';
        }
      }
      leaf Cable {
        tailf:info
          "CMTS interface";
        tailf:cli-allow-join-with-value {
          tailf:cli-display-joined;
        }
        tailf:non-strict-leafref {
          path "/ncs:devices/ncs:device/ncs:config/ios:interface/Cable/name" {
            tailf:xpath-root 3;
          }
        }
        type string {
          pattern '[0-9]+.*';
        }
      }
      leaf Video {
        tailf:info
          "video service interface";
        tailf:cli-allow-join-with-value {
          tailf:cli-display-joined;
        }
        tailf:non-strict-leafref {
          path "/ncs:devices/ncs:device/ncs:config/ios:interface/Video/name" {
            tailf:xpath-root 3;
          }
        }
        type string {
          pattern '[0-9]+.*';
        }
      }
      leaf Integrated-Cable {
        tailf:info
          "Integrated Cable interface";
        tailf:cli-allow-join-with-value {
          tailf:cli-display-joined;
        }
        tailf:non-strict-leafref {
          path "/ncs:devices/ncs:device/ncs:config/ios:interface/Integrated-Cable/name" {
            tailf:xpath-root 3;
          }
        }
        type string {
          pattern '[0-9]+.*';
        }
      }
      leaf Modular-Cable {
        tailf:info
          "Modular Cable interface";
        tailf:cli-allow-join-with-value {
          tailf:cli-display-joined;
        }
        tailf:non-strict-leafref {
          path "/ncs:devices/ncs:device/ncs:config/ios:interface/Modular-Cable/name" {
            tailf:xpath-root 3;
          }
        }
        type string {
          pattern '[0-9]+.*';
        }
      }
      leaf Wideband-Cable {
        tailf:info
          "Wideband CMTS interface";
        tailf:cli-allow-join-with-value {
          tailf:cli-display-joined;
        }
        tailf:non-strict-leafref {
          path "/ncs:devices/ncs:device/ncs:config/ios:interface/Wideband-Cable/name" {
            tailf:xpath-root 3;
          }
        }
        type string {
          pattern '[0-9]+.*';
        }
      }
      leaf Dialer {
        tailf:info
          "Dialer interface";
        tailf:cli-allow-join-with-value {
          tailf:cli-display-joined;
        }
        tailf:non-strict-leafref {
          path "/ncs:devices/ncs:device/ncs:config/ios:interface/Dialer/name" {
            tailf:xpath-root 3;
          }
        }
        type string {
          tailf:info
            "<0-255>;;Dialer interface number";
          pattern '[0-9]+.*';
        }
      }
      leaf Bundle {
        tailf:info
          "Virtual Bundle";
        tailf:cli-allow-join-with-value {
          tailf:cli-display-joined;
        }
        tailf:non-strict-leafref {
          path "/ncs:devices/ncs:device/ncs:config/ios:interface/Bundle/name" {
            tailf:xpath-root 3;
          }
        }
        type uint8 {
          tailf:info
            "<1-255>;;Bundle interface number";
          range "1..255";
        }
      }
      leaf Cellular {
        tailf:info
          "Cellular";
        tailf:cli-allow-join-with-value {
          tailf:cli-display-joined;
        }
        tailf:non-strict-leafref {
          path "/ncs:devices/ncs:device/ncs:config/ios:interface/Cellular/name" {
            tailf:xpath-root 3;
          }
        }
        type string {
          pattern '[0-9]+.*';
        }
      }
      leaf Qam-red {
        tailf:info
          "QAM red interface";
        tailf:cli-allow-join-with-value {
          tailf:cli-display-joined;
        }
        tailf:non-strict-leafref {
          path "/ncs:devices/ncs:device/ncs:config/ios:interface/Qam-red/name" {
            tailf:xpath-root 3;
          }
        }
        type string {
          pattern '[0-9]+.*';
        }
      }
      leaf Asi {
        tailf:info
          "ASI interface";
        tailf:cli-allow-join-with-value {
          tailf:cli-display-joined;
        }
        tailf:non-strict-leafref {
          path "/ncs:devices/ncs:device/ncs:config/ios:interface/Asi/name" {
            tailf:xpath-root 3;
          }
        }
        type string {
          pattern '[0-9]+.*';
        }
      }
      leaf Vlan {
        tailf:info
          "Catalyst Vlans";
        tailf:cli-allow-join-with-value {
          tailf:cli-display-joined;
        }
        tailf:non-strict-leafref {
          path "/ncs:devices/ncs:device/ncs:config/ios:interface/Vlan/name" {
            tailf:xpath-root 3;
          }
        }
        type uint16 {
          tailf:info
            "<1-4094>;;Vlan interface number";
          range "1..4094";
        }
      }
      leaf Async {
        tailf:info
          "Async interface";
        tailf:cli-allow-join-with-value {
          tailf:cli-display-joined;
        }
        tailf:non-strict-leafref {
          path "/ncs:devices/ncs:device/ncs:config/ios:interface/Async/name" {
            tailf:xpath-root 3;
          }
        }
        type string {
          pattern '[0-9]+.*';
        }
      }
      leaf Group-Async {
        tailf:info
          "Async Group interface";
        tailf:cli-allow-join-with-value {
          tailf:cli-display-joined;
        }
        tailf:non-strict-leafref {
          path "/ncs:devices/ncs:device/ncs:config/ios:interface/Group-Async/name" {
            tailf:xpath-root 3;
          }
        }
        type uint16;
      }
      leaf POS {
        tailf:info
          "POS interface";
        tailf:cli-allow-join-with-value {
          tailf:cli-display-joined;
        }
        tailf:non-strict-leafref {
          path "/ncs:devices/ncs:device/ncs:config/ios:interface/POS/name" {
            tailf:xpath-root 3;
          }
        }
        type string {
          pattern '[0-9]+.*';
        }
      }
      leaf Serial {
        tailf:info
          "Serial interface";
        tailf:cli-allow-join-with-value {
          tailf:cli-display-joined;
        }
        tailf:non-strict-leafref {
          path "/ncs:devices/ncs:device/ncs:config/ios:interface/Serial/name" {
            tailf:xpath-root 3;
          }
        }
        type string {
          pattern '[0-9]+(/[\.0-9]+)*(:[0-9]+)?';
        }
      }
      container Serial-subinterface {
        tailf:cli-drop-node-name;
        tailf:cli-flatten-container;
        tailf:cli-compact-syntax;
        leaf Serial {
          tailf:cli-allow-join-with-value {
            tailf:cli-display-joined;
          }
          tailf:non-strict-leafref {
            path "/ncs:devices/ncs:device/ncs:config/ios:interface/Serial-subinterface/Serial/name" {
              tailf:xpath-root 3;
            }
          }
          type string {
            pattern '[0-9]+(/[\.0-9]+)*(:[0-9]+)?\.[0-9]+';
          }
        }
      }
      leaf Virtual-Template {
        tailf:info
          "Virtual Template interface";
        tailf:cli-allow-join-with-value {
          tailf:cli-display-joined;
        }
        tailf:non-strict-leafref {
          path "/ncs:devices/ncs:device/ncs:config/ios:interface/Virtual-Template/name" {
            tailf:xpath-root 3;
          }
        }
        type uint16 {
          tailf:info
            "<1-4095>;;Virtual-Template interface number";
          range "1..4095";
        }
      }
      leaf pseudowire {
        tailf:info
          "Pseudowire Interface";
        tailf:cli-allow-join-with-value {
          tailf:cli-display-joined;
        }
        tailf:non-strict-leafref {
          path "/ncs:devices/ncs:device/ncs:config/ios:interface/pseudowire/name" {
            tailf:xpath-root 3;
          }
        }
        type uint32 {
          tailf:info
            "<1-231072>;;pseudowire interface number";
          range "1..231072";
        }
      }
      leaf LISP {
        tailf:info
          "Locator/ID Separation Protocol Virtual Interface";
        tailf:cli-allow-join-with-value {
          tailf:cli-display-joined;
        }
        tailf:non-strict-leafref {
          path "/ncs:devices/ncs:device/ncs:config/ios:interface/LISP/name" {
            tailf:xpath-root 3;
          }
        }
        type uint16 {
          tailf:info
            "<0-1999>;;LISP interface number";
          range "0..1999";
        }
      }
      container LISP-subinterface {
        tailf:cli-drop-node-name;
        tailf:cli-flatten-container;
        tailf:cli-compact-syntax;
        leaf LISP {
          tailf:cli-allow-join-with-value {
            tailf:cli-display-joined;
          }
          tailf:non-strict-leafref {
            path "/ncs:devices/ncs:device/ncs:config/ios:interface/LISP-subinterface/LISP/name" {
              tailf:xpath-root 3;
            }
          }
          type string {
            pattern '[0-9]+\.[0-9]+';
          }
        }
      }
      leaf ToP {
        tailf:cli-allow-join-with-value {
          tailf:cli-display-joined;
        }
        type string {
          pattern '[0-9]+/[0-9]+';
        }
      }
      leaf Dot11Radio {
        tailf:info
          "IEEE 802.11 WLAN";
        tailf:cli-allow-join-with-value {
          tailf:cli-display-joined;
        }
        tailf:non-strict-leafref {
          path "/ncs:devices/ncs:device/ncs:config/ios:interface/Dot11Radio/name" {
            tailf:xpath-root 3;
          }
        }
        type string {
          pattern '[0-9]+.*';
        }
      }
      leaf vasileft {
        tailf:info
          "VasiLeft interface";
        tailf:cli-allow-join-with-value {
          tailf:cli-display-joined;
        }
        tailf:non-strict-leafref {
          path "/ncs:devices/ncs:device/ncs:config/ios:interface/vasileft/name" {
            tailf:xpath-root 3;
          }
        }
        type uint16 {
          tailf:info
            "<1-1000>;;vasileft interface number";
          range "1..1000";
        }
      }
      leaf vasiright {
        tailf:info
          "VasiRight interface";
        tailf:cli-allow-join-with-value {
          tailf:cli-display-joined;
        }
        tailf:non-strict-leafref {
          path "/ncs:devices/ncs:device/ncs:config/ios:interface/vasiright/name" {
            tailf:xpath-root 3;
          }
        }
        type uint16 {
          tailf:info
            "<1-1000>;;vasiright interface number";
          range "1..1000";
        }
      }
      leaf AppNav-Compress {
        tailf:info
          "Service-Context Virtual Interface Compress";
        tailf:cli-allow-join-with-value {
          tailf:cli-display-joined;
        }
        tailf:non-strict-leafref {
          path "/ncs:devices/ncs:device/ncs:config/ios:interface/AppNav-Compress/name" {
            tailf:xpath-root 3;
          }
        }
        type uint16 {
          tailf:info
            "<1-1000>;;AppNav-Compress interface number";
          range "1..1000";
        }
      }
      leaf AppNav-UnCompress {
        tailf:info
          "Service-Context Virtual interface UnCompress";
        tailf:cli-allow-join-with-value {
          tailf:cli-display-joined;
        }
        tailf:non-strict-leafref {
          path "/ncs:devices/ncs:device/ncs:config/ios:interface/AppNav-UnCompress/name" {
            tailf:xpath-root 3;
          }
        }
        type uint16 {
          tailf:info
            "<1-1000>;;AppNav-UnCompress interface number";
          range "1..1000";
        }
      }
      leaf ucse {
        tailf:info
          "Cisco ucse server";
        tailf:cli-allow-join-with-value {
          tailf:cli-display-joined;
        }
        tailf:non-strict-leafref {
          path "/ncs:devices/ncs:device/ncs:config/ios:interface/ucse/name" {
            tailf:xpath-root 3;
          }
        }
        type string {
          pattern '[0-9]+.*';
        }
      }
    }
  }

  grouping service-policy-grouping {
    leaf input {
      tailf:info
        "Assign input policy-map";
      tailf:cli-remove-before-change;
      tailf:non-strict-leafref {
        path "/ncs:devices/ncs:device/ncs:config/ios:policy-map/name" {
          tailf:xpath-root 3;
        }
      }
      type string {
        tailf:info
          "WORD;;input Policy-map name";
      }
    }
    leaf output {
      tailf:info
        "Assign output policy-map";
      tailf:cli-remove-before-change;
      tailf:non-strict-leafref {
        path "/ncs:devices/ncs:device/ncs:config/ios:policy-map/name" {
          tailf:xpath-root 3;
        }
      }
      type string {
        tailf:info
          "WORD;;output Policy-map name";
      }
    }
  }

  grouping police-action-transmit-grouping {
    leaf transmit {
      tailf:info
        "transmit packet";
      type empty;
    }
  }

  grouping police-action-drop-grouping {
    leaf drop {
      tailf:info
        "drop packet";
      type empty;
    }
  }

  grouping police-conform-action-grouping {
    container conform-action {
      tailf:info
        "action when rate is less than conform burst";
      tailf:cli-flatten-container;
      choice conform-action-choice {
        leaf set-clp-transmit {
          tailf:info
            "set atm clp and send it";
          type empty;
        }
        leaf set-cos-transmit {
          tailf:info
            "rewrite packet cos and send it";
          type cos_value-type;
        }
        leaf set-discard-class-transmit {
          tailf:info
            "set discard-class and send it";
          type uint8 {
            tailf:info
              "<0-7>;;new discard-class";
            range "0..7";
          }
        }
        leaf set-dscp-transmit {
          tailf:info
            "set dscp and send it";
          type dscp-type;
        }
        leaf set-frde-transmit {
          tailf:info
            "set FR DE and send it";
          type empty;
        }
        leaf set-mpls-exp-imposition-transmit {
          tailf:info
            "set exp at tag imposition and send it";
          type exp_value-type;
        }
        leaf set-mpls-exp-topmost-transmit {
          tailf:info
            "set exp on topmost label and send it";
          type exp_value-type;
        }
        leaf set-prec-transmit {
          tailf:info
            "rewrite packet precedence and send it";
          type prec_value-type;
        }
        leaf set-qos-transmit {
          tailf:info
            "set qos-group and send it";
          type qos_value-type;
        }
        leaf transmit {
          tailf:info
            "transmit packet";
          type empty;
        }
        leaf drop {
          tailf:info
            "drop packet";
          type empty;
        }
      }
    }
    leaf table {
      tailf:info
        "Specify conform-action table-map";
      tailf:cli-optional-in-sequence;
      tailf:non-strict-leafref {
        path "/ncs:devices/ncs:device/ncs:config/ios:table-map/name" {
          tailf:xpath-root 3;
        }
      }
      type string {
        tailf:info
          "WORD;;table-map name";
      }
    }
  }

  grouping police-exceed-action-grouping {
    container exceed-action {
      tailf:info
        "action when rate is within conform and conform + exceed burst";
      tailf:cli-flatten-container;
      choice exceed-action-choice {
        leaf dscp {
          type dscp-type;
        }
        leaf set-clp-transmit {
          tailf:info
            "set atm clp and send it";
          type empty;
        }
        leaf set-cos-transmit {
          tailf:info
            "rewrite packet cos and send it";
          type cos_value-type;
        }
        leaf set-discard-class-transmit {
          tailf:info
            "set discard-class and send it";
          type uint8 {
            tailf:info
              "<0-7>;;new discard-class";
            range "0..7";
          }
        }
        leaf set-dscp-transmit {
          tailf:info
            "set dscp and send it";
          type dscp-type;
        }
        leaf set-frde-transmit {
          tailf:info
            "set FR DE and send it";
          type empty;
        }
        leaf set-mpls-exp-imposition-transmit {
          tailf:info
            "set exp at tag imposition and send it";
          type exp_value-type;
        }
        leaf set-mpls-exp-topmost-transmit {
          tailf:info
            "set exp on topmost label and send it";
          type exp_value-type;
        }
        leaf set-prec-transmit {
          tailf:info
            "rewrite packet precedence and send it";
          type prec_value-type;
        }
        leaf set-qos-transmit {
          tailf:info
            "set qos-group and send it";
          type qos_value-type;
        }
        leaf transmit {
          tailf:info
            "transmit packet";
          type empty;
        }
        leaf drop {
          tailf:info
            "drop packet";
          type empty;
        }
      }
    }
  }

  grouping police-violate-action-grouping {
    container violate-action {
      tailf:info
        "action when rate is greater than conform exceed burst";
      tailf:cli-flatten-container;
      choice violate-action-choice {
        leaf set-clp-transmit {
          tailf:info
            "set atm clp and send it";
          type empty;
        }
        leaf set-cos-transmit {
          tailf:info
            "rewrite packet cos and send it";
          type cos_value-type;
        }
        leaf set-discard-class-transmit {
          tailf:info
            "set discard-class and send it";
          type uint8 {
            tailf:info
              "<0-7>;;new discard-class";
            range "0..7";
          }
        }
        leaf set-dscp-transmit {
          tailf:info
            "set dscp and send it";
          type dscp-type;
        }
        leaf set-frde-transmit {
          tailf:info
            "set FR DE and send it";
          type empty;
        }
        leaf set-mpls-exp-imposition-transmit {
          tailf:info
            "set exp at tag imposition and send it";
          type exp_value-type;
        }
        leaf set-mpls-exp-topmost-transmit {
          tailf:info
            "set exp on topmost label and send it";
          type exp_value-type;
        }
        leaf set-prec-transmit {
          tailf:info
            "rewrite packet precedence and send it";
          type prec_value-type;
        }
        leaf set-qos-transmit {
          tailf:info
            "set qos-group and send it";
          type qos_value-type;
        }
        leaf transmit {
          tailf:info
            "transmit packet";
          type empty;
        }
        leaf drop {
          tailf:info
            "drop packet";
          type empty;
        }
      }
    }
  }

  grouping police-multiple-conform-action-grouping {
    container conform-set-clp-transmit {
      tailf:cli-no-keyword;
      tailf:cli-drop-node-name;
      tailf:cli-flatten-container;
      container conform-action {
        tailf:info
          "action when rate is less than conform burst";
        tailf:cli-flatten-container;
        leaf set-clp-transmit {
          tailf:info
            "set atm clp and send it";
          type empty;
        }
      }
    }
    container conform-set-cos-transmit {
      tailf:cli-no-keyword;
      tailf:cli-drop-node-name;
      tailf:cli-flatten-container;
      container conform-action {
        tailf:info
          "action when rate is less than conform burst";
        tailf:cli-flatten-container;
        leaf set-cos-transmit {
          tailf:info
            "rewrite packet cos and send it";
          type cos_value-type;
        }
      }
    }
    container conform-set-cos-transmit-table {
      tailf:cli-no-keyword;
      tailf:cli-drop-node-name;
      tailf:cli-flatten-container;
      container conform-action {
        tailf:info
          "action when rate is less than conform burst";
        tailf:cli-flatten-container;
        tailf:cli-compact-syntax;
        tailf:cli-sequence-commands;
        leaf set-cos-transmit {
          tailf:info
            "rewrite packet cos and send it";
          type cos_value-type;
        }
        leaf table {
          tailf:info
            "Specify table-map";
          tailf:non-strict-leafref {
            path "/ncs:devices/ncs:device/ncs:config/ios:table-map/name" {
              tailf:xpath-root 3;
            }
          }
          type string {
            tailf:info
              "WORD;;table-map name";
          }
        }
      }
    }
    container conform-set-discard-class-transmit {
      tailf:cli-no-keyword;
      tailf:cli-drop-node-name;
      tailf:cli-flatten-container;
      container conform-action {
        tailf:info
          "action when rate is less than conform burst";
        tailf:cli-flatten-container;
        leaf set-discard-class-transmit {
          tailf:info
            "set discard-class and send it";
          type uint8 {
            tailf:info
              "<0-7>;;new discard-class";
            range "0..7";
          }
        }
      }
    }
    container conform-set-dscp-transmit {
      tailf:cli-no-keyword;
      tailf:cli-drop-node-name;
      tailf:cli-flatten-container;
      container conform-action {
        tailf:info
          "action when rate is less than conform burst";
        tailf:cli-flatten-container;
        leaf set-dscp-transmit {
          tailf:info
            "set dscp and send it";
          type dscp-type;
        }
      }
    }
    container conform-set-dscp-transmit-table {
      tailf:cli-no-keyword;
      tailf:cli-drop-node-name;
      tailf:cli-flatten-container;
      container conform-action {
        tailf:info
          "action when rate is less than conform burst";
        tailf:cli-flatten-container;
        tailf:cli-compact-syntax;
        tailf:cli-sequence-commands;
        leaf set-dscp-transmit {
          tailf:info
            "set dscp and send it";
          type dscp-type;
        }
        leaf table {
          tailf:info
            "Specify table-map";
          tailf:non-strict-leafref {
            path "/ncs:devices/ncs:device/ncs:config/ios:table-map/name" {
              tailf:xpath-root 3;
            }
          }
          type string {
            tailf:info
              "WORD;;table-map name";
          }
        }
      }
    }
    container conform-set-frde-transmit {
      tailf:cli-no-keyword;
      tailf:cli-drop-node-name;
      tailf:cli-flatten-container;
      container conform-action {
        tailf:info
          "action when rate is less than conform burst";
        tailf:cli-flatten-container;
        leaf set-frde-transmit {
          tailf:info
            "set FR DE and send it";
          type empty;
        }
      }
    }
    container conform-set-mpls-exp-imposition-transmit {
      tailf:cli-no-keyword;
      tailf:cli-drop-node-name;
      tailf:cli-flatten-container;
      container conform-action {
        tailf:info
          "action when rate is less than conform burst";
        tailf:cli-flatten-container;
        leaf set-mpls-exp-imposition-transmit {
          tailf:info
            "set exp at tag imposition and send it";
          type exp_value-type;
        }
      }
    }
    container conform-set-mpls-exp-imposition-transmit-table {
      tailf:cli-no-keyword;
      tailf:cli-drop-node-name;
      tailf:cli-flatten-container;
      container conform-action {
        tailf:info
          "action when rate is less than conform burst";
        tailf:cli-flatten-container;
        tailf:cli-compact-syntax;
        tailf:cli-sequence-commands;
        leaf set-mpls-exp-imposition-transmit {
          tailf:info
            "set exp at tag imposition and send it";
          type exp_value-type;
        }
        leaf table {
          tailf:info
            "Specify table-map";
          tailf:non-strict-leafref {
            path "/ncs:devices/ncs:device/ncs:config/ios:table-map/name" {
              tailf:xpath-root 3;
            }
          }
          type string {
            tailf:info
              "WORD;;table-map name";
          }
        }
      }
    }
    container conform-set-mpls-exp-topmost-transmit {
      tailf:cli-no-keyword;
      tailf:cli-drop-node-name;
      tailf:cli-flatten-container;
      container conform-action {
        tailf:info
          "action when rate is less than conform burst";
        tailf:cli-flatten-container;
        leaf set-mpls-exp-topmost-transmit {
          tailf:info
            "set exp on topmost label and send it";
          type exp_value-type;
        }
      }
    }
    container conform-set-mpls-exp-topmost-transmit-table {
      tailf:cli-no-keyword;
      tailf:cli-drop-node-name;
      tailf:cli-flatten-container;
      container conform-action {
        tailf:info
          "action when rate is less than conform burst";
        tailf:cli-flatten-container;
        tailf:cli-compact-syntax;
        tailf:cli-sequence-commands;
        leaf set-mpls-exp-topmost-transmit {
          tailf:info
            "set exp on topmost label and send it";
          type exp_value-type;
        }
        leaf table {
          tailf:info
            "Specify table-map";
          tailf:non-strict-leafref {
            path "/ncs:devices/ncs:device/ncs:config/ios:table-map/name" {
              tailf:xpath-root 3;
            }
          }
          type string {
            tailf:info
              "WORD;;table-map name";
          }
        }
      }
    }
    container conform-set-prec-transmit {
      tailf:cli-no-keyword;
      tailf:cli-drop-node-name;
      tailf:cli-flatten-container;
      container conform-action {
        tailf:info
          "action when rate is less than conform burst";
        tailf:cli-flatten-container;
        leaf set-prec-transmit {
          tailf:info
            "rewrite packet precedence and send it";
          type prec_value-type;
        }
      }
    }
    container conform-set-prec-transmit-table {
      tailf:cli-no-keyword;
      tailf:cli-drop-node-name;
      tailf:cli-flatten-container;
      container conform-action {
        tailf:info
          "action when rate is less than conform burst";
        tailf:cli-flatten-container;
        tailf:cli-compact-syntax;
        tailf:cli-sequence-commands;
        leaf set-prec-transmit {
          tailf:info
            "rewrite packet precedence and send it";
          type prec_value-type;
        }
        leaf table {
          tailf:info
            "Specify table-map";
          tailf:non-strict-leafref {
            path "/ncs:devices/ncs:device/ncs:config/ios:table-map/name" {
              tailf:xpath-root 3;
            }
          }
          type string {
            tailf:info
              "WORD;;table-map name";
          }
        }
      }
    }
    container conform-set-qos-transmit {
      tailf:cli-no-keyword;
      tailf:cli-drop-node-name;
      tailf:cli-flatten-container;
      container conform-action {
        tailf:info
          "action when rate is less than conform burst";
        tailf:cli-flatten-container;
        leaf set-qos-transmit {
          tailf:info
            "set qos-group and send it";
          type qos_value-type;
        }
      }
    }
    container conform-set-qos-transmit-table {
      tailf:cli-no-keyword;
      tailf:cli-drop-node-name;
      tailf:cli-flatten-container;
      container conform-action {
        tailf:info
          "action when rate is less than conform burst";
        tailf:cli-flatten-container;
        tailf:cli-compact-syntax;
        tailf:cli-sequence-commands;
        leaf set-qos-transmit {
          tailf:info
            "set qos-group and send it";
          type qos_value-type;
        }
        leaf table {
          tailf:info
            "Specify table-map";
          tailf:non-strict-leafref {
            path "/ncs:devices/ncs:device/ncs:config/ios:table-map/name" {
              tailf:xpath-root 3;
            }
          }
          type string {
            tailf:info
              "WORD;;table-map name";
          }
        }
      }
    }
    container conform-transmit {
      tailf:cli-no-keyword;
      tailf:cli-drop-node-name;
      tailf:cli-flatten-container;
      container conform-action {
        tailf:info
          "action when rate is less than conform burst";
        tailf:cli-flatten-container;
        uses police-action-transmit-grouping;
      }
    }
    container conform-drop {
      tailf:cli-no-keyword;
      tailf:cli-drop-node-name;
      tailf:cli-flatten-container;
      container conform-action {
        tailf:info
          "action when rate is less than conform burst";
        tailf:cli-flatten-container;
        uses police-action-drop-grouping;
      }
    }
  }

  grouping police-multiple-exceed-action-grouping {
    container exceed-dscp {
      tailf:cli-no-keyword;
      tailf:cli-drop-node-name;
      tailf:cli-flatten-container;
      container exceed-action {
        tailf:info
          "action when rate is within conform and conform + exceed burst";
        tailf:cli-flatten-container;
        leaf dscp {
          type dscp-type;
        }
      }
    }
    container exceed-set-clp-transmit {
      tailf:cli-no-keyword;
      tailf:cli-drop-node-name;
      tailf:cli-flatten-container;
      container exceed-action {
        tailf:info
          "action when rate is within conform and conform + exceed burst";
        tailf:cli-flatten-container;
        leaf set-clp-transmit {
          tailf:info
            "set atm clp and send it";
          type empty;
        }
      }
    }
    container exceed-set-cos-transmit {
      tailf:cli-no-keyword;
      tailf:cli-drop-node-name;
      tailf:cli-flatten-container;
      container exceed-action {
        tailf:info
          "action when rate is within conform and conform + exceed burst";
        tailf:cli-flatten-container;
        leaf set-cos-transmit {
          tailf:info
            "rewrite packet cos and send it";
          type cos_value-type;
        }
      }
    }
    container exceed-set-cos-transmit-table {
      tailf:cli-no-keyword;
      tailf:cli-drop-node-name;
      tailf:cli-flatten-container;
      container exceed-action {
        tailf:info
          "action when rate is within conform and conform + exceed burst";
        tailf:cli-flatten-container;
        tailf:cli-compact-syntax;
        tailf:cli-sequence-commands;
        leaf set-cos-transmit {
          tailf:info
            "rewrite packet cos and send it";
          type cos_value-type;
        }
        leaf table {
          tailf:info
            "Specify table-map";
          tailf:non-strict-leafref {
            path "/ncs:devices/ncs:device/ncs:config/ios:table-map/name" {
              tailf:xpath-root 3;
            }
          }
          type string {
            tailf:info
              "WORD;;table-map name";
          }
        }
      }
    }
    container exceed-set-discard-class-transmit {
      tailf:cli-no-keyword;
      tailf:cli-drop-node-name;
      tailf:cli-flatten-container;
      container exceed-action {
        tailf:info
          "action when rate is within conform and conform + exceed burst";
        tailf:cli-flatten-container;
        leaf set-discard-class-transmit {
          tailf:info
            "set discard-class and send it";
          type uint8 {
            tailf:info
              "<0-7>;;new discard-class";
            range "0..7";
          }
        }
      }
    }
    container exceed-set-dscp-transmit {
      tailf:cli-no-keyword;
      tailf:cli-drop-node-name;
      tailf:cli-flatten-container;
      container exceed-action {
        tailf:info
          "action when rate is within conform and conform + exceed burst";
        tailf:cli-flatten-container;
        leaf set-dscp-transmit {
          tailf:info
            "set dscp and send it";
          type dscp-type;
        }
      }
    }
    container exceed-set-frde-transmit {
      tailf:cli-no-keyword;
      tailf:cli-drop-node-name;
      tailf:cli-flatten-container;
      container exceed-action {
        tailf:info
          "action when rate is within conform and conform + exceed burst";
        tailf:cli-flatten-container;
        leaf set-frde-transmit {
          tailf:info
            "set FR DE and send it";
          type empty;
        }
      }
    }
    container exceed-set-mpls-exp-imposition-transmit {
      tailf:cli-no-keyword;
      tailf:cli-drop-node-name;
      tailf:cli-flatten-container;
      container exceed-action {
        tailf:info
          "action when rate is within conform and conform + exceed burst";
        tailf:cli-flatten-container;
        leaf set-mpls-exp-imposition-transmit {
          tailf:info
            "set exp at tag imposition and send it";
          type exp_value-type;
        }
      }
    }
    container exceed-set-mpls-exp-topmost-transmit {
      tailf:cli-no-keyword;
      tailf:cli-drop-node-name;
      tailf:cli-flatten-container;
      container exceed-action {
        tailf:info
          "action when rate is within conform and conform + exceed burst";
        tailf:cli-flatten-container;
        leaf set-mpls-exp-topmost-transmit {
          tailf:info
            "set exp on topmost label and send it";
          type exp_value-type;
        }
      }
    }
    container exceed-set-prec-transmit {
      tailf:cli-no-keyword;
      tailf:cli-drop-node-name;
      tailf:cli-flatten-container;
      container exceed-action {
        tailf:info
          "action when rate is within conform and conform + exceed burst";
        tailf:cli-flatten-container;
        leaf set-prec-transmit {
          tailf:info
            "rewrite packet precedence and send it";
          type prec_value-type;
        }
      }
    }
    container exceed-set-qos-transmit {
      tailf:cli-no-keyword;
      tailf:cli-drop-node-name;
      tailf:cli-flatten-container;
      container exceed-action {
        tailf:info
          "action when rate is within conform and conform + exceed burst";
        tailf:cli-flatten-container;
        leaf set-qos-transmit {
          tailf:info
            "set qos-group and send it";
          type qos_value-type;
        }
      }
    }
    container exceed-set-qos-transmit-table {
      tailf:cli-no-keyword;
      tailf:cli-drop-node-name;
      tailf:cli-flatten-container;
      container exceed-action {
        tailf:info
          "action when rate is within conform and conform + exceed burst";
        tailf:cli-flatten-container;
        tailf:cli-compact-syntax;
        tailf:cli-sequence-commands;
        leaf set-qos-transmit {
          tailf:info
            "set qos-group and send it";
          type cos_value-type;
        }
        leaf table {
          tailf:info
            "Specify table-map";
          tailf:non-strict-leafref {
            path "/ncs:devices/ncs:device/ncs:config/ios:table-map/name" {
              tailf:xpath-root 3;
            }
          }
          type string {
            tailf:info
              "WORD;;table-map name";
          }
        }
      }
    }
    container exceed-transmit {
      tailf:cli-no-keyword;
      tailf:cli-drop-node-name;
      tailf:cli-flatten-container;
      container exceed-action {
        tailf:info
          "action when rate is within conform and conform + exceed burst";
        tailf:cli-flatten-container;
        uses police-action-transmit-grouping;
      }
    }
    container exceed-drop {
      tailf:cli-no-keyword;
      tailf:cli-drop-node-name;
      tailf:cli-flatten-container;
      container exceed-action {
        tailf:info
          "action when rate is within conform and conform + exceed burst";
        tailf:cli-flatten-container;
        uses police-action-drop-grouping;
      }
    }
  }

  grouping police-multiple-violate-action-grouping {
    container violate-set-clp-transmit {
      tailf:cli-no-keyword;
      tailf:cli-drop-node-name;
      tailf:cli-flatten-container;
      container violate-action {
        tailf:info
          "action when rate is greater than conform + exceed burst";
        tailf:cli-flatten-container;
        leaf set-clp-transmit {
          tailf:info
            "set atm clp and send it";
          type empty;
        }
      }
    }
    container violate-set-cos-transmit {
      tailf:cli-no-keyword;
      tailf:cli-drop-node-name;
      tailf:cli-flatten-container;
      container violate-action {
        tailf:info
          "action when rate is greater than conform + exceed burst";
        tailf:cli-flatten-container;
        leaf set-cos-transmit {
          tailf:info
            "rewrite packet cos and send it";
          type cos_value-type;
        }
      }
    }
    container violate-set-discard-class-transmit {
      tailf:cli-no-keyword;
      tailf:cli-drop-node-name;
      tailf:cli-flatten-container;
      container violate-action {
        tailf:info
          "action when rate is greater than conform + exceed burst";
        tailf:cli-flatten-container;
        leaf set-discard-class-transmit {
          tailf:info
            "set discard-class and send it";
          type uint8 {
            tailf:info
              "<0-7>;;new discard-class";
            range "0..7";
          }
        }
      }
    }
    container violate-set-dscp-transmit {
      tailf:cli-no-keyword;
      tailf:cli-drop-node-name;
      tailf:cli-flatten-container;
      container violate-action {
        tailf:info
          "action when rate is greater than conform + exceed burst";
        tailf:cli-flatten-container;
        leaf set-dscp-transmit {
          tailf:info
            "set dscp and send it";
          type dscp-type;
        }
      }
    }
    container violate-set-frde-transmit {
      tailf:cli-no-keyword;
      tailf:cli-drop-node-name;
      tailf:cli-flatten-container;
      container violate-action {
        tailf:info
          "action when rate is greater than conform + exceed burst";
        tailf:cli-flatten-container;
        leaf set-frde-transmit {
          tailf:info
            "set FR DE and send it";
          type empty;
        }
      }
    }
    container violate-set-mpls-exp-imposition-transmit {
      tailf:cli-no-keyword;
      tailf:cli-drop-node-name;
      tailf:cli-flatten-container;
      container violate-action {
        tailf:info
          "action when rate is greater than conform + exceed burst";
        tailf:cli-flatten-container;
        leaf set-mpls-exp-imposition-transmit {
          tailf:info
            "set exp at tag imposition and send it";
          type exp_value-type;
        }
      }
    }
    container violate-set-mpls-exp-topmost-transmit {
      tailf:cli-no-keyword;
      tailf:cli-drop-node-name;
      tailf:cli-flatten-container;
      container violate-action {
        tailf:info
          "action when rate is greater than conform + exceed burst";
        tailf:cli-flatten-container;
        leaf set-mpls-exp-topmost-transmit {
          tailf:info
            "set exp on topmost label and send it";
          type exp_value-type;
        }
      }
    }
    container violate-set-prec-transmit {
      tailf:cli-no-keyword;
      tailf:cli-drop-node-name;
      tailf:cli-flatten-container;
      container violate-action {
        tailf:info
          "action when rate is greater than conform + exceed burst";
        tailf:cli-flatten-container;
        leaf set-prec-transmit {
          tailf:info
            "rewrite packet precedence and send it";
          type prec_value-type;
        }
      }
    }
    container violate-set-qos-transmit {
      tailf:cli-no-keyword;
      tailf:cli-drop-node-name;
      tailf:cli-flatten-container;
      container violate-action {
        tailf:info
          "action when rate is greater than conform + exceed burst";
        tailf:cli-flatten-container;
        leaf set-qos-transmit {
          tailf:info
            "set qos-group and send it";
          type qos_value-type;
        }
      }
    }
    container violate-transmit {
      tailf:cli-no-keyword;
      tailf:cli-drop-node-name;
      tailf:cli-flatten-container;
      container violate-action {
        tailf:info
          "action when rate is greater than conform + exceed burst";
        tailf:cli-flatten-container;
        uses police-action-transmit-grouping;
      }
    }
    container violate-drop {
      tailf:cli-no-keyword;
      tailf:cli-drop-node-name;
      tailf:cli-flatten-container;
      container violate-action {
        tailf:info
          "action when rate is greater than conform + exceed burst";
        tailf:cli-flatten-container;
        uses police-action-drop-grouping;
      }
    }
  }

  grouping police-action-grouping {
    container actions {
      tailf:cli-break-sequence-commands;
      tailf:cli-no-keyword;
      tailf:cli-drop-node-name;
      tailf:cli-flatten-container;
      uses police-multiple-conform-action-grouping;
      uses police-multiple-exceed-action-grouping;
      uses police-multiple-violate-action-grouping;
    }
  }

  grouping policy-map-class-grouping {
    leaf pass-through {
      tailf:info
        "pass-through action";
      tailf:cli-full-command;
      type empty;
    }
    container policy {
      tailf:cli-drop-node-name;
      tailf:cli-compact-syntax;
      tailf:cli-sequence-commands {
        tailf:cli-reset-siblings;
      }
      leaf action {
        tailf:cli-drop-node-name;
        tailf:cli-remove-before-change;
        type enumeration {
          enum "drop" {
            tailf:info
              "Drop the packet";
          }
          enum "inspect" {
            tailf:info
              "Context-based Access Control Engine";
          }
          enum "pass" {
            tailf:info
              "Pass the packet";
          }
        }
      }
      leaf log {
        when "(../action = 'drop') or (../action = 'pass')" {
          tailf:xpath-root 3;
          tailf:dependency "../action";
        }
        tailf:info
          "Send logging message for drop|pass";
        tailf:cli-optional-in-sequence;
        type empty;
      }
      leaf parameter-map {
        tailf:cli-drop-node-name;
        when "../action = 'inspect'" {
          tailf:xpath-root 3;
          tailf:dependency "../action";
        }
        tailf:non-strict-leafref {
          path "/ncs:devices/ncs:device/ncs:config/ios:parameter-map/type/inspect/name" {
            tailf:xpath-root 3;
          }
        }
        type string {
          tailf:info
            "WORD;;Parameter-map (inspect) name";
        }
      }
    }
    container inspect-police {
      when "../policy/action = 'inspect'" {
        tailf:xpath-root 3;
        tailf:dependency "../policy/action";
      }
      tailf:cli-drop-node-name;
      container police {
        tailf:info
          "Police";
        tailf:cli-compact-syntax;
        tailf:cli-sequence-commands {
          tailf:cli-reset-siblings;
        }
        leaf rate {
          tailf:info
            "Specify police rate";
          type uint32 {
            tailf:info
              "<8000-2000000000>;;Rate value in bps";
            range "8000..2000000000";
          }
        }
        leaf burst {
          tailf:info
            "Specify 'burst' parameter";
          type uint32 {
            tailf:info
              "<1000-512000000>;;Burst value in bytes";
            range "1000..512000000";
          }
        }
      }
    }
    container bandwidth {
      tailf:info
        "Bandwidth";
      leaf bits {
        tailf:cli-drop-node-name;
        type uint32 {
          tailf:info
            "<8-10000000>;;Kilo Bits per second";
          range "8..10000000";
        }
      }
      leaf percent {
        tailf:info
          "% of total Bandwidth";
        tailf:cli-remove-before-change;
        type percentage-type;
      }
      container remaining {
        tailf:info
          "% of the remaining bandwidth";
        container percent {
          tailf:info
            "% of the remaining bandwidth";
          tailf:cli-compact-syntax;
          tailf:cli-sequence-commands;
          leaf percent {
            tailf:cli-diff-dependency "../../ratio/ratio" {
              tailf:xpath-root 3;
              tailf:cli-trigger-on-set;
            }
            tailf:cli-drop-node-name;
            type percentage-type;
          }
          uses bandwidth-remaining-account-grouping;
        }
        container ratio {
          tailf:info
            "ratio for sharing excess bandwidth";
          tailf:cli-compact-syntax;
          tailf:cli-sequence-commands;
          leaf ratio {
            tailf:cli-drop-node-name;
            type uint32 {
              tailf:info
                "<1-65536>;;Ratio";
              range "1..65536";
            }
          }
          uses bandwidth-remaining-account-grouping;
        }
      }
    }
    container compression {
      tailf:info
        "Activate Compression";
      presence "Activate Compression";
      container header {
        tailf:info
          "configure header compression";
        presence "configure header compression";
        leaf ip {
          tailf:info
            "configure ip header compression";
          type enumeration {
            enum "rtp" {
              tailf:code-name "header_rtp";
              tailf:info
                "configure rtp header compression";
            }
            enum "tcp" {
              tailf:info
                "configure tcp header compression";
            }
          }
        }
      }
    }
    leaf dbl {
      tailf:info
        "enable dynamic buffer limiting";
      tailf:cli-full-command;
      type empty;
    }
    container estimate {
      tailf:info
        "estimate resources required for this class";
      container bandwidth {
        tailf:info
          "bandwidth required to service this class";
        tailf:cli-compact-syntax;
        tailf:cli-sequence-commands;
        presence "true";
        container delay-one-in {
          tailf:info
            "specify QoS target delay";
          tailf:cli-compact-syntax;
          tailf:cli-sequence-commands;
          leaf doi {
            tailf:cli-drop-node-name;
            tailf:cli-incomplete-command;
            type uint32 {
              range "50..1000000";
              tailf:info
                "<50-1000000>;;delay one packet of N";
            }
          }
          leaf milliseconds {
            type uint32 {
              range "8..1000" {
                tailf:info
                  "<8-1000>;;worst-case milliseconds of delay";
              }
            }
          }
        }
        leaf drop-one-in {
          tailf:info
            "specify QoS target loss rate";
          type uint32 {
            tailf:info
              "<50-1000000>;;drop one packet of N";
          }
        }
      }
    }
    container fair-queue {
      tailf:info
        "Enable Flow-based Fair Queuing in this Class";
      tailf:cli-reset-container;
      presence "true";
      leaf dynamic-queues {
        tailf:cli-drop-node-name;
        tailf:cli-full-command;
        type uint32 {
          range "16|32|64|128|256|512|1024|2048|4096" {
            tailf:info
              "<16-4096>;;Number Dynamic Conversation Queues";
          }
        }
      }
      leaf queue-limit {
        tailf:info
          "per flow queue limit";
        tailf:cli-full-command;
        type uint16 {
          tailf:info
            "<1-32768>;;packets";
          range "1..32768";
        }
      }
    }
    container flow {
      tailf:info
        "Flow subcommands";
      leaf monitor {
        tailf:info
          "Apply a Flow Monitor";
        tailf:non-strict-leafref {
          path "/ncs:devices/ncs:device/ncs:config/ios:flow/monitor/name" {
            tailf:xpath-root 3;
          }
        }
        type string {
          tailf:info
            "WORD;;Flow Monitor name";
        }
      }
    }
    leaf netflow-sampler {
      tailf:info
        "NetFlow action";
      tailf:cli-full-command;
      type string {
        tailf:info
          "WORD;;Name of the flow sampler";
      }
    }
    container police-aggregate {
      tailf:cli-no-keyword;
      tailf:cli-drop-node-name;
      container police {
        tailf:info
          "Police";
        leaf aggregate {
          tailf:info
            "Choose aggregate policer for current class";
          tailf:cli-diff-dependency "/ios:qos/aggregate-policer" {
            tailf:xpath-root 3;
          }
          tailf:cli-diff-dependency "../../../police-policy-map/police/cir" {
            tailf:xpath-root 3;
            tailf:cli-trigger-on-set;
          }
          type string {
            tailf:info
              "WORD;;enter aggregate-policer name";
          }
        }
      }
    }
    choice police-choice {
      case police-cirmode-case {
        container police-policy-map {
          tailf:cli-no-keyword;
          tailf:cli-drop-node-name;
          container police {
            tailf:cli-add-mode;
            tailf:cli-mode-name "config-pmap-c-police";
            tailf:cli-flatten-container;
            tailf:cli-sequence-commands {
              tailf:cli-reset-siblings;
            }
            when "contains(/ios:tailfned/police, 'cirmode')" {
              tailf:xpath-root 3;
              tailf:dependency "/ncs:devices/ncs:device/ncs:config/ios:tailfned/police";
            }
            leaf cir {
              tailf:info
                "Committed information rate";
              tailf:cli-hide-in-submode;
              tailf:cli-diff-dependency "../../../police-aggregate/police/aggregate" {
                tailf:xpath-root 3;
                tailf:cli-trigger-on-set;
              }
              type police-bps-type;
            }
            leaf bc {
              tailf:info
                "Conform burst";
              tailf:cli-optional-in-sequence;
              tailf:cli-hide-in-submode;
              type police-burst-type;
            }
            leaf be {
              when "../bc" {
                tailf:xpath-root 3;
                tailf:dependency "../bc";
              }
              tailf:info
                "Excess burst";
              tailf:cli-optional-in-sequence;
              tailf:cli-hide-in-submode;
              type police-burst-type;
            }
            leaf pir {
              tailf:info
                "Peak Information Rate";
              tailf:cli-optional-in-sequence;
              tailf:cli-hide-in-submode;
              type police-bps-type;
            }
            container pir-be {
              when "../pir" {
                tailf:xpath-root 3;
                tailf:dependency "../pir";
              }
              tailf:cli-drop-node-name;
              tailf:cli-optional-in-sequence;
              tailf:cli-flatten-container;
              tailf:cli-hide-in-submode;
              leaf be {
                tailf:info
                  "Excess burst";
                type police-burst-type;
              }
            }
            uses police-action-grouping;
            container conform-color {
              tailf:info
                "conform color aware";
              tailf:cli-compact-syntax;
              tailf:cli-sequence-commands {
                tailf:cli-reset-siblings;
              }
              leaf class-map-name {
                tailf:cli-drop-node-name;
                tailf:non-strict-leafref {
                  path "/ncs:devices/ncs:device/ncs:config/ios:class-map/name" {
                    tailf:xpath-root 3;
                  }
                }
                type string {
                  tailf:info
                    "WORD;;class-map name for conform color aware";
                }
              }
              leaf exceed-color {
                tailf:info
                  "exceed color aware";
                tailf:non-strict-leafref {
                  path "/ncs:devices/ncs:device/ncs:config/ios:class-map/name" {
                    tailf:xpath-root 3;
                  }
                }
                type string {
                  tailf:info
                    "WORD;;lass-map name for exceed color aware";
                }
              }
            }
          }
        }
      }
      case police-cir-percent-case {
        container police-cir-percent {
          tailf:cli-no-keyword;
          tailf:cli-drop-node-name;
          container police {
            container cir {
              tailf:info
                "Committed information rate";
              container percent {
                tailf:info
                  "% of interface bandwidth for Committed information rate";
                tailf:cli-add-mode;
                tailf:cli-mode-name "config-pmap-c-police";
                tailf:cli-incomplete-command;
                tailf:cli-flatten-container;
                tailf:cli-sequence-commands {
                  tailf:cli-reset-siblings;
                }
                leaf percentage {
                  tailf:cli-drop-node-name;
                  tailf:cli-hide-in-submode;
                  type percentage-type;
                }
                leaf bc {
                  tailf:info
                    "Conform burst";
                  tailf:cli-optional-in-sequence;
                  tailf:cli-hide-in-submode;
                  type uint16 {
                    tailf:info
                      "<1-2000>;;Burst ms";
                  }
                }
                container bc-ms {
                  when "../bc" {
                    tailf:xpath-root 3;
                    tailf:dependency "../bc";
                  }
                  tailf:cli-drop-node-name;
                  tailf:cli-optional-in-sequence;
                  tailf:cli-hide-in-submode;
                  tailf:cli-flatten-container;
                  tailf:cli-compact-syntax;
                  leaf ms {
                    tailf:info
                      "Milli seconds";
                    tailf:cli-no-keyword;
                    type empty;
                  }
                }
                leaf be {
                  when "../bc-ms/ms" {
                    tailf:xpath-root 3;
                    tailf:dependency "../bc-ms/ms";
                  }
                  tailf:info
                    "Excess burst";
                  tailf:cli-optional-in-sequence;
                  tailf:cli-hide-in-submode;
                  type uint16 {
                    tailf:info
                      "<1-2000>;;Burst ms";
                  }
                }
                container be-ms {
                  when "../be" {
                    tailf:xpath-root 3;
                    tailf:dependency "../be";
                  }
                  tailf:cli-drop-node-name;
                  tailf:cli-hide-in-submode;
                  tailf:cli-flatten-container;
                  tailf:cli-compact-syntax;
                  leaf ms {
                    tailf:info
                      "Milli seconds";
                    tailf:cli-no-keyword;
                    type empty;
                  }
                }
                container pir {
                  tailf:info
                    "Peak Information Rate";
                  tailf:cli-flatten-container;
                  tailf:cli-compact-syntax;
                  tailf:cli-hide-in-submode;
                  tailf:cli-optional-in-sequence;
                  leaf percent {
                    tailf:info
                      "% of interface bandwidth for Peak Information Rate";
                    type percentage-type;
                  }
                }
                container pir-be {
                  when "../pir" {
                    tailf:xpath-root 3;
                    tailf:dependency "../pir";
                  }
                  tailf:cli-drop-node-name;
                  tailf:cli-optional-in-sequence;
                  tailf:cli-flatten-container;
                  tailf:cli-hide-in-submode;
                  leaf be {
                    tailf:info
                      "Excess burst";
                    type uint16 {
                      tailf:info
                        "<1-2000>;;Burst ms";
                    }
                  }
                }
                container pir-be-ms {
                  when "../pir-be/be" {
                    tailf:xpath-root 3;
                    tailf:dependency "../pir-be/be";
                  }
                  tailf:cli-drop-node-name;
                  tailf:cli-optional-in-sequence;
                  tailf:cli-hide-in-submode;
                  tailf:cli-flatten-container;
                  leaf ms {
                    tailf:info
                      "Milli seconds";
                    tailf:cli-no-keyword;
                    type empty;
                  }
                }
                uses police-action-grouping;
              }
            }
          }
        }
      }
      case police-rate-unit-case {
        container police-rate-unit {
          tailf:cli-no-keyword;
          tailf:cli-drop-node-name;
          container police {
            container rate {
              tailf:info
                "Specify police rate";
              tailf:cli-add-mode;
              tailf:cli-mode-name "config-pmap-c-police";
              tailf:cli-sequence-commands {
                tailf:cli-reset-siblings;
              }
              leaf units {
                tailf:cli-drop-node-name;
                tailf:cli-hide-in-submode;
                type uint64 {
                  tailf:info
                    "<1-2000000000>;;Rate value in the range 8000-2,000,000,000 bps or 1-2,000,000 pps";
                }
              }
              leaf xps {
                tailf:cli-no-keyword;
                tailf:cli-drop-node-name;
                tailf:cli-optional-in-sequence;
                tailf:cli-hide-in-submode;
                type police-pps-bps-type;
              }
              leaf burst {
                tailf:info
                  "Specify 'burst' parameter";
                tailf:cli-optional-in-sequence;
                tailf:cli-hide-in-submode;
                type uint32 {
                  tailf:info
                    "<1-512000000>;;Burst value in packets/bytes";
                }
              }
              leaf burst-type {
                when "../burst" {
                  tailf:xpath-root 3;
                  tailf:dependency "../burst";
                }
                tailf:cli-no-keyword;
                tailf:cli-drop-node-name;
                tailf:cli-optional-in-sequence;
                tailf:cli-hide-in-submode;
                type police-packets-bytes-type;
              }
              leaf peak-rate {
                tailf:info
                  "Specify peak rate";
                tailf:cli-optional-in-sequence;
                tailf:cli-hide-in-submode;
                type uint32 {
                  tailf:info
                    "<1-512000000>;;Peak-rate value in packets or bytes per second";
                  range "1..512000000";
                }
              }
              leaf peak-rate-type {
                when "../peak-rate" {
                  tailf:xpath-root 3;
                  tailf:dependency "../peak-rate";
                }
                tailf:cli-no-keyword;
                tailf:cli-drop-node-name;
                tailf:cli-optional-in-sequence;
                tailf:cli-hide-in-submode;
                type police-pps-bps-type;
              }
              leaf peak-burst {
                tailf:info
                  "Specify 'peak-burst' parameter for peak-rate";
                tailf:cli-optional-in-sequence;
                tailf:cli-hide-in-submode;
                type uint32 {
                  tailf:info
                    "<1-512000000>;;Burst value in packets/bytes";
                }
              }
              leaf peak-burst-type {
                when "../peak-burst" {
                  tailf:xpath-root 3;
                  tailf:dependency "../peak-burst";
                }
                tailf:cli-no-keyword;
                tailf:cli-drop-node-name;
                tailf:cli-optional-in-sequence;
                tailf:cli-hide-in-submode;
                type police-packets-bytes-type;
              }
              uses police-action-grouping;
            }
          }
        }
      }
      case police-rate-percent-case {
        container police-rate-percent {
          tailf:cli-no-keyword;
          tailf:cli-drop-node-name;
          container police {
            container rate {
              tailf:info
                "Specify police rate";
              container percent {
                tailf:info
                  "% of interface bandwidth for rate";
                tailf:cli-add-mode;
                tailf:cli-mode-name "config-pmap-c-police";
                tailf:cli-sequence-commands {
                  tailf:cli-reset-siblings;
                }
                leaf percentage {
                  tailf:cli-drop-node-name;
                  tailf:cli-hide-in-submode;
                  type percentage-type;
                }
                leaf burst {
                  tailf:info
                    "Specify 'burst' parameter";
                  tailf:cli-optional-in-sequence;
                  tailf:cli-hide-in-submode;
                  type uint16 {
                    tailf:info
                      "<1-2000>;;Burst value in milliseconds";
                  }
                }
                leaf ms {
                  when "../burst" {
                    tailf:xpath-root 3;
                    tailf:dependency "../burst";
                  }
                  tailf:info
                    "Treat 'burst' value in milliseconds";
                  tailf:cli-hide-in-submode;
                  type empty;
                }
                container peak-rate {
                  tailf:info
                    "Specify peak rate";
                  tailf:cli-hide-in-submode;
                  tailf:cli-optional-in-sequence;
                  tailf:cli-flatten-container;
                  leaf percent {
                    tailf:info
                      "% of interface bandwidth for peak-rate";
                    type percentage-type;
                  }
                }
                leaf peak-burst {
                  tailf:info
                    "Specify 'peak-burst' parameter for 'peak-rate'";
                  tailf:cli-hide-in-submode;
                  tailf:cli-optional-in-sequence;
                  type uint16 {
                    tailf:info
                      "<1-2000>;;Peak burst value in milliseconds";
                  }
                }
                container peak-burst-ms {
                  when "../peak-burst" {
                    tailf:xpath-root 3;
                    tailf:dependency "../peak-burst";
                  }
                  tailf:cli-drop-node-name;
                  tailf:cli-optional-in-sequence;
                  tailf:cli-hide-in-submode;
                  tailf:cli-flatten-container;
                  leaf ms {
                    tailf:info
                      "Milli seconds";
                    tailf:cli-no-keyword;
                    type empty;
                  }
                }
                uses police-action-grouping;
              }
            }
          }
        }
      }
      case police-rate-pdp-case {
        container police-rate-pdp {
          tailf:cli-no-keyword;
          tailf:cli-drop-node-name;
          container police {
            container rate {
              tailf:info
                "Specify police rate";
              container pdp {
                tailf:info
                  "% of interface bandwidth for rate";
                tailf:cli-add-mode;
                tailf:cli-mode-name "config-pmap-c-police";
                tailf:cli-flatten-container;
                tailf:cli-sequence-commands {
                  tailf:cli-reset-siblings;
                }
                leaf burst {
                  tailf:info
                    "Conform burst";
                  tailf:cli-hide-in-submode;
                  tailf:cli-optional-in-sequence;
                  type police-burst-type;
                }
                leaf peak-rate {
                  tailf:info
                    "Specify peak rate";
                  tailf:cli-hide-in-submode;
                  tailf:cli-optional-in-sequence;
                  type enumeration {
                    enum "pdp";
                  }
                }
                leaf peak-burst {
                  when "../peak-rate" {
                    tailf:xpath-root 3;
                    tailf:dependency "../peak-rate";
                  }
                  tailf:info
                    "Specify 'peak-burst' parameter for 'peak-rate'";
                  tailf:cli-hide-in-submode;
                  tailf:cli-optional-in-sequence;
                  type police-burst-type;
                }
                uses police-action-grouping;
              }
            }
          }
        }
      }
      case police-flow-case {
        container police-flow {
          tailf:cli-no-keyword;
          tailf:cli-drop-node-name;
          container police {
            container flow {
              tailf:info
                "police each flow";
              tailf:cli-add-mode;
              tailf:cli-mode-name "config-pmap-c-police";
              tailf:cli-flatten-container;
              tailf:cli-sequence-commands {
                tailf:cli-reset-siblings;
              }
              leaf mask {
                tailf:info
                  "flow mask to be used for policing";
                tailf:cli-hide-in-submode;
                tailf:cli-optional-in-sequence;
                type enumeration {
                  enum "dest-only" {
                    tailf:info
                      "destination-address only flow mask";
                  }
                  enum "full-flow" {
                    tailf:info
                      "full flow mask";
                  }
                  enum "src-only" {
                    tailf:info
                      "source-address only flow mask";
                  }
                }
              }
              leaf bps {
                tailf:cli-drop-node-name;
                tailf:cli-hide-in-submode;
                type police-bps-type;
              }
              leaf burst-normal {
                when "../bps" {
                  tailf:xpath-root 3;
                  tailf:dependency "../bps";
                }
                tailf:cli-drop-node-name;
                tailf:cli-hide-in-submode;
                tailf:cli-optional-in-sequence;
                type police-burst-type;
              }
              uses police-action-grouping;
            }
          }
        }
      }
      case police-bpsflat-case {
        container police-catalyst {
          tailf:cli-no-keyword;
          tailf:cli-drop-node-name;
          container police {
            tailf:cli-add-mode;
            tailf:cli-mode-name "config-pmap-c-police";
            tailf:cli-flatten-container;
            tailf:cli-sequence-commands {
              tailf:cli-reset-siblings;
            }
            when "contains(/ios:tailfned/police, 'bpsflat')" {
              tailf:xpath-root 3;
              tailf:dependency "/ncs:devices/ncs:device/ncs:config/ios:tailfned/police";
            }
            leaf bps-value {
              tailf:cli-no-keyword;
              tailf:cli-drop-node-name;
              tailf:cli-hide-in-submode;
              tailf:cli-incomplete-command;
              type string {
                tailf:info
                  "<32000-32000000000>;;Rate in bits per second (postfix k, m, g optional; decimal point allowed)";
              }
            }
            leaf bps {
              when "../bps-value" {
                tailf:xpath-root 3;
                tailf:dependency "../bps-value";
              }
              tailf:cli-hide-in-submode;
              tailf:cli-incomplete-command;
              type empty;
            }
            leaf byte-value {
              tailf:cli-no-keyword;
              tailf:cli-drop-node-name;
              tailf:cli-hide-in-submode;
              tailf:cli-incomplete-command;
              type string {
                tailf:info
                  "<32000-32000000000>;;(postfix k, m, g optional; decimal point allowed)";
              }
            }
            leaf byte {
              when "../byte-value" {
                tailf:xpath-root 3;
                tailf:dependency "../byte-value";
              }
              tailf:cli-hide-in-submode;
              type empty;
            }
            container actions {
              tailf:cli-break-sequence-commands;
              tailf:cli-no-keyword;
              tailf:cli-drop-node-name;
              tailf:cli-flatten-container;
              tailf:cli-hide-in-submode;
              uses police-multiple-conform-action-grouping;
              uses police-multiple-exceed-action-grouping;
              uses police-multiple-violate-action-grouping;
            }
          }
        }
      }
      case police-switch-case {
        container police-switch {
          tailf:cli-no-keyword;
          tailf:cli-drop-node-name;
          container police {
            tailf:cli-compact-syntax;
            tailf:cli-sequence-commands {
              tailf:cli-reset-siblings;
            }
            when "contains(/ios:tailfned/police, 'numflat')" {
              tailf:xpath-root 3;
              tailf:dependency "/ncs:devices/ncs:device/ncs:config/ios:tailfned/police";
            }
            leaf cir {
              tailf:cli-drop-node-name;
              tailf:cli-incomplete-command;
              tailf:cli-diff-dependency "../../../police-aggregate/police/aggregate" {
                tailf:xpath-root 3;
                tailf:cli-trigger-on-set;
              }
              type uint32 {
                tailf:info
                  "<8000-1000000000>;;Bits per second";
                range "8000..1000000000";
              }
            }
            leaf bc {
              tailf:cli-drop-node-name;
              type uint32 {
                tailf:info
                  "<8000-2000000>;;Normal burst bytes";
                range "8000..2000000";
              }
            }
            leaf exceed-action {
              tailf:info
                "action when rate is exceeded";
              type enumeration {
                enum "drop" {
                  tailf:info
                    "drop packet";
                }
                enum "policed-dscp-transmit" {
                  tailf:info
                    "change dscp per policed-dscp map and send it";
                }
              }
            }
          }
        }
      }
      case police-numflat-case {
        container police-numflat {
          tailf:cli-no-keyword;
          tailf:cli-drop-node-name;
          container police {
            tailf:cli-compact-syntax;
            tailf:cli-sequence-commands {
              tailf:cli-reset-siblings;
            }
            when "contains(/ios:tailfned/police, 'numflat')" {
              tailf:xpath-root 3;
              tailf:dependency "/ncs:devices/ncs:device/ncs:config/ios:tailfned/police";
            }
            leaf cir {
              tailf:cli-drop-node-name;
              tailf:cli-diff-dependency "../../../police-aggregate/police/aggregate" {
                tailf:xpath-root 3;
                tailf:cli-trigger-on-set;
              }
              type police-bps-type;
            }
            leaf bc {
              tailf:cli-drop-node-name;
              tailf:cli-optional-in-sequence;
              type police-burst-type;
            }
            leaf be {
              tailf:cli-drop-node-name;
              tailf:cli-optional-in-sequence;
              type police-burst-type;
            }
            container actions {
              tailf:cli-break-sequence-commands;
              tailf:cli-no-keyword;
              tailf:cli-drop-node-name;
              tailf:cli-flatten-container;
              uses police-multiple-conform-action-grouping;
              uses police-multiple-exceed-action-grouping;
              uses police-multiple-violate-action-grouping;
            }
          }
        }
      }
      case police-cirflat-case {
        container police-cirflat {
          tailf:cli-no-keyword;
          tailf:cli-drop-node-name;
          container police {
            tailf:cli-compact-syntax;
            tailf:cli-sequence-commands {
              tailf:cli-reset-siblings;
            }
            when "contains(/ios:tailfned/police, 'cirflat')" {
              tailf:xpath-root 3;
              tailf:dependency "/ncs:devices/ncs:device/ncs:config/ios:tailfned/police";
            }
            leaf cir {
              tailf:info
                "Committed information rate";
              tailf:cli-diff-dependency "../../../police-aggregate/police/aggregate" {
                tailf:xpath-root 3;
                tailf:cli-trigger-on-set;
              }
              type police-bps-type;
            }
            leaf bc {
              tailf:info
                "Conform burst";
              tailf:cli-optional-in-sequence;
              type police-burst-type;
            }
            leaf pir {
              tailf:info
                "Peak Information Rate";
              tailf:cli-optional-in-sequence;
              type police-bps-type;
            }
            leaf be {
              tailf:info
                "Excess burst";
              tailf:cli-optional-in-sequence;
              type police-burst-type;
            }
            container actions {
              tailf:cli-break-sequence-commands;
              tailf:cli-drop-node-name;
              tailf:cli-flatten-container;
              tailf:cli-compact-syntax;
              tailf:cli-sequence-commands;
              uses police-conform-action-grouping;
              uses police-exceed-action-grouping;
              uses police-violate-action-grouping;
            }
          }
        }
      }
    }
    container priority {
      tailf:info
        "Strict Scheduling Priority for this Class";
      tailf:cli-compact-syntax;
      tailf:cli-sequence-commands;
      tailf:cli-reset-container;
      tailf:cli-delete-when-empty;
      presence "true";
      leaf level {
        tailf:info
          "Multi-Level Priority Queue";
        tailf:cli-optional-in-sequence;
        type uint8 {
          tailf:info
            "<1-2>;;Multi-Level Priority Queue";
          range "1..2";
        }
      }
      choice priority-type {
        leaf kilo-bits {
          tailf:cli-drop-node-name;
          type uint32 {
            tailf:info
              "<8-10000000>;;Kilo Bits per second";
            range "8..10000000";
          }
        }
        leaf percent {
          tailf:info
            "% of total bandwidth";
          tailf:cli-remove-before-change;
          type uint16 {
            tailf:info
              "<1-100>;;percentage";
            range "1..100";
          }
        }
      }
      leaf burst {
        tailf:cli-drop-node-name;
        type uint32 {
          tailf:info
            "<32-64000000>;;Burst in bytes";
          range "32..64000000";
        }
      }
    }
    container shape {
      tailf:info
        "Traffic Shaping";
      leaf adaptive {
        tailf:info
          "Enable Traffic Shaping adaptation to BECN";
        tailf:cli-full-command;
        type uint32 {
          range "8000..154400000";
          tailf:info
            "<8000-154400000>;;Lower Bound Target Bit Rate (bits per second)";
        }
      }
      container average {
        tailf:info
          "configure token bucket: CIR (bps) [Bc (bits) [Be (bits)]], send out Bc only per interval";
        tailf:cli-compact-syntax;
        tailf:cli-sequence-commands;
        choice average-choice {
          case a {
            leaf bit-rate {
              tailf:cli-drop-node-name;
              type uint64 {
                tailf:info
                  "<8000-max>;;Target Bit Rate (bits per second), the value needs to be a multiple of 8000";
              }
            }
            leaf bits-per-interval-sustained {
              tailf:cli-drop-node-name;
              type uint32 {
                tailf:info
                  "<256-154400000>;;bits per interval, sustained. Needs to be multiple of 128. Recommend not to configure it, the algorithm will find out the best value";
                range "256..154400000";
              }
            }
            leaf bits-per-interval-excess {
              tailf:cli-drop-node-name;
              type uint32 {
                range "0..154400000";
                tailf:info
                  "<0-154400000>;;bits per interval, excess. Needs to be multiple of 128. Bc will be used if you don't configure it.";
              }
            }
          }
          case b {
            leaf percent {
              tailf:info
                "% of interface bandwidth for Committed information rate";
              type percentage-type;
            }
            leaf burst-size-sustained {
              tailf:cli-incomplete-command;
              tailf:cli-drop-node-name;
              type uint16 {
                tailf:info
                  "<10-2000>;;Sustained burst size in msec";
                range "10..2000";
              }
            }
            leaf ms {
              tailf:info
                "milliseconds";
              type empty;
            }
            container bse {
              tailf:cli-drop-node-name;
              tailf:cli-flatten-container;
              tailf:cli-compact-syntax;
              tailf:cli-sequence-commands;
              leaf burst-size-excess {
                tailf:cli-incomplete-command;
                type uint16 {
                  tailf:info
                    "<10-2000>;;Excess burst size in msec";
                  range "10..2000";
                }
              }
              leaf ms {
                tailf:info
                  "milliseconds";
                type empty;
              }
            }
          }
          case c {
            leaf target-bit-rate {
              tailf:cli-drop-node-name;
              type uint64 {
                tailf:info
                  "<8000-max>;;Target Bit Rate (bits per second), the value needs to be a multiple of 8000";
              }
            }
            leaf account {
              tailf:info
                "Overhead Accounting";
              tailf:cli-incomplete-command;
              type empty;
            }
            leaf user-defined {
              tailf:info
                "Offset Size";
              type int8 {
                tailf:info
                  "<-63 - 63>;;User Defined size";
                range "-63..63";
              }
            }
            leaf atm {
              tailf:info
                "ATM cell tax";
              type empty;
            }
          }
        }
      }
      leaf fecn-adapt {
        tailf:info
          "Enable Traffic Shaping reflection of FECN as BECN";
        tailf:cli-full-command;
        type empty;
      }
      container fr-voice-adapt {
        tailf:info
          "Enable rate adjustment depending on voice presence";
        presence "true";
        leaf deactivation {
          type uint16 {
            range "1..10000";
            tailf:info
              "<1-10000>;;de-activation delay in seconds";
          }
        }
      }
      leaf max-buffers {
        tailf:cli-full-command;
        tailf:info
          "Set Maximum Buffer Limit";
        type uint16 {
          tailf:info
            "<1-4096>;;Maximum Buffer Limit";
          range "1..4096";
        }
      }
    }
    container queue-limit {
      tailf:info
        "Queue Max Threshold for Tail Drop";
      tailf:cli-compact-syntax;
      tailf:cli-sequence-commands {
        tailf:cli-reset-siblings;
      }
      tailf:cli-diff-dependency "../shape" {
        tailf:xpath-root 3;
      }
      choice queue-limit-choice {
        case queue-limit-percent {
          leaf percent {
            tailf:info
              "% of threshold";
            type percentage-type;
          }
        }
        case queue-limit-dscp {
          list dscp {
            tailf:info
              "parameters for each dscp value";
            tailf:cli-suppress-mode;
            tailf:cli-delete-when-empty;
            tailf:cli-compact-syntax;
            tailf:cli-incomplete-command;
            key "dscp";
            leaf dscp {
              type dscp-type;
            }
            leaf percent {
              tailf:info
                "% of threshold";
              type percentage-type;
            }
          }
        }
        case queue-limit-value {
          leaf queue-limit-value {
            tailf:cli-drop-node-name;
            type uint32 {
              tailf:info
                "<1-8192000>;;in bytes, <1-3400> in ms, <1-32768> in packets by default";
              range "1..8192000";
            }
          }
          leaf queue-limit-type {
            tailf:cli-drop-node-name;
            type enumeration {
              enum "bytes" {
                tailf:info
                  "in bytes";
              }
              enum "ms" {
                tailf:info
                  "in milliseconds";
              }
              enum "us" {
                tailf:info
                  "in microseconds";
              }
              enum "packets" {
                tailf:info
                  "in packets";
              }
            }
          }
        }
      }
    }
    container random-detect {
      tailf:info
        "Enable Random Early Detection as drop policy";
      container base {
        tailf:cli-drop-node-name;
        tailf:cli-compact-syntax;
        tailf:cli-sequence-commands {
          tailf:cli-reset-siblings;
        }
        leaf type {
          tailf:cli-drop-node-name;
          tailf:cli-remove-before-change;
          tailf:cli-diff-dependency "../../../bandwidth/percent" {
            tailf:xpath-root 3;
          }
          type enumeration {
            enum "cos-based" {
              tailf:info
                "Enable cos-class-based WRED as drop policy";
            }
            enum "precedence-based" {
              tailf:info
                "Enable precedence-based WRED as drop policy";
            }
            enum "discard-class-based" {
              tailf:info
                "Enable discard-class-based WRED as drop policy";
            }
            enum "dscp-based" {
              tailf:info
                "Enable dscp-based WRED as drop policy";
            }
          }
        }
        leaf aggregate {
          tailf:info
            "aggregate subclasses";
          type empty;
        }
        leaf minimum-thresh {
          tailf:info
            "minimum threshold for red aggregate";
          tailf:cli-incomplete-command;
          type uint32 {
            tailf:info
              "<0-1000000>;;minimum threshold (number of packets)";
            range "0..1000000";
          }
        }
        leaf maximum-thresh {
          tailf:info
            "maximum threshold for red aggregate";
          type uint32 {
            tailf:info
              "<0-1000000>;;maximum threshold (number of packets)";
            range "0..1000000";
          }
        }
        leaf mark-probability {
          tailf:info
            "mark-probability for red aggregate";
          type empty;
        }
        leaf denominator {
          tailf:cli-drop-node-name;
          type uint32 {
            tailf:info
              "<0-65535>;;mark probability denominator";
            range "0..65535";
          }
        }
      }
      leaf exponential-weighting-constant {
        tailf:info
          "weight for mean queue depth calculation";
        tailf:cli-full-command;
        type uint16 {
          tailf:info
            "<1-16>;;integer in 1..16 used in weighted average to mean 2^number";
          range "1..16";
        }
      }
      leaf ecn {
        tailf:info
          "explicit congestion notification";
        tailf:cli-full-command;
        type empty;
      }
      list cos {
        when "../base/type = 'cos-based'" {
          tailf:xpath-root 3;
          tailf:dependency "../base/type";
        }
        tailf:info
          "parameters for each cos value";
        tailf:cli-suppress-mode;
        tailf:cli-delete-when-empty;
        tailf:cli-compact-syntax;
        tailf:cli-sequence-commands;
        tailf:cli-incomplete-command;
        tailf:cli-diff-dependency "../base/type" {
          tailf:xpath-root 3;
        }
        key "cos";
        leaf cos {
          type uint8 {
            tailf:info
              "<0-7>;;cos value";
            range "0..7";
          }
        }
        uses random-detect-grouping;
      }
      list precedence {
        when "../base/type = 'precedence-based'" {
          tailf:xpath-root 3;
          tailf:dependency "../base/type";
        }
        tailf:info
          "parameters for each precedence value";
        tailf:cli-suppress-mode;
        tailf:cli-delete-when-empty;
        tailf:cli-compact-syntax;
        tailf:cli-sequence-commands;
        tailf:cli-incomplete-command;
        tailf:cli-diff-dependency "../base/type" {
          tailf:xpath-root 3;
        }
        key "prec";
        leaf prec {
          type union {
            type uint8 {
              tailf:info
                "<0-7>;;IP precedence";
              range "0..7";
            }
            type enumeration {
              enum "rsvp" {
                tailf:info
                  "rsvp traffic";
              }
            }
          }
        }
        uses random-detect-grouping;
      }
      container precedence-values {
        tailf:cli-drop-node-name;
        list precedence {
          tailf:info
            "parameters for each precedence value";
          when "../../base/type = 'precedence-based'" {
            tailf:xpath-root 3;
            tailf:dependency "../../base/type";
          }
          tailf:cli-suppress-mode;
          tailf:cli-delete-when-empty;
          tailf:cli-compact-syntax;
          tailf:cli-sequence-commands;
          tailf:cli-incomplete-command;
          tailf:cli-diff-dependency "../../base/type" {
            tailf:xpath-root 3;
          }
          key "values";
          leaf values {
            tailf:info
              "multiple precedence subclasses";
            tailf:cli-expose-key-name;
            type uint8 {
              tailf:info
                "<0-7>;;SUBCLASS id";
              range "0..7";
            }
          }
          uses random-detect-values-grouping;
        }
      }
      list discard-class {
        when "../base/type = 'discard-class-based'" {
          tailf:xpath-root 3;
          tailf:dependency "../base/type";
        }
        tailf:info
          "parameters for each discard-class value";
        tailf:cli-suppress-mode;
        tailf:cli-delete-when-empty;
        tailf:cli-compact-syntax;
        tailf:cli-sequence-commands;
        tailf:cli-incomplete-command;
        tailf:cli-diff-dependency "../base/type" {
          tailf:xpath-root 3;
        }
        key "dclass";
        leaf dclass {
          type uint16 {
            tailf:info
              "<0-7>;;discard-class value";
            range "0..7";
          }
        }
        uses random-detect-grouping;
      }
      list dscp {
        when "../base/type = 'dscp-based'" {
          tailf:xpath-root 3;
          tailf:dependency "../base/type";
        }
        tailf:info
          "parameters for each dscp value";
        tailf:cli-suppress-mode;
        tailf:cli-delete-when-empty;
        tailf:cli-compact-syntax;
        tailf:cli-sequence-commands;
        tailf:cli-incomplete-command;
        tailf:cli-diff-dependency "../base/type" {
          tailf:xpath-root 3;
        }
        key "dscpvalue";
        leaf dscpvalue {
          type dscp-type;
        }
        uses random-detect-grouping;
      }
    }
    container set {
      tailf:info
        "Set QoS values";
      leaf atm-clp {
        tailf:info
          "Set ATM CLP bit to 1";
        tailf:cli-full-command;
        type empty;
      }
      container cos {
        tailf:info
          "Set IEEE 802.1Q/ISL class of service/user priority";
        tailf:cli-compact-syntax;
        tailf:cli-sequence-commands;
        choice cos-type {
          case a {
            leaf val {
              tailf:cli-drop-node-name;
              type uint16 {
                range "0..7";
                tailf:info
                  "<0-7>;;cos value";
              }
            }
          }
          case b {
            leaf pack {
              tailf:cli-drop-node-name;
              type enumeration {
                enum "dscp" {
                  tailf:code-name "pack_dscp";
                  tailf:info
                    "Set value from packet dscp";
                }
                enum "precedence" {
                  tailf:code-name "pack_precedence";
                  tailf:info
                    "Set value from packet precedence.";
                }
              }
            }
            leaf table {
              tailf:info
                "Set codepoint value based on tablemap.";
              tailf:non-strict-leafref {
                path "/ncs:devices/ncs:device/ncs:config/ios:table-map/name" {
                  tailf:xpath-root 3;
                }
              }
              type string {
                tailf:info
                  "WORD;;table-map name";
              }
            }
          }
        }
      }
      leaf discard-class {
        tailf:info
          "Discard behavior identifier";
        tailf:cli-full-command;
        type uint16 {
          range "0..7";
          tailf:info
            "<0-7>;;Discard Class value";
        }
      }
      container dscp {
        tailf:info
          "Set DSCP in IP(v4) and IPv6 packets";
        leaf tunnel {
          tailf:info
            "set tunnel packet dscp";
          tailf:cli-full-command;
          type dscp-type;
        }
        leaf value {
          tailf:cli-drop-node-name;
          tailf:cli-full-command;
          type dscp-type;
        }
      }
      leaf fr-de {
        tailf:info
          "Set FR DE bit to 1";
        tailf:cli-full-command;
        type empty;
      }
      container ip {
        tailf:info
          "Set IP specific values";
        choice ip-choice {
          leaf dscp {
            tailf:info
              "Set IP DSCP (DiffServ CodePointint)";
            type dscp-type;
          }
          container precedence {
            tailf:info
              "Set IP precedence";
            presence "Set IP precedence";
            leaf precedence-val {
              tailf:cli-drop-node-name;
              type precedence-type;
            }
          }
        }
      }
      container mpls {
        tailf:info
          "Set MPLS specific values";
        container experimental {
          tailf:info
            "Set Experimental value";
          container imposition {
            tailf:info
              "Set Experimental value at tag imposition";
            leaf exp-value {
              tailf:cli-drop-node-name;
              type uint8 {
                tailf:info
                  "<0-7>;;Experimental value";
                range "0..7";
              }
            }
          }
          container topmost {
            tailf:info
              "Set Experimental value on topmost label";
            leaf exp-value {
              tailf:cli-drop-node-name;
              type uint8 {
                tailf:info
                  "<0-7>;;Experimental value";
                range "0..7";
              }
            }
          }
        }
      }
      container qos-group {
        tailf:info
          "Set QoS Group";
        leaf qos-group-value {
          tailf:cli-drop-node-name;
          tailf:cli-full-command;
          type uint8 {
            range "0..99";
          }
        }
      }
      container precedence {
        tailf:info
          "Set precedence in IP(v4) and IPv6 packets";
        tailf:cli-sequence-commands;
        tailf:cli-compact-syntax;
        choice precedence-choice {
          case precedence-value {
            leaf precedence-value {
              tailf:cli-drop-node-name;
              tailf:cli-no-keyword;
              type precedence-type;
            }
          }
          case precedence-from-field {
            leaf from-field {
              tailf:cli-drop-node-name;
              tailf:cli-no-keyword;
              type enumeration {
                enum "cos" {
                  tailf:info
                    "Set packet precedence from L2 COS";
                }
                enum "qos-group" {
                  tailf:info
                    "Set packet precedence from QoS Group.";
                }
              }
            }
            leaf table {
              tailf:info
                "Set packet precedence based on table map.";
              tailf:non-strict-leafref {
                path "/ncs:devices/ncs:device/ncs:config/ios:table-map/name" {
                  tailf:xpath-root 3;
                }
              }
              type string {
                tailf:info
                  "WORD;;table-map name";
              }
            }
          }
        }
      }
    }
    leaf service-policy {
      tailf:info
        "Configure QoS Service Policy";
      tailf:cli-remove-before-change;
      tailf:cli-full-command;
      tailf:non-strict-leafref {
        path "/ncs:devices/ncs:device/ncs:config/ios:policy-map/name" {
          tailf:xpath-root 3;
        }
      }
      type string {
        tailf:info
          "WORD;;policy-map name";
      }
    }
    leaf trust {
      tailf:info
        "Set trust value for the class";
      type enumeration {
        enum "cos" {
          tailf:info
            "trust value for the class";
        }
        enum "dscp" {
          tailf:info
            "trust value for the class";
        }
        enum "ip-precedence" {
          tailf:info
            "trust value for the class";
        }
      }
    }
    container distribute {
      tailf:info
        "Distribute action";
      list service-node-group {
        tailf:info
          "Distribute to service-node-group";
        tailf:cli-suppress-mode;
        tailf:cli-delete-when-empty;
        max-elements 2;
        key "name";
        leaf name {
          type string {
            tailf:info
              "WORD;;service-node-group name";
          }
        }
      }
    }
    leaf monitor-load {
      tailf:info
        "Monitor AO";
      tailf:cli-full-command;
      type enumeration {
        enum "MS-port-mapper" {
          tailf:info
            "Monitor Microsoft Endpoint Port Mapper load";
        }
        enum "cifs" {
          tailf:info
            "Monitor CIFS Accelerator load";
        }
        enum "http" {
          tailf:info
            "Monitor HTTP Accelerator load";
        }
        enum "ica" {
          tailf:info
            "Monitor ICA Accelerator load";
        }
        enum "mapi" {
          tailf:info
            "Monitor MAPI Accelerator load";
        }
        enum "nfs" {
          tailf:info
            "Monitor NFS Accelerator load";
        }
        enum "ssl" {
          tailf:info
            "Monitor SSL accelerator load";
        }
        enum "video" {
          tailf:info
            "Monitor Video Accelerator load";
        }
        enum "ice";
      }
    }
  }

  grouping distribute-list-content-grouping {
    leaf access-list-name {
      tailf:cli-drop-node-name;
      tailf:cli-prefix-key;
      tailf:cli-optional-in-sequence;
      tailf:cli-disallow-value "route-map|prefix|gateway|in|out";
      type exp-ip-acl-type;
    }
    leaf prefix-list {
      tailf:info
        "Filter connections based on an IPv6 prefix-list";
      tailf:cli-prefix-key;
      tailf:cli-optional-in-sequence;
      tailf:cli-diff-dependency "/ios:ipv6/prefix-list/prefixes" {
        tailf:xpath-root 3;
      }
      type string {
        tailf:info
          "WORD;;Prefix-list name";
      }
    }
    leaf prefix {
      tailf:info
        "Filter prefixes in routing updates";
      tailf:cli-prefix-key;
      tailf:cli-optional-in-sequence;
      tailf:cli-diff-dependency "/ios:ip/prefix-list/prefixes" {
        tailf:xpath-root 3;
      }
      type string {
        tailf:info
          "WORD;;Name of an IP prefix-list";
      }
    }
    leaf gateway {
      tailf:info
        "Filtering incoming updates based on gateway";
      tailf:cli-prefix-key;
      tailf:cli-optional-in-sequence;
      tailf:cli-diff-dependency "/ios:ip/prefix-list/prefixes" {
        tailf:xpath-root 3;
      }
      type string {
        tailf:info
          "WORD;;Name of an IP prefix-list";
      }
    }
    leaf route-map {
      tailf:info
        "Filter prefixes based on the route-map";
      tailf:cli-prefix-key;
      tailf:cli-optional-in-sequence;
      type string {
        tailf:info
          "WORD;;route-map name";
      }
    }
  }

  grouping redistribute-ospf-match-grouping {
    leaf match {
      tailf:info
        "Redistribution of OSPF routes";
      tailf:cli-incomplete-command;
      type empty;
    }
    leaf internal {
      when "../match" {
        tailf:xpath-root 3;
        tailf:dependency "../match";
      }
      tailf:info
        "Redistribute OSPF internal routes";
      type empty;
    }
    container external-1 {
      when "../match" {
        tailf:xpath-root 3;
        tailf:dependency "../match";
      }
      tailf:cli-drop-node-name;
      tailf:cli-flatten-container;
      leaf external {
        tailf:info
          "Redistribute OSPF external routes";
        type enumeration {
          enum "1" {
            tailf:info
              "Redistribute external type 1 routes";
          }
        }
      }
    }
    container external-2 {
      when "../match" {
        tailf:xpath-root 3;
        tailf:dependency "../match";
      }
      tailf:cli-drop-node-name;
      tailf:cli-flatten-container;
      leaf external {
        tailf:info
          "Redistribute OSPF external routes";
        type enumeration {
          enum "2" {
            tailf:info
              "Redistribute external type 2 routes";
          }
        }
      }
    }
    container nssa-external-1 {
      when "../match" {
        tailf:xpath-root 3;
        tailf:dependency "../match";
      }
      tailf:cli-drop-node-name;
      tailf:cli-flatten-container;
      leaf nssa-external {
        tailf:info
          "Redistribute OSPF NSSA external routes";
        type enumeration {
          enum "1" {
            tailf:info
              "Redistribute NSSA external type 1 routes";
          }
        }
      }
    }
    container nssa-external-2 {
      when "../match" {
        tailf:xpath-root 3;
        tailf:dependency "../match";
      }
      tailf:cli-drop-node-name;
      tailf:cli-flatten-container;
      leaf nssa-external {
        tailf:info
          "Redistribute OSPF NSSA external routes";
        type enumeration {
          enum "2" {
            tailf:info
              "Redistribute NSSA external type 2 routes";
          }
        }
      }
    }
  }

  grouping router-distribute-list-grouping {
    list distribute-list {
      tailf:info
        "Filter networks in routing updates";
      tailf:cli-suppress-mode;
      tailf:cli-delete-when-empty;
      tailf:cli-compact-syntax;
      tailf:cli-sequence-commands;
      tailf:cli-remove-before-change;
      key "direction";
      leaf direction {
        tailf:cli-diff-dependency "../../distribute-list-interface/distribute-list" {
          tailf:xpath-root 3;
          tailf:cli-trigger-on-set;
        }
        type enumeration {
          enum "in" {
            tailf:info
              "Filter incoming routing updates";
          }
          enum "out" {
            tailf:info
              "Filter outgoing routing updates";
          }
        }
      }
      uses distribute-list-content-grouping;
    }
    container distribute-list-interface {
      tailf:cli-drop-node-name;
      list distribute-list {
        tailf:info
          "Filter networks in routing updates";
        tailf:cli-suppress-mode;
        tailf:cli-delete-when-empty;
        tailf:cli-compact-syntax;
        tailf:cli-sequence-commands;
        tailf:cli-remove-before-change;
        key "direction interface";
        leaf direction {
          type enumeration {
            enum "in" {
              tailf:info
                "Filter incoming routing updates";
            }
            enum "out" {
              tailf:info
                "Filter outgoing routing updates";
            }
          }
        }
        leaf interface {
          tailf:cli-diff-dependency "/ios:interface" {
            tailf:xpath-root 3;
          }
          type string {
            tailf:info
              "WORD;;Interface name";
          }
        }
        uses distribute-list-content-grouping;
      }
    }
  }

  grouping router-offset-list-grouping {
    list offset-list {
      tailf:info
        "Add or subtract offset from metrics";
      tailf:cli-suppress-mode;
      tailf:cli-delete-when-empty;
      tailf:cli-compact-syntax;
      tailf:cli-sequence-commands;
      tailf:cli-incomplete-command;
      key "direction";
      leaf id {
        tailf:cli-drop-node-name;
        tailf:cli-prefix-key;
        type union {
          type uint32 {
            tailf:info
              "<0-99>;;Access list of networks to apply offset (0 selects all networks)";
            range "0..99";
          }
          type uint32 {
            tailf:info
              "<1300-1999>;;Access list of networks to apply offset (expanded range)";
            range "1300..1999";
          }
          type string {
            tailf:info
              "WORD;;Access-list name";
          }
        }
      }
      leaf direction {
        type enumeration {
          enum "in" {
            tailf:info
              "Perform offset on incoming updates";
          }
          enum "out" {
            tailf:info
              "Perform offset on outgoing updates";
          }
        }
      }
      leaf offset {
        tailf:cli-drop-node-name;
        type uint8 {
          tailf:info
            "<0-16>;;Offset";
          range "0..16";
        }
      }
    }
    container offset-list-interface {
      tailf:cli-drop-node-name;
      list offset-list {
        tailf:info
          "Add or subtract offset from metrics";
        tailf:cli-suppress-mode;
        tailf:cli-delete-when-empty;
        tailf:cli-compact-syntax;
        tailf:cli-sequence-commands;
        key "direction interface";
        leaf id {
          tailf:cli-drop-node-name;
          tailf:cli-prefix-key;
          type union {
            type uint32 {
              tailf:info
                "<0-99>;;Access list of networks to apply offset (0 selects all networks)";
              range "0..99";
            }
            type uint32 {
              tailf:info
                "<1300-1999>;;Access list of networks to apply offset (expanded range)";
              range "1300..1999";
            }
            type string {
              tailf:info
                "WORD;;Access-list name";
            }
          }
        }
        leaf direction {
          type enumeration {
            enum "in" {
              tailf:info
                "Perform offset on incoming updates";
            }
            enum "out" {
              tailf:info
                "Perform offset on outgoing updates";
            }
          }
        }
        leaf offset {
          tailf:cli-drop-node-name;
          tailf:cli-prefix-key {
            tailf:cli-before-key 2;
          }
          type uint32 {
            tailf:info
              "<0-2147483647>;;Offset";
          }
        }
        leaf interface {
          tailf:cli-diff-dependency "/ios:interface" {
            tailf:xpath-root 3;
          }
          type string {
            tailf:info
              "WORD;;Interface name";
          }
        }
      }
    }
  }

  grouping passive-interface-grouping {
    container passive-interface {
      tailf:info
        "Suppress routing updates on an interface";
      choice passive-interface-choice {
        leaf default {
          tailf:info
            "Suppress routing updates on all interfaces";
          type empty;
        }
        list interface {
          tailf:cli-drop-node-name;
          tailf:cli-suppress-mode;
          tailf:cli-delete-when-empty;
          key "name";
          leaf name {
            tailf:cli-diff-dependency "/ios:interface" {
              tailf:xpath-root 3;
            }
            type string {
              tailf:info
                "WORD;;Interface name";
            }
          }
        }
      }
    }
    container disable {
      tailf:info
        "Use with 'disable passive-interface' for 'no passive-interface' config";
      when "../passive-interface/default" {
        tailf:xpath-root 3;
        tailf:dependency "../passive-interface/default";
      }
      tailf:cli-diff-dependency "../passive-interface/default" {
        tailf:xpath-root 3;
      }
      list passive-interface {
        tailf:cli-suppress-mode;
        tailf:cli-delete-when-empty;
        tailf:cli-compact-syntax;
        key "interface";
        leaf interface {
          tailf:cli-multi-word-key;
          tailf:cli-diff-dependency "/ios:interface" {
            tailf:xpath-root 3;
          }
          type string {
            tailf:info
              "WORD;;Interface name";
          }
        }
      }
    }
  }

  grouping ip-community-list-grouping {
    list entry {
      tailf:cli-drop-node-name;
      tailf:cli-suppress-mode;
      tailf:cli-delete-when-empty;
      tailf:cli-compact-syntax;
      tailf:cli-show-long-obu-diffs;
      ordered-by user;
      key "expr";
      leaf expr {
        tailf:cli-multi-word-key {
          tailf:cli-max-words 11;
        }
        type string {
          tailf:info
            "<RULE>;;deny <options> | permit <options>";
          pattern '(permit.*)|(deny.*)';
        }
      }
    }
  }

  grouping ip-extcommunity-list-grouping {
    list entry {
      tailf:cli-drop-node-name;
      tailf:cli-suppress-mode;
      tailf:cli-delete-when-empty;
      tailf:cli-compact-syntax;
      tailf:cli-show-long-obu-diffs;
      ordered-by user;
      key "expr";
      leaf expr {
        tailf:cli-multi-word-key;
        type string {
          tailf:info
            "<RULE>;;deny <LINE> | permit <LINE>";
          pattern '(permit.*)|(deny.*)';
        }
      }
    }
  }

  grouping ip-route-options-grouping {
    leaf dhcp {
      tailf:info
        "Default Gateway obtained from DHCP";
      tailf:cli-optional-in-sequence;
      tailf:cli-case-insensitive;
      type empty;
    }
    leaf metric {
      tailf:cli-drop-node-name;
      tailf:cli-break-sequence-commands;
      type uint8 {
        tailf:info
          "<1-255>;;Distance metric for this route";
        range "1..255";
      }
    }
    leaf global {
      tailf:info
        "Next hop address is global";
      type empty;
    }
    leaf name {
      tailf:info
        "Specify name of the next hop";
      type string {
        tailf:info
          "WORD;;Name of the next hop";
      }
    }
    leaf permanent {
      tailf:info
        "permanent route";
      type empty;
    }
    leaf multicast {
      tailf:info
        "multicast route";
      type empty;
    }
    leaf tag {
      tailf:info
        "Set tag for this route";
      type uint32 {
        tailf:info
          "<1-4294967295>;;Tag value";
        range "1..4294967295";
      }
    }
    leaf track {
      tailf:info
        "Install route depending on tracked item";
      type uint16 {
        tailf:info
          "<1-1000>;;tracked object number";
        range "1..1000";
      }
    }
  }

  grouping ip-route-grouping {
    list ip-route-interface-forwarding-list {
      tailf:cli-drop-node-name;
      tailf:cli-suppress-mode;
      tailf:cli-delete-when-empty;
      tailf:cli-compact-syntax;
      tailf:cli-sequence-commands;
      tailf:cli-reset-container;
      key "prefix mask interface forwarding-address";
      leaf prefix {
        tailf:cli-disallow-value "vrf";
        type inet:ipv4-address {
          tailf:info
            "A.B.C.D;;Destination prefix";
        }
      }
      leaf mask {
        type inet:ipv4-address {
          tailf:info
            "A.B.C.D;;Destination prefix mask";
        }
      }
      leaf interface {
        type string {
          tailf:info
            "WORD;;Interface name";
        }
      }
      leaf forwarding-address {
        type union {
          type inet:ipv4-address {
            tailf:info
              "A.B.C.D;;Forwarding router's address";
          }
          type enumeration {
            enum "multicast" {
              tailf:info
                "multicast route";
            }
          }
        }
      }
      uses ip-route-options-grouping;
    }
    list ip-route-forwarding-list {
      tailf:cli-drop-node-name;
      tailf:cli-suppress-mode;
      tailf:cli-delete-when-empty;
      tailf:cli-compact-syntax;
      tailf:cli-sequence-commands;
      tailf:cli-reset-container;
      key "prefix mask forwarding-address";
      leaf prefix {
        tailf:cli-disallow-value "vrf";
        type inet:ipv4-address {
          tailf:info
            "A.B.C.D;;Destination prefix";
        }
      }
      leaf mask {
        type inet:ipv4-address {
          tailf:info
            "A.B.C.D;;Destination prefix mask";
        }
      }
      leaf forwarding-address {
        type inet:ipv4-address {
          tailf:info
            "A.B.C.D;;Forwarding router's address";
        }
      }
      uses ip-route-options-grouping;
    }
    list ip-route-interface-list {
      tailf:cli-drop-node-name;
      tailf:cli-suppress-mode;
      tailf:cli-delete-when-empty;
      tailf:cli-compact-syntax;
      tailf:cli-sequence-commands;
      tailf:cli-reset-container;
      key "prefix mask interface";
      leaf prefix {
        tailf:cli-disallow-value "vrf";
        type inet:ipv4-address {
          tailf:info
            "A.B.C.D;;Destination prefix";
        }
      }
      leaf mask {
        type inet:ipv4-address {
          tailf:info
            "A.B.C.D;;Destination prefix mask";
        }
      }
      leaf interface {
        tailf:cli-disallow-value "metric|global|name|permanent|multicast|tag|track";
        type union {
          type string {
            tailf:info
              "WORD;;Interface name";
          }
          type enumeration {
            enum "dhcp" {
              tailf:info
                "Default Gateway obtained from DHCP";
            }
          }
        }
      }
      uses ip-route-options-grouping;
    }
  }

  grouping ipv6-route-options-grouping {
    leaf distance {
      tailf:cli-drop-node-name;
      tailf:cli-break-sequence-commands;
      type uint8 {
        tailf:info
          "<1-254>;;Administrative distance";
        range "1..254";
      }
    }
    choice type-choice {
      leaf multicast {
        tailf:info
          "Route only usable by multicast";
        tailf:cli-full-command;
        type empty;
      }
      leaf unicast {
        tailf:info
          "Route only usable by unicast";
        type empty;
      }
    }
    leaf tag {
      tailf:info
        "Tag value";
      tailf:cli-full-command;
      type uint32 {
        tailf:info
          "<0-4294967295>;;Tag value";
      }
    }
  }

  grouping ipv6-route-grouping {
    list ipv6-route-interface-destination-list {
      tailf:cli-drop-node-name;
      tailf:cli-suppress-mode;
      tailf:cli-delete-when-empty;
      tailf:cli-compact-syntax;
      tailf:cli-sequence-commands {
        tailf:cli-reset-all-siblings;
      }
      key "prefix interface destination";
      leaf prefix {
        tailf:cli-disallow-value "vrf";
        type ipv6-prefix {
          tailf:info
            "X:X:X:X::X/<0-128>;;IPv6 prefix x:x::y/<z>";
        }
      }
      leaf interface {
        tailf:cli-diff-dependency "../../../../../interface" {
          tailf:xpath-root 3;
        }
        type string {
          tailf:info
            "WORD;;Interface name";
        }
      }
      leaf destination {
        type inet:ipv6-address {
          tailf:info
            "X:X:X:X::X;;IPv6 address of next-hop";
        }
      }
      uses ipv6-route-options-grouping;
    }
    list ipv6-route-destination-list {
      tailf:cli-drop-node-name;
      tailf:cli-suppress-mode;
      tailf:cli-delete-when-empty;
      tailf:cli-compact-syntax;
      tailf:cli-sequence-commands {
        tailf:cli-reset-all-siblings;
      }
      key "prefix destination";
      leaf prefix {
        tailf:cli-disallow-value "vrf";
        type ipv6-prefix {
          tailf:info
            "X:X:X:X::X/<0-128>;;IPv6 prefix x:x::y/<z>";
        }
      }
      leaf destination {
        type inet:ipv6-address {
          tailf:info
            "X:X:X:X::X;;IPv6 address of next-hop";
        }
      }
      uses ipv6-route-options-grouping;
    }
    list ipv6-route-interface-list {
      tailf:cli-drop-node-name;
      tailf:cli-suppress-mode;
      tailf:cli-delete-when-empty;
      tailf:cli-compact-syntax;
      tailf:cli-sequence-commands {
        tailf:cli-reset-all-siblings;
      }
      key "prefix interface";
      leaf prefix {
        tailf:cli-disallow-value "vrf";
        type ipv6-prefix {
          tailf:info
            "X:X:X:X::X/<0-128>;;IPv6 prefix x:x::y/<z>";
        }
      }
      leaf interface {
        tailf:cli-diff-dependency "../../../../../interface" {
          tailf:xpath-root 3;
        }
        type string {
          tailf:info
            "WORD;;Interface name";
        }
      }
      uses ipv6-route-options-grouping;
    }
  }

  grouping random-detect-grouping {
    leaf min-threshold {
      tailf:cli-drop-node-name;
      tailf:cli-incomplete-command;
      type uint32 {
        tailf:info
          "<1-262143>;;minimum threshold (in packet by default)";
      }
    }
    leaf min-threshold-unit {
      tailf:cli-drop-node-name;
      tailf:cli-optional-in-sequence;
      type enumeration {
        enum "bytes" {
          tailf:info
            "number of bytes";
        }
        enum "ms" {
          tailf:info
            "milliseconds";
        }
        enum "us" {
          tailf:info
            "microseconds";
        }
      }
    }
    leaf max-threshold {
      tailf:cli-drop-node-name;
      type uint32 {
        tailf:info
          "<1-262143>;;maximum threshold (number of packets)";
      }
    }
    leaf max-threshold-unit {
      tailf:cli-drop-node-name;
      tailf:cli-optional-in-sequence;
      type enumeration {
        enum "bytes" {
          tailf:info
            "number of bytes";
        }
        enum "ms" {
          tailf:info
            "milliseconds";
        }
        enum "us" {
          tailf:info
            "microseconds";
        }
      }
    }
    leaf denominator {
      tailf:cli-drop-node-name;
      type uint32 {
        tailf:info
          "<1-65535>;;mark probability denominator";
      }
    }
  }

  grouping random-detect-values-grouping {
    leaf minimum-thresh {
      tailf:info
        "minimum threshold for red aggregate";
      tailf:cli-incomplete-command;
      type uint32 {
        tailf:info
          "<1-512000000>;;minimum threshold (number of packets)";
      }
    }
    leaf maximum-thresh {
      tailf:info
        "maximum threshold for red aggregate";
      type uint32 {
        tailf:info
          "<1-512000000>;;maximum threshold (number of packets)";
      }
    }
    leaf mark-prob {
      tailf:info
        "mark-probability for red aggregate";
      type uint32 {
        tailf:info
          "<0-65535>;;mark probability denominator";
        range "0..65535";
      }
    }
  }

  grouping class-map-match-grouping {
    container access-group {
      tailf:info
        "Access group";
      leaf-list index {
        tailf:cli-drop-node-name;
        tailf:cli-list-syntax;
        type uint32 {
          tailf:info
            "<1-2799>;;Access list index";
          range "1..2799";
        }
      }
      leaf-list name {
        tailf:info
          "Named Access List";
        tailf:cli-list-syntax;
        type string {
          tailf:info
            "WORD;;Access List name";
        }
      }
    }
    leaf any {
      tailf:info
        "Any packets";
      type empty;
    }
    leaf-list class-map {
      tailf:info
        "Class map";
      tailf:cli-list-syntax;
      tailf:non-strict-leafref {
        path "/ncs:devices/ncs:device/ncs:config/ios:class-map/name" {
          tailf:xpath-root 3;
        }
      }
      type string {
        tailf:info
          "WORD;;Match class-map name";
      }
    }
    leaf-list cos {
      tailf:info
        "IEEE 802.1Q/ISL class of service/user priority values";
      tailf:cli-flat-list-syntax;
      tailf:cli-disallow-value "inner";
      max-elements 8;
      type uint16 {
        tailf:info
          "<0-7>;;Enter up to 8 class-of-service values separated by white-spaces";
        range "0..7";
      }
    }
    container cos-inner {
      tailf:cli-drop-node-name;
      container cos {
        tailf:info
          "IEEE 802.1Q/ISL class of service/user priority values";
        leaf-list inner {
          tailf:info
            "ATM VC configured as Access VC class of service/user priority values";
          tailf:cli-flat-list-syntax;
          max-elements 8;
          type uint16 {
            tailf:info
              "<0-7>;;Enter up to 8 class-of-service values separated by white-spaces";
            range "0..7";
          }
        }
      }
    }
    container destination-address {
      tailf:info
        "Destination address";
      leaf-list mac {
        tailf:info
          "MAC address";
        tailf:cli-list-syntax;
        type string {
          tailf:info
            "H.H.H;;MAC address";
        }
      }
    }
    leaf-list discard-class {
      tailf:info
        "Discard behavior identifier";
      tailf:cli-list-syntax;
      type uint8 {
        tailf:info
          "<0-7>;;Discard Class value";
        range "0..7";
      }
    }
    leaf-list dscp {
      tailf:info
        "Match DSCP in IP(v4) and IPv6 packets";
      tailf:cli-flat-list-syntax;
      tailf:cli-full-command;
      tailf:meta-data "max-values" {
        tailf:meta-value "2 :: 8";
      }
      type dscp-type;
    }
    leaf fr-de {
      tailf:info
        "Match on Frame-relay DE bit";
      type empty;
    }
    leaf-list fr-dlci {
      tailf:info
        "Match on fr-dlci";
      tailf:cli-list-syntax;
      type uint16 {
        tailf:info
          "<16-1007>;;frame-relay dlci number";
        range "16..1007";
      }
    }
    leaf-list input-interface {
      tailf:info
        "Select an input interface to match";
      tailf:cli-list-syntax;
      type string {
        tailf:info
          "WORD;;Interface name";
      }
    }
    container ip {
      tailf:info
        "IP specific values";
      leaf-list dscp {
        tailf:info
          "Match IP DSCP (DiffServ CodePoints)";
        tailf:cli-flat-list-syntax;
        type dscp-type;
      }
      leaf-list precedence {
        tailf:info
          "Match IP precedence";
        tailf:cli-flat-list-syntax;
        type precedence-type;
      }
      list rtp {
        tailf:info
          "Match RTP port nos";
        tailf:cli-suppress-mode;
        tailf:cli-delete-when-empty;
        key "port1 port2";
        leaf port1 {
          type uint16 {
            tailf:info
              "<2000-65535>;;Lower bound of UDP destination port";
            range "2000..65535";
          }
        }
        leaf port2 {
          type uint16 {
            tailf:info
              "<0-16383>;;Range of UDP ports";
            range "0..16383";
          }
        }
      }
    }
    container mpls {
      tailf:info
        "Multi Protocol Label Switching specific values";
      container experimental {
        tailf:info
          "Match MPLS experimental";
        leaf-list topmost {
          tailf:info
            "Match MPLS experimental value on topmost label";
          tailf:cli-flat-list-syntax;
          type uint16 {
            tailf:info
              "<0-7>;;Enter up to 8 experimental values separated by white-spaces";
            range "0..7";
          }
        }
      }
    }
    leaf-list precedence {
      tailf:info
        "Match Precedence in IP(v4) and IPv6 packets";
      tailf:cli-flat-list-syntax;
      type precedence-type;
    }
    container protocol {
      tailf:info
        "Protocol";
      container attribute {
        tailf:info
          "Attribute based protocol match";
        list category {
          tailf:info
            "Category attribute";
          tailf:cli-suppress-mode;
          tailf:cli-delete-when-empty;
          key "category-type";
          leaf category-type {
            type enumeration {
              enum "voice-and-video" {
                tailf:info
                  "Filter incoming connections";
              }
              enum "database" {
                tailf:info
                  "Filter outgoing connections";
              }
              enum "email" {
                tailf:info
                  "Email related applications";
              }
              enum "browsing" {
                tailf:info
                  "Browsing related applications";
              }
              enum "trojan" {
                tailf:info
                  "Trojan related applications";
              }
              enum "gaming" {
                tailf:info
                  "Gaming related applications";
              }
              enum "anonymizers" {
                tailf:info
                  "Anonymizers applications";
              }
              enum "backup-and-storage" {
                tailf:info
                  "Backup and storage related applications";
              }
              enum "business-and-productivity-tools" {
                tailf:info
                  "Business-and-productivity-tools related applications";
              }
              enum "epayement" {
                tailf:info
                  "Epayement related applications";
              }
              enum "file-sharing" {
                tailf:info
                  "File-sharing related applications";
              }
              enum "industrial-protocols" {
                tailf:info
                  "Industrial-protocols related applications";
              }
              enum "instant-messaging" {
                tailf:info
                  "Instant-messaging related applications";
              }
              enum "inter-process-rpc" {
                tailf:info
                  "Inter-process-rpc related applications";
              }
              enum "internet-security" {
                tailf:info
                  "Internet security related applications";
              }
              enum "layer3-over-ip" {
                tailf:info
                  "Layer3-over-IP related applications";
              }
              enum "location-based-services" {
                tailf:info
                  "Location-based-services related applications";
              }
              enum "net-admin" {
                tailf:info
                  "Net-admin related applications";
              }
              enum "newsgroup" {
                tailf:info
                  "Newsgroup related applications";
              }
              enum "other" {
                tailf:info
                  "Other related applications";
              }
              enum "social-networking" {
                tailf:info
                  "Social-networking related applications";
              }
              enum "software-updates" {
                tailf:info
                  "Software updates and downloads related applications";
              }
            }
          }
        }
        list traffic-class {
          tailf:info
            "traffic-class attribute";
          tailf:cli-suppress-mode;
          tailf:cli-delete-when-empty;
          key "traffic-class-type";
          leaf traffic-class-type {
            type enumeration {
              enum "broadcast-video" {
                tailf:info
                  "Broadcast TV, live events, video surveillance";
              }
              enum "bulk-data" {
                tailf:info
                  "Non-interactive data applications";
              }
              enum "multimedia-conferencing" {
                tailf:info
                  "Desktop software multimedia collaboration applications";
              }
              enum "multimedia-streaming" {
                tailf:info
                  "Video-on-Demand (VoD) streaming video";
              }
              enum "network-control" {
                tailf:info
                  "Network control plane traffic";
              }
              enum "ops-admin-mgmt" {
                tailf:info
                  "Network operations, administration, and management";
              }
              enum "real-time-interactive" {
                tailf:info
                  "High-definition interactive video applications";
              }
              enum "signaling" {
                tailf:info
                  "Signaling traffic that supports IP voice and video telephony";
              }
              enum "transactional-data" {
                tailf:info
                  "Interactive data applications";
              }
              enum "voip-telephony" {
                tailf:info
                  "VoIP telephony (bearer-only) traffic";
              }
            }
          }
        }
        list business-relevance {
          tailf:info
            "business-relevance attribute";
          tailf:cli-suppress-mode;
          tailf:cli-delete-when-empty;
          key "business-relevance-type";
          leaf business-relevance-type {
            type enumeration {
              enum "business-irrelevant" {
                tailf:info
                  "Undesirable business traffic";
              }
              enum "business-relevant" {
                tailf:info
                  "Business critical applications";
              }
              enum "default" {
                tailf:info
                  "Related business applications";
              }
            }
          }
        }
      }
      list protocol-list {
        tailf:cli-drop-node-name;
        tailf:cli-suppress-mode;
        tailf:cli-delete-when-empty;
        key "name";
        leaf name {
          tailf:cli-disallow-value "attribute";
          type string {
            tailf:info
              "WORD;;protocol";
          }
        }
        list values {
          tailf:cli-drop-node-name;
          tailf:cli-suppress-mode;
          tailf:cli-delete-when-empty;
          tailf:cli-show-long-obu-diffs;
          ordered-by user;
          key "value";
          leaf value {
            tailf:cli-multi-word-key;
            type string;
          }
        }
      }
    }
    container packet {
      tailf:info
        "Layer 3 Packet length";
      list length {
        tailf:info
          "Layer 3 Packet length";
        tailf:cli-suppress-mode;
        tailf:cli-delete-when-empty;
        tailf:cli-show-long-obu-diffs;
        ordered-by user;
        key "line";
        leaf line {
          tailf:cli-multi-word-key;
          type string {
            tailf:info
              "LINE;;min X | max X | min X max Y";
            pattern '(min \d+)|(max \d+)|(min \d+ max \d+)';
          }
        }
      }
    }
    leaf-list qos-group {
      tailf:info
        "Qos-group";
      tailf:cli-list-syntax;
      type uint16 {
        tailf:info
          "<0-99>;;Qos Group value";
        range "0..99";
      }
    }
    container source-address {
      tailf:info
        "Source address";
      leaf-list mac {
        tailf:info
          "MAC address";
        tailf:cli-list-syntax;
        type string {
          tailf:info
            "H.H.H;;MAC address";
        }
      }
    }
    leaf-list vlan {
      tailf:info
        "VLANs to match";
      tailf:cli-range-list-syntax;
      type uint16 {
        tailf:info
          "<1-4094>;;VLAN id";
        range "1..4094";
      }
    }
    container service {
      tailf:info
        "Service Instance to match";
      container instance {
        tailf:info
          "Service Instance to match";
        leaf-list ethernet {
          tailf:info
            "Service Instance to match";
          tailf:cli-list-syntax;
          type uint32 {
            tailf:info
              "<1-4294967295>;;Service Instance Identifier";
          }
        }
      }
    }
  }

  grouping ip-name-server-grouping {
    list name-server-list {
      tailf:cli-drop-node-name;
      tailf:cli-suppress-mode;
      tailf:cli-delete-when-empty;
      tailf:cli-show-long-obu-diffs;
      ordered-by user;
      max-elements 6;
      key "address";
      leaf address {
        type union {
          type inet:ipv4-address {
            tailf:info
              "A.B.C.D;;Domain server IP address (maximum of 6)";
          }
          type inet:ipv6-address {
            tailf:info
              "X:X:X:X::X;;Domain server IPv6 address (maximum of 6)";
          }
        }
      }
    }
  }

  grouping ip-host-grouping {
    list host-list {
      tailf:cli-drop-node-name;
      tailf:cli-suppress-mode;
      tailf:cli-delete-when-empty;
      tailf:cli-compact-syntax;
      tailf:cli-sequence-commands;
      tailf:cli-incomplete-command;
      key "hostname";
      leaf hostname {
        tailf:cli-disallow-value "vrf";
        type string {
          tailf:info
            "WORD;;Name of host";
        }
      }
      leaf tcp-port-number {
        tailf:cli-drop-node-name;
        tailf:cli-optional-in-sequence;
        tailf:cli-incomplete-command;
        type uint16 {
          tailf:info
            "<0-65535>;;Default telnet port number";
        }
      }
      leaf-list ip-address1 {
        tailf:cli-drop-node-name;
        tailf:cli-flat-list-syntax;
        tailf:cli-replace-all;
        type inet:ipv4-address {
          tailf:info
            "A.B.C.D;;Host IP address";
        }
      }
    }
  }

  grouping ip-dhcp-excluded-address-grouping {
    list low-list {
      tailf:cli-drop-node-name;
      tailf:cli-suppress-mode;
      tailf:cli-delete-when-empty;
      key "low";
      leaf low {
        tailf:cli-disallow-value "vrf";
        type inet:ipv4-address {
          tailf:info
            "A.B.C.D;;Low IP address";
        }
      }
    }
    list low-high-list {
      tailf:cli-drop-node-name;
      tailf:cli-suppress-mode;
      tailf:cli-delete-when-empty;
      key "low high";
      leaf low {
        tailf:cli-disallow-value "vrf";
        type inet:ipv4-address {
          tailf:info
            "A.B.C.D;;Low IP address";
        }
      }
      leaf high {
        tailf:cli-disallow-value "vrf";
        type inet:ipv4-address {
          tailf:info
            "A.B.C.D;;High IP address";
        }
      }
    }
  }

  grouping ntp-peer-grouping {
    list peer-list {
      tailf:cli-drop-node-name;
      tailf:cli-suppress-mode;
      tailf:cli-delete-when-empty;
      tailf:cli-compact-syntax;
      tailf:cli-reset-container;
      key "name";
      leaf name {
        tailf:cli-disallow-value "vrf";
        type inet:host {
          tailf:info
            "Hostname, A.B.C.D or X:X:X:X::X;;Address of peer";
        }
      }
      leaf burst {
        tailf:info
          "Send a burst when peer is reachable (Default)";
        type empty;
      }
      leaf iburst {
        tailf:info
          "Send a burst when peer is unreachable (Default)";
        type empty;
      }
      leaf key {
        tailf:info
          "Configure peer authentication key";
        type uint32 {
          tailf:info
            "<1-4294967295>;;Peer key number";
          range "1..4294967295";
        }
      }
      leaf maxpoll {
        tailf:info
          "Maximum poll interval";
        type uint8 {
          tailf:info
            "<4-17>;;Poll value in Log2";
          range "4..17";
        }
      }
      leaf minpoll {
        tailf:info
          "Minimum poll interval";
        type uint8 {
          tailf:info
            "<4-17>;;Poll value in Log2";
          range "4..17";
        }
      }
      leaf normal-sync {
        tailf:info
          "Disable rapid sync at startup";
        type empty;
      }
      leaf prefer {
        tailf:info
          "Prefer this peer when possible";
        type empty;
      }
      container source {
        tailf:info
          "Interface for source address";
        tailf:cli-flatten-container;
        tailf:cli-compact-syntax;
        uses interface-name-grouping;
      }
      leaf version {
        tailf:info
          "Configure NTP version";
        type uint8 {
          tailf:info
            "<1-4>;;NTP version number";
        }
      }
    }
  }

  grouping sntp-server-grouping {
    list server-list {
      tailf:cli-drop-node-name;
      tailf:cli-suppress-mode;
      tailf:cli-delete-when-empty;
      tailf:cli-compact-syntax;
      tailf:cli-reset-container;
      key "name";
      leaf name {
        tailf:cli-disallow-value "vrf";
        type inet:host {
          tailf:info
            "Hostname, A.B.C.D or X:X:X:X::X;;Address of peer";
        }
      }
      leaf key {
        tailf:info
          "Configure server authentication key";
        type uint32 {
          tailf:info
            "<1-4294967295>;;Server key number";
          range "1..4294967295";
        }
      }
      leaf version {
        tailf:info
          "Configure NTP version";
        type uint8 {
          tailf:info
            "<1-4>;;NTP version number";
        }
      }
    }
  }

  grouping line-grouping {
    leaf location {
      tailf:info
        "Enter terminal location description";
      tailf:cli-multi-value;
      tailf:cli-preformatted;
      tailf:cli-full-command;
      type string {
        tailf:info
          "LINE;;One text line describing the terminal's location";
      }
    }
    leaf absolute-timeout {
      tailf:info
        "Set absolute timeout for line disconnection";
      tailf:cli-full-command;
      type uint32 {
        tailf:info
          "<0-10000>;;Absolute timeout interval in minutes";
      }
    }
    container access-class {
      tailf:info
        "Filter connections based on an IP access list";
      tailf:cli-flatten-container;
      tailf:cli-compact-syntax;
      tailf:cli-sequence-commands {
        tailf:cli-reset-siblings;
      }
      list access-list {
        tailf:cli-drop-node-name;
        tailf:cli-suppress-mode;
        tailf:cli-delete-when-empty;
        tailf:cli-compact-syntax;
        tailf:cli-sequence-commands {
          tailf:cli-reset-siblings;
        }
        key "direction";
        leaf direction {
          type enumeration {
            enum "in" {
              tailf:info
                "Filter incoming connections";
            }
            enum "out" {
              tailf:info
                "Filter outgoing connections";
            }
          }
        }
        leaf access-list {
          tailf:cli-drop-node-name;
          tailf:cli-prefix-key;
          type exp-ip-acl-type;
        }
        leaf vrf-also {
          tailf:info
            "Same access list is applied for all VRFs";
          type empty;
        }
      }
    }
    leaf flush-at-activation {
      tailf:info
        "Clear input stream at activation";
      tailf:cli-boolean-no;
      tailf:cli-full-command;
      type boolean;
      default "true";
    }
    container activation-character-choice {
      tailf:cli-drop-node-name;
      choice activation-character-choice {
        leaf activation-character {
          tailf:info
            "Define the activation character";
          tailf:cli-boolean-no;
          type boolean;
          default "true";
        }
        container activation-character-conf {
          tailf:cli-drop-node-name;
          tailf:cli-incomplete-command;
          tailf:cli-incomplete-no;
          leaf activation-character {
            type string {
              tailf:info
                "CHAR or <0-127>;;Activation character or its decimal equivalent";
            }
          }
        }
      }
    }
    leaf escape-character {
      tailf:info
        "Change the current line's escape character";
      type union {
        type uint8 {
          tailf:info
            "ASCII decimal equivalent";
        }
        type enumeration {
          enum "BREAK" {
            tailf:info
              "Cause escape on BREAK";
          }
          enum "DEFAULT" {
            tailf:info
              "Use default escape character";
          }
          enum "NONE" {
            tailf:info
              "Disable escape entirely";
          }
        }
      }
    }
    container script {
      tailf:info
        "specify event related chat scripts to run on the line";
      leaf dialer {
        tailf:info
          "chat script to run whenever dialer makes an outgoing call";
        tailf:non-strict-leafref {
          path "/ncs:devices/ncs:device/ncs:config/ios:chat-script/name" {
            tailf:xpath-root 3;
          }
        }
        type string {
          tailf:info
            "WORD;;chat script name";
        }
      }
    }
    container modem {
      tailf:info
        "Configure the Modem Control Lines";
      leaf enable {
        tailf:info
          "Console port is used for connecting modem";
        tailf:cli-boolean-no;
        type boolean;
      }
      leaf InOut {
        tailf:info
          "Configure line for incoming AND outgoing use of modem";
        type empty;
      }
      container autoconfigure {
        tailf:info
          "Automatically configure modem on line";
        leaf discovery {
          tailf:info
            "Attempt to determine modem type automatically";
          type empty;
        }
        leaf type {
          tailf:info
            "Specify modem type";
          type string {
            tailf:info
              "WORD;;Modem type";
          }
        }
      }
    }
    container exec-choice {
      tailf:cli-drop-node-name;
      choice exec-choice {
        default "exec";
        leaf exec {
          tailf:info
            "Configure EXEC";
          tailf:cli-boolean-no;
          type boolean;
          default "true";
        }
        container exec-conf {
          tailf:cli-drop-node-name;
          tailf:cli-incomplete-command;
          tailf:cli-incomplete-no;
          container exec {
            tailf:cli-incomplete-command;
            tailf:cli-incomplete-no;
            container prompt {
              tailf:info
                "EXEC prompt";
              leaf timestamp {
                tailf:info
                  "Print timestamps for show commands";
                type empty;
              }
            }
          }
        }
      }
    }
    container exec-timeout {
      tailf:info
        "Set the EXEC timeout";
      tailf:cli-compact-syntax;
      tailf:cli-sequence-commands;
      leaf minutes {
        tailf:cli-drop-node-name;
        type uint32 {
          tailf:info
            "<0-35791>;;Timeout in minutes";
        }
      }
      leaf seconds {
        tailf:cli-drop-node-name;
        type uint32 {
          tailf:info
            "<0-2147483>;;Timeout in seconds";
        }
      }
    }
    container timeout {
      tailf:info
        "Timeouts for the line";
      container login {
        tailf:info
          "Timeouts related to the login sequence";
        leaf response {
          tailf:info
            "Timeout for any user input during login sequences";
          type uint16 {
            tailf:info
              "<1-300>;;Timeout in seconds";
            range "1..300";
          }
        }
      }
    }
    container session-disconnect-warning {
      tailf:info
        "Set warning countdown for session-timeout";
      tailf:cli-compact-syntax;
      tailf:cli-sequence-commands {
        tailf:cli-reset-siblings;
      }
      leaf seconds {
        tailf:cli-drop-node-name;
        type uint32 {
          tailf:info
            "<0-4294967295>;;Session timeout warning in seconds";
        }
      }
      leaf message {
        tailf:info
          "Optional warning message";
        tailf:cli-multi-value;
        type string {
          tailf:info
            "LINE;;One text line optional warning message";
        }
      }
    }
    container logging {
      tailf:info
        "Modify message logging facilities";
      container synchronous {
        tailf:info
          "Synchronized message output";
        tailf:cli-delete-when-empty;
        presence "true";
        leaf level {
          tailf:info
            "Severity level to output asynchronously";
          type union {
            type uint8 {
              tailf:info
                "<0-7>;;Severity level; lower number for higher severity";
              range "0..7";
            }
            type enumeration {
              enum "all" {
                tailf:info
                  "Turn off all severity level for asynchronous output";
              }
            }
          }
        }
      }
    }
    leaf rotary {
      tailf:info
        "Add line to a rotary group";
      type uint8 {
        tailf:info
          "<0-100>;;Rotary group to add line to";
        range "0..100";
      }
    }
    container login {
      tailf:info
        "Enable password checking";
      tailf:cli-delete-when-empty;
      presence "true";
      leaf local {
        tailf:info
          "Local password checking";
        type empty;
      }
    }
    container local-authentication {
      tailf:cli-drop-node-name;
      container login {
        tailf:info
          "Enable password checking";
        tailf:cli-incomplete-command;
        tailf:cli-incomplete-no;
        leaf tacacs {
          type empty;
        }
        leaf authentication {
          tailf:info
            "Authentication parameters.";
          type union {
            type string {
              tailf:info
                "WORD;;Use an authentication list with this name.";
            }
            type enumeration {
              enum "default" {
                tailf:info
                  "Use the default authentication list.";
              }
            }
          }
          default "default";
        }
      }
    }
    container autocommand {
      tailf:info
        "Automatically execute an EXEC command";
      leaf command {
        tailf:cli-drop-node-name;
        tailf:cli-multi-value;
        type string {
          tailf:info
            "LINE;;Appropriate EXEC command";
        }
      }
    }
    container accounting {
      tailf:info
        "Accounting parameters";
      leaf exec {
        tailf:info
          "For starting an exec (shell)";
        type union {
          type string {
            tailf:info
              "WORD;;Use an accounting list with this name";
          }
          type enumeration {
            enum "default" {
              tailf:info
                "Use the default accounting list.";
            }
          }
        }
        default "default";
      }
      list commands {
        tailf:info
          "For exec (shell) commands.";
        tailf:cli-suppress-mode;
        tailf:cli-delete-when-empty;
        tailf:cli-compact-syntax;
        tailf:cli-incomplete-command;
        key "level";
        leaf level {
          type uint8 {
            tailf:info
              "<0-15>;;Enable level";
            range "0..15";
          }
        }
        leaf name {
          tailf:cli-drop-node-name;
          type union {
            type string {
              tailf:info
                "WORD;;Use an accounting list with this name";
            }
            type enumeration {
              enum "default" {
                tailf:info
                  "Use the default accounting list";
              }
            }
          }
          default "default";
        }
      }
    }
    leaf logout-warning {
      tailf:info
        "Set Warning countdown for absolute timeout of line";
      tailf:cli-full-command;
      type uint32 {
        tailf:info
          "<0-4294967295>;;Warning time in seconds";
      }
    }
    container ipv6 {
      tailf:info
        "IPv6 options";
      list access-class {
        tailf:info
          "Filter connections based on an IPv6 access list";
        tailf:cli-suppress-mode;
        tailf:cli-delete-when-empty;
        tailf:cli-compact-syntax;
        tailf:cli-sequence-commands;
        key "direction";
        leaf direction {
          type enumeration {
            enum "in" {
              tailf:info
                "Filter incoming connections";
            }
            enum "out" {
              tailf:info
                "Filter outgoing connections";
            }
          }
        }
        leaf access-list {
          tailf:cli-drop-node-name;
          tailf:cli-prefix-key;
          type exp-ip-acl-type;
        }
      }
    }
    container authorization {
      tailf:info
        "Authorization parameters";
      leaf exec {
        tailf:info
          "For starting an exec (shell)";
        type union {
          type enumeration {
            enum "default" {
              tailf:info
                "Use the default authorization list";
            }
          }
          type string {
            tailf:info
              "WORD;;Use an authorization list with this name";
          }
        }
        default "default";
      }
      list commands {
        tailf:info
          "For exec (shell) commands.";
        tailf:cli-suppress-mode;
        tailf:cli-delete-when-empty;
        tailf:cli-compact-syntax;
        tailf:cli-incomplete-command;
        key "level";
        leaf level {
          type uint8 {
            tailf:info
              "<0-15>;;Enable level";
            range "0..15";
          }
        }
        leaf name {
          tailf:cli-drop-node-name;
          type union {
            type string {
              tailf:info
                "WORD;;Use an authorization list with this name";
            }
            type enumeration {
              enum "default" {
                tailf:info
                  "Use the default authorization list";
              }
            }
          }
          default "default";
        }
      }
    }
    container history {
      tailf:info
        "Enable and control the command history function";
      leaf size {
        tailf:info
          "Set history buffer size";
        type uint16 {
          tailf:info
            "<0-256>;;Size of history buffer";
          range "0..256";
        }
      }
    }
    leaf full-help {
      tailf:info
        "Provide help to unprivileged user";
      type empty;
    }
    container password {
      tailf:info
        "Set a password";
      tailf:cli-compact-syntax;
      tailf:cli-sequence-commands;
      uses password-grouping;
    }
    container privilege {
      tailf:info
        "Change privilege level for line";
      leaf level {
        tailf:info
          "Assign default privilege level for line";
        type uint8 {
          tailf:info
            "<0-15>;;Default privilege level for line";
          range "0..15";
        }
      }
    }
    container session-timeout {
      tailf:info
        "Set interval for closing connection when there is no input traffic";
      tailf:cli-sequence-commands;
      tailf:cli-compact-syntax;
      leaf session-timeout-value {
        tailf:cli-drop-node-name;
        type uint16 {
          tailf:info
            "<0-35791>;;Session timeout interval in minutes";
          range "0..35791";
        }
      }
      leaf output {
        tailf:info
          "Include output traffic as well as input traffic";
        type empty;
      }
    }
    leaf stopbits {
      tailf:info
        "Set async line stop bits";
      type enumeration {
        enum "1" {
          tailf:info
            "One stop bit";
        }
        enum "1.5" {
          tailf:info
            "One and one-half stop bits";
        }
        enum "2" {
          tailf:info
            "Two stop bits";
        }
      }
    }
    container telnet {
      tailf:info
        "Telnet protocol-specific configuration";
      leaf transparent {
        tailf:info
          "Send a CR as a CR followed by a NULL instead of a CR followed by a LF";
        type empty;
      }
    }
    container transport {
      tailf:info
        "Define transport protocols for line";
      tailf:cli-incomplete-no;
      leaf-list input {
        tailf:info
          "Define which protocols to use when connecting to the terminal server";
        tailf:cli-flat-list-syntax;
        tailf:cli-replace-all;
        tailf:cli-no-value-on-delete;
        type enumeration {
          enum "all" {
            tailf:info
              "All protocols";
          }
          enum "none" {
            tailf:info
              "No protocols";
          }
          enum "ssh" {
            tailf:info
              "TCP/IP SSH protocol";
          }
          enum "telnet" {
            tailf:info
              "TCP/IP Telnet protocol";
          }
          enum "lat" {
            tailf:info
              "DEC LAT protocol";
          }
          enum "pad" {
            tailf:info
              "X.3 PAD";
          }
          enum "udptn" {
            tailf:info
              "UDPTN async via UDP protocol";
          }
          enum "rlogin" {
            tailf:info
              "Unix rlogin protocol";
          }
          enum "lapb-ta";
          enum "mop";
          enum "v120";
          enum "acercon";
        }
      }
      leaf-list output {
        tailf:info
          "Define which protocols to use for outgoing connections";
        tailf:cli-flat-list-syntax;
        tailf:cli-replace-all;
        tailf:cli-no-value-on-delete;
        type enumeration {
          enum "all" {
            tailf:info
              "All protocols";
          }
          enum "none" {
            tailf:info
              "No protocols";
          }
          enum "ssh" {
            tailf:info
              "TCP/IP SSH protocol";
          }
          enum "telnet" {
            tailf:info
              "TCP/IP Telnet protocol";
          }
          enum "lat" {
            tailf:info
              "DEC LAT protocol";
          }
          enum "pad" {
            tailf:info
              "X.3 PAD";
          }
          enum "udptn" {
            tailf:info
              "UDPTN async via UDP protocol";
          }
          enum "rlogin" {
            tailf:info
              "Unix rlogin protocol";
          }
          enum "lapb-ta";
          enum "mop";
          enum "v120";
        }
      }
      leaf preferred {
        tailf:info
          "Specify the preferred protocol to use";
        tailf:cli-no-value-on-delete;
        type enumeration {
          enum "none" {
            tailf:info
              "No protocols";
          }
          enum "ssh" {
            tailf:info
              "TCP/IP SSH protocol";
          }
          enum "telnet" {
            tailf:info
              "TCP/IP Telnet protocol";
          }
        }
      }
    }
    leaf speed {
      tailf:info
        "Set the transmit and receive speeds";
      tailf:cli-full-command;
      type uint32 {
        tailf:info
          "<0-4294967295>;;Transmit and receive speeds";
      }
    }
    leaf rxspeed {
      tailf:info
        "Set the receive speed";
      type uint32 {
        tailf:info
          "<0-4294967295>;;Receive speed";
      }
    }
    leaf txspeed {
      tailf:info
        "Set the transmit speed";
      type uint32 {
        tailf:info
          "<0-4294967295>;;Transmit speed";
      }
    }
    leaf flowcontrol {
      tailf:info
        "Set the flow control";
      type enumeration {
        enum "hardware" {
          tailf:info
            "Set hardware flow control";
        }
        enum "software" {
          tailf:info
            "Set software flow control";
        }
      }
    }
    leaf length {
      tailf:info
        "Set number of lines on a screen";
      tailf:cli-full-command;
      type uint16 {
        tailf:info
          "<0-512>;;Number of lines on screen (0 for no pausing)";
        range "0..512";
      }
    }
    leaf width {
      tailf:info
        "Set width of the display terminal";
      tailf:cli-full-command;
      type uint16 {
        tailf:info
          "Number of characters on a screen line";
        range "0..512";
      }
    }
  }

  grouping queue-size-grouping {
    leaf queue-size-1 {
      tailf:cli-drop-node-name;
      type uint8 {
        tailf:info
          "<1-100>;;enter percent of queue size between 1 and 100";
        range "1..100";
      }
    }
    leaf queue-size-2 {
      tailf:cli-drop-node-name;
      type uint8 {
        tailf:info
          "<1-100>;;enter percent of queue size between 1 and 100";
        range "1..100";
      }
    }
    leaf queue-size-3 {
      tailf:cli-drop-node-name;
      type uint8 {
        tailf:info
          "<1-100>;;enter percent of queue size between 1 and 100";
        range "1..100";
      }
    }
    leaf queue-size-4 {
      tailf:cli-drop-node-name;
      type uint8 {
        tailf:info
          "<1-100>;;enter percent of queue size between 1 and 100";
        range "1..100";
      }
    }
    leaf queue-size-5 {
      tailf:cli-drop-node-name;
      type uint8 {
        tailf:info
          "<1-100>;;enter percent of queue size between 1 and 100";
        range "1..100";
      }
    }
    leaf queue-size-6 {
      tailf:cli-drop-node-name;
      type uint8 {
        tailf:info
          "<1-100>;;enter percent of queue size between 1 and 100";
        range "1..100";
      }
    }
    leaf queue-size-7 {
      tailf:cli-drop-node-name;
      type uint8 {
        tailf:info
          "<1-100>;;enter percent of queue size between 1 and 100";
        range "1..100";
      }
    }
    leaf queue-size-8 {
      tailf:cli-drop-node-name;
      type uint8 {
        tailf:info
          "<1-100>;;enter percent of queue size between 1 and 100";
        range "1..100";
      }
    }
  }

  grouping interface-common-pre-grouping {
    leaf mac-address {
      tailf:info
        "Manually set interface MAC address";
      type string {
        tailf:info
          "H.H.H;;MAC address";
      }
    }
    leaf description {
      tailf:info
        "Interface specific description";
      tailf:cli-multi-value;
      tailf:cli-preformatted;
      tailf:cli-full-command;
      type string {
        tailf:info
          "LINE;;Up to 240 characters describing this interface";
        length "0..240";
      }
    }
    container backup {
      tailf:info
        "Modify backup parameters";
      container interface {
        tailf:info
          "Configure an interface as a backup";
        uses interface-name-grouping;
      }
    }
    list glbp {
      tailf:info
        "Gateway Load Balancing Protocol interface commands";
      tailf:cli-suppress-mode;
      tailf:cli-delete-when-empty;
      key "group-number";
      leaf group-number {
        type uint16 {
          tailf:info
            "<0-1023>;;Group number";
          range "0..1023";
        }
      }
      leaf ip {
        tailf:info
          "Enable group and set virtual IP address";
        type inet:ipv4-address {
          tailf:info
            "A.B.C.D;;Virtual IP address";
        }
      }
      container ip-secondary-list {
        tailf:cli-drop-node-name;
        list ip {
          tailf:cli-suppress-mode;
          tailf:cli-delete-when-empty;
          tailf:cli-incomplete-command;
          key "address";
          leaf address {
            type inet:ipv4-address {
              tailf:info
                "A.B.C.D;;Virtual IP address";
            }
          }
          leaf secondary {
            tailf:info
              "Make this IP address a secondary address";
            type empty;
          }
        }
      }
      leaf priority {
        tailf:info
          "Priority level";
        type uint8 {
          tailf:info
            "<1-255>;;Priority value";
          range "1..255";
        }
      }
      container preempt {
        tailf:info
          "Overthrow lower priority designated routers";
        tailf:cli-delete-when-empty;
        presence "true";
        container delay {
          tailf:info
            "Wait before preempting";
          leaf minimum {
            tailf:info
              "Delay at least this long";
            type uint32 {
              tailf:info
                "<0-3600>;;Number of seconds for minimum delay";
              range "0..3600";
            }
          }
        }
      }
    }
  }

  grouping interface-ospfv3-grouping {
    container area {
      tailf:info
        "Set the OSPF area ID";
      tailf:cli-compact-syntax;
      tailf:cli-sequence-commands;
      leaf id {
        tailf:cli-drop-node-name;
        tailf:cli-reset-container;
        type union {
          type uint32 {
            tailf:info
              "<0-4294967295>;;OSPF area ID as a decimal value";
          }
          type inet:ipv4-address {
            tailf:info
              "A.B.C.D;;OSPF area ID in IP address format";
          }
        }
      }
      leaf instance {
        tailf:info
          "Set the OSPF instance";
        type uint8 {
          tailf:info
            "<0-31>;;Instance ID";
          range "0..31";
        }
      }
    }
    leaf priority {
      tailf:info
        "Router priority";
      tailf:cli-full-command;
      type uint8 {
        tailf:info
          "<0-255>;;Priority";
      }
    }
    container authentication {
      tailf:info
        "Enable authentication";
      choice authentication-choice {
        leaf key-chain {
          tailf:info
            "Use a key-chain for cryptographic authentication keys";
          tailf:non-strict-leafref {
            path "/ncs:devices/ncs:device/ncs:config/ios:key/chain/name" {
              tailf:xpath-root 3;
            }
          }
          type string {
            tailf:info
              "WORD;;Key-chain name";
          }
        }
        leaf null {
          tailf:info
            "Use no authentication";
          type empty;
        }
      }
    }
  }

  grouping interface-common-grouping0 {
    container arp {
      tailf:info
        "Set arp type (arpa, probe, snap), timeout, log options orpacket priority";
      leaf timeout {
        tailf:info
          "Set ARP cache timeout";
        tailf:cli-full-command;
        type uint32 {
          tailf:info
            "<0-2147483>;;Seconds";
          range "0..2147483";
        }
      }
      leaf frame-relay {
        tailf:info
          "Enable ARP for a frame relay interface";
        tailf:cli-boolean-no;
        tailf:cli-full-command;
        type boolean;
      }
    }
    container authentication {
      tailf:info
        "set the port-control value";
      container event {
        tailf:info
          "Set action for authentication events";
        container server {
          tailf:info
            "Configure actions for AAA server events";
          container dead {
            tailf:info
              "Configure AAA server dead actions";
            container action {
              tailf:info
                "Required action for authentication event";
              container authorize {
                tailf:info
                  "Authorize the port";
                leaf vlan {
                  tailf:info
                    "Configure Critical Authorization VLAN";
                  type uint16 {
                    tailf:info
                      "<1-4094>;;Enter a VlanId";
                  }
                }
              }
            }
          }
        }
        container no-response {
          tailf:info
            "Configure non-responsive host actions";
          container action {
            tailf:info
              "Required action for authentication event";
            container authorize {
              tailf:info
                "Authorize the port";
              leaf vlan {
                tailf:info
                  "Configure Guest vlan";
                type uint16 {
                  tailf:info
                    "<1-4094>;;Enter a VlanId";
                  range "1..4094";
                }
              }
            }
          }
        }
      }
      leaf host-mode {
        tailf:info
          "Set the Host mode for authentication on this interface";
        type enumeration {
          enum "multi-auth" {
            tailf:info
              "Multiple Authentication Mode";
          }
          enum "multi-domain" {
            tailf:info
              "Multiple Domain Mode";
          }
          enum "multi-host" {
            tailf:info
              "Multiple Host Mode";
          }
          enum "single-host" {
            tailf:info
              "SINGLE HOST Mode";
          }
        }
      }
      container order {
        tailf:info
          "Add an authentication method to the order list";
        leaf dot1x {
          tailf:info
            "Authentication method 'dot1x' allowed";
          type enumeration {
            enum "mab" {
              tailf:info
                "Authentication method 'mab' allowed";
            }
            enum "webauth" {
              tailf:info
                "Authentication method 'webauth' allowed";
            }
          }
        }
      }
      container priority {
        tailf:info
          "Add an authentication method to the priority list";
        leaf dot1x {
          tailf:info
            "Authentication method 'dot1x' allowed";
          type enumeration {
            enum "mab" {
              tailf:info
                "Authentication method 'mab' allowed";
            }
            enum "webauth" {
              tailf:info
                "Authentication method 'webauth' allowed";
            }
          }
        }
      }
      leaf port-control {
        tailf:info
          "Set the port-control value";
        type enumeration {
          enum "auto" {
            tailf:info
              "PortState will be set to AUTO";
          }
          enum "force-authorized" {
            tailf:info
              "PortState set to Authorized";
          }
          enum "force-unauthorized" {
            tailf:info
              "PortState will be set to UnAuthorized";
          }
        }
      }
      leaf periodic {
        tailf:info
          "Enable or Disable Reauthentication for this port";
        type empty;
      }
      container timer {
        tailf:info
          "Set authentication timer values";
        leaf reauthenticate {
          tailf:info
            "Time in seconds after which an automatic re-authentication should be initiated (default 1 hour)";
          type union {
            type uint16 {
              tailf:info
                "<1-65535>;;Enter a value between 1 and 65535";
              range "1..65535";
            }
            type enumeration {
              enum "server" {
                tailf:info
                  "Obtain re-authentication timeout value from the server";
              }
            }
          }
        }
      }
    }
    container access-session {
      tailf:info
        "Access Session specific Interface Configuration Commands";
      leaf closed {
        tailf:info
          "Enable closed access on port (disabled by default, i.e. open access)";
        type empty;
      }
      leaf port-control {
        tailf:info
          "Set the port-control value";
        type enumeration {
          enum "auto" {
            tailf:info
              "PortState set to automatic";
          }
          enum "force-authorized" {
            tailf:info
              "PortState set to AUTHORIZED";
          }
          enum "force-unauthorized" {
            tailf:info
              "PortState set to UnAuthorized";
          }
        }
        default "force-authorized";
      }
    }
    container mab {
      tailf:info
        "MAC Authentication Bypass Interface Config Commands";
      presence "true";
      leaf eap {
        tailf:info
          "Use EAP authentication for MAC Auth Bypass";
        type empty;
      }
    }
    leaf medium {
      tailf:info
        "Configures the interface as point-to-point";
      type enumeration {
        enum "p2p";
      }
    }
    container frame-relay {
      tailf:info
        "Set frame relay parameters";
      container multilink {
        tailf:info
          "Set Multilink FR parameters";
        leaf output-threshold {
          tailf:info
            "Set output-threshold as xmt credit on one bundle link";
          type uint32 {
            tailf:info
              "<20-2147483647>;;number of bytes";
            range "20..2147483647";
          }
        }
        container bid {
          tailf:info
            "Bundle id for this bundle interface";
          tailf:cli-reset-container;
          leaf bid {
            tailf:cli-drop-node-name;
            type string {
              tailf:info
                "LINE;;String to identify this bundle to the peer";
            }
          }
        }
      }
      leaf lmi-type {
        tailf:info
          "Use CISCO-ANSI-CCITT type LMI";
        tailf:cli-full-command;
        type enumeration {
          enum "ansi";
          enum "cisco";
          enum "q933a";
        }
      }
      leaf intf-type {
        tailf:info
          "Configure a FR DTE/DCE/NNI interface";
        tailf:cli-full-command;
        type enumeration {
          enum "dce" {
            tailf:info
              "Configure a FR DCE";
          }
          enum "dte" {
            tailf:info
              "Configure a FR DTE";
          }
          enum "nni" {
            tailf:info
              "Configure a FR NNI";
          }
        }
      }
      container interface-dlci {
        tailf:info
          "Define a DLCI on an interface/subinterface";
        tailf:cli-add-mode;
        tailf:cli-mode-name "config-fr-dlci";
        tailf:cli-compact-syntax;
        tailf:cli-sequence-commands {
          tailf:cli-reset-siblings;
        }
        leaf dlci {
          tailf:cli-drop-node-name;
          tailf:cli-hide-in-submode;
          type uint16 {
            tailf:info
              "<16-1007>;;Define a switched or locally terminated DLCI";
          }
        }
        leaf encapsulation {
          tailf:cli-drop-node-name;
          tailf:cli-hide-in-submode;
          type enumeration {
            enum "cisco" {
              tailf:info
                "Use CISCO Encapsulation";
            }
            enum "IETF" {
              tailf:info
                "Use RFC1490/RFC2427 Encapsulation";
            }
          }
        }
        leaf class {
          tailf:non-strict-leafref {
            path "/ncs:devices/ncs:device/ncs:config/ios:map-class/frame-relay/name" {
              tailf:xpath-root 3;
            }
          }
          type string;
        }
      }
    }
    container fair-queue {
      tailf:info
        "Enable Fair Queuing on an Interface";
      tailf:cli-compact-syntax;
      tailf:cli-sequence-commands;
      tailf:cli-reset-container;
      tailf:cli-delete-when-empty;
      presence "true";
      leaf congestive-discard-threshold {
        tailf:cli-drop-node-name;
        type uint16 {
          tailf:info
            "<1-4096>;;Congestive Discard Threshold";
        }
      }
      leaf dynamic-queues {
        tailf:cli-drop-node-name;
        type uint16 {
          tailf:info
            "<16-4096>;;Number Dynamic Conversation Queues";
        }
      }
      leaf reservable-queues {
        tailf:cli-drop-node-name;
        type uint16 {
          tailf:info
            "<0-1000>;;Number Reservable Conversation Queues";
        }
      }
    }
    container flowcontrol {
      tailf:info
        "Configure flow operation.";
      leaf bidirectional {
        tailf:cli-boolean-no;
        tailf:cli-full-command;
        type boolean;
        default "true";
      }
      leaf receive {
        tailf:info
          "Configure receiving flow operation";
        type enumeration {
          enum "desired" {
            tailf:info
              "Allow but do not require flow-control packets on port";
          }
          enum "off" {
            tailf:info
              "Disable flow-control packets on port";
          }
          enum "on" {
            tailf:info
              "Enable flow-control packets on port";
          }
        }
      }
      leaf send {
        tailf:info
          "Configure sending flow operation";
        type enumeration {
          enum "desired" {
            tailf:info
              "Allow but do not require flow-control packets on port";
          }
          enum "off" {
            tailf:info
              "Disable flow-control packets on port";
          }
          enum "on" {
            tailf:info
              "Enable flow-control packets on port";
          }
        }
      }
    }
    container traffic-shape {
      tailf:info
        "Enable Traffic Shaping on an Interface or Sub-Interface";
      container rate {
        tailf:info
          "configure token bucket: CIR (bps) [Bc (bits) [Be (bits)]]";
        tailf:cli-compact-syntax;
        tailf:cli-sequence-commands;
        leaf bit-rate {
          tailf:cli-drop-node-name;
          tailf:cli-diff-dependency "../../group/access-list" {
            tailf:xpath-root 3;
            tailf:cli-trigger-on-set;
          }
          type uint32 {
            tailf:info
              "<8000-100000000>;;Target Bit Rate (bits per second)";
          }
        }
        leaf burst-size {
          tailf:cli-drop-node-name;
          type uint32 {
            tailf:info
              "<0-100000000>;;bits per interval, sustained";
            range "0..100000000";
          }
        }
        leaf excess-burst-size {
          tailf:cli-drop-node-name;
          type uint32 {
            tailf:info
              "<0-100000000>;;bits per interval, excess in first interval";
            range "0..100000000";
          }
        }
        leaf max-buffers {
          tailf:cli-drop-node-name;
          type uint16 {
            tailf:info
              "<1-4096>;;Set buffer limit";
            range "1..4096";
          }
        }
      }
      list group {
        tailf:info
          "configure token bucket: group <access-list> CIR (bps) [Bc (bits) [Be (bits)]] ";
        tailf:cli-suppress-mode;
        tailf:cli-delete-when-empty;
        tailf:cli-compact-syntax;
        tailf:cli-sequence-commands;
        key "access-list";
        leaf access-list {
          tailf:cli-diff-dependency "../../rate/bit-rate" {
            tailf:xpath-root 3;
            tailf:cli-trigger-on-set;
          }
          type uint16 {
            tailf:info
              "<1-2799>;;selecting Access list";
            range "1..2799";
          }
        }
        leaf bit-rate {
          tailf:cli-drop-node-name;
          type uint32 {
            tailf:info
              "<8000-100000000>;;Target Bit Rate (bits per second)";
          }
        }
        leaf burst-size {
          tailf:cli-drop-node-name;
          type uint32 {
            tailf:info
              "<0-100000000>;;bits per interval, sustained";
            range "0..100000000";
          }
        }
        leaf excess-burst-size {
          tailf:cli-drop-node-name;
          type uint32 {
            tailf:info
              "<0-100000000>;;bits per interval, excess in first interval";
            range "0..100000000";
          }
        }
        leaf max-buffers {
          tailf:cli-drop-node-name;
          type uint16 {
            tailf:info
              "<1-4096>;;Set buffer limit";
            range "1..4096";
          }
        }
      }
    }
    choice keepalive-choice {
      leaf keepalive {
        tailf:info
          "Enable keepalive";
        tailf:cli-boolean-no;
        tailf:cli-full-command;
        type boolean;
        default "true";
      }
      container keepalive-period {
        tailf:cli-drop-node-name;
        leaf keepalive {
          tailf:info
            "Enable keepalive";
          type uint16 {
            tailf:info
              "<0-32767>;;Keepalive period (default 10 seconds)";
            range "0..32767";
          }
          default "10";
        }
      }
      container keepalive-period-retries {
        tailf:cli-drop-node-name;
        container keepalive {
          tailf:cli-compact-syntax;
          tailf:cli-sequence-commands {
            tailf:cli-reset-siblings;
          }
          leaf period {
            tailf:cli-drop-node-name;
            type uint16 {
              tailf:info
                "<0-32767>;;Keepalive period (default 10 seconds)";
              range "0..32767";
            }
          }
          leaf retries {
            tailf:cli-drop-node-name;
            type uint8 {
              range "1..255";
            }
          }
        }
      }
    }
    container snmp {
      tailf:info
        "Modify SNMP interface parameters";
      container ifindex {
        tailf:info
          "Persist ifindex for the interface";
        leaf persist {
          tailf:info
            "Enable/Disable ifIndex persistence ";
          type empty;
        }
      }
      container trap {
        tailf:info
          "Allow a specific SNMP trap";
        leaf link-status {
          tailf:info
            "Allow SNMP LINKUP and LINKDOWN traps";
          tailf:cli-boolean-no;
          tailf:cli-full-command;
          type boolean;
          default "true";
        }
        container link-status-capas {
          tailf:cli-drop-node-name;
          container link-status {
            tailf:info
              "Allow SNMP LINKUP and LINKDOWN traps";
            container permit {
              tailf:info
                "Permit the following capability";
              leaf duplicates {
                tailf:info
                  "Permit duplicate SNMP LINKUP and LINKDOWN traps";
                type empty;
              }
            }
          }
        }
        container mac-notification {
          tailf:info
            "MAC Address notification for the interface";
          container change {
            tailf:info
              "Enable Mac Address notification feature for this port";
            leaf added {
              tailf:info
                "Enable Mac Address added notification for this port";
              type empty;
            }
            leaf removed {
              tailf:info
                "Enable Mac Address removed notification for this port";
              type empty;
            }
          }
        }
      }
    }
    container flow-sampler {
      tailf:info
        "Attach flow sampler to the interface";
      leaf name {
        tailf:cli-drop-node-name;
        tailf:non-strict-leafref {
          path "/ncs:devices/ncs:device/ncs:config/ios:flow-sampler-map/name" {
            tailf:xpath-root 3;
          }
        }
        type string {
          tailf:info
            "WORD;;Name of the flow sampler";
        }
      }
      container egress {
        tailf:cli-drop-node-name;
        tailf:cli-compact-syntax;
        tailf:cli-sequence-commands;
        leaf name {
          tailf:cli-drop-node-name;
          tailf:cli-incomplete-command;
          tailf:non-strict-leafref {
            path "/ncs:devices/ncs:device/ncs:config/ios:flow-sampler-map/name" {
              tailf:xpath-root 3;
            }
          }
          type string {
            tailf:info
              "WORD;;Name of the flow sampler";
          }
        }
        leaf egress {
          tailf:info
            "Egress flow sampler";
          type empty;
        }
      }
    }
    container lldp {
      tailf:info
        "LLDP interface subcommands";
      leaf transmit {
        tailf:info
          "Enable LLDP transmission on interface";
        tailf:cli-boolean-no;
        tailf:cli-full-command;
        type boolean;
        default "true";
      }
      leaf receive {
        tailf:info
          "Enable LLDP reception on interface";
        tailf:cli-boolean-no;
        tailf:cli-full-command;
        type boolean;
        default "true";
      }
    }
    container bfd {
      tailf:info
        "BFD interface configuration commands";
      container interval {
        tailf:info
          "Transmit interval between BFD packets";
        tailf:cli-compact-syntax;
        tailf:cli-sequence-commands {
          tailf:cli-reset-all-siblings;
        }
        leaf msecs {
          tailf:cli-drop-node-name;
          tailf:cli-incomplete-command;
          type uint16 {
            tailf:info
              "<15-999>;;Milliseconds";
            range "15..999";
          }
        }
        leaf min_rx {
          tailf:info
            "Minimum receive interval capability";
          tailf:cli-incomplete-command;
          type uint16 {
            tailf:info
              "<15-999>;;Milliseconds";
            range "15..999";
          }
        }
        leaf multiplier {
          tailf:info
            "Multiplier value used to compute holddown";
          type uint8 {
            tailf:info
              "<3-50>;;value used to multiply the interval";
            range "3..50";
          }
        }
      }
      leaf echo {
        tailf:info
          "Use echo adjunct as bfd detection mechanism";
        tailf:cli-boolean-no;
        tailf:cli-full-command;
        type boolean;
        default "true";
      }
      leaf template {
        tailf:info
          "BFD template";
        tailf:cli-full-command;
        type string {
          tailf:info
            "WORD;;bfd template name";
        }
      }
    }
    container bandwidth {
      tailf:info
        "Set bandwidth informational parameter";
      tailf:cli-compact-syntax;
      tailf:cli-sequence-commands {
        tailf:cli-reset-siblings;
      }
      leaf inherit {
        tailf:cli-optional-in-sequence;
        tailf:info
          "Specify how bandwidth is inherited";
        type empty;
      }
      leaf kilobits {
        tailf:cli-drop-node-name;
        type uint32 {
          tailf:info
            "<1-10000000>;;Bandwidth in kilobits";
          range "1..10000000";
        }
      }
    }
    container cdp {
      tailf:info
        "CDP interface subcommands";
      leaf enable {
        tailf:info
          "Enable CDP on interface";
        tailf:cli-boolean-no;
        tailf:cli-full-command;
        type boolean;
        default "true";
      }
      container tlv {
        tailf:info
          "Enable exchange of specific tlv information";
        container app {
          tailf:info
            "Enable/Configure Application TLV";
          tailf:cli-display-separated;
          tailf:cli-compact-syntax;
          tailf:cli-reset-container;
          tailf:cli-sequence-commands;
          presence "true";
          leaf tlvtype {
            tailf:info
              "Configure APP TLV";
            tailf:cli-incomplete-command;
            type uint16 {
              tailf:info
                "Configure App TLV Type information";
              range "1001..65535";
            }
          }
          leaf value {
            tailf:info
              "Configure App TLV Value information";
            type string {
              tailf:info
                "WORD;;Configure App TLV value information";
            }
          }
        }
        leaf server-location {
          tailf:info
            "Enable CDP location server on interface";
          tailf:cli-full-command;
          type empty;
        }
        leaf location {
          tailf:info
            "Exchange location information";
          tailf:cli-full-command;
          type empty;
        }
      }
    }
    container mop {
      tailf:info
        "DEC MOP server commands";
      leaf xenabled {
        tailf:alt-name "enabled";
        tailf:info
          "Enable MOP for interface";
        tailf:cli-boolean-no;
        tailf:cli-full-command;
        type boolean;
        default "true";
      }
      leaf sysid {
        tailf:cli-boolean-no;
        tailf:cli-full-command;
        type boolean;
        default "true";
      }
    }
    container dampening {
      tailf:info
        "Enable event dampening";
      presence "true";
      leaf dampening-time {
        tailf:cli-drop-node-name;
        tailf:cli-delete-container-on-delete;
        type uint16 {
          tailf:info
            "<1-30>;;Half-life time for penalty";
          range "1..30";
        }
      }
    }
    list vlan-range {
      tailf:cli-mode-name "config-if-vlan-range";
      key "id";
      leaf id {
        type uint16 {
          tailf:info
            "WORD;;VLAN IDs 1-4094";
          range "1..4094";
        }
      }
      container service-policy {
        tailf:info
          "Configure Service Policy";
        uses service-policy-grouping;
      }
    }
    list hold-queue {
      tailf:info
        "Set hold queue depth";
      tailf:cli-suppress-mode;
      tailf:cli-delete-when-empty;
      tailf:cli-compact-syntax;
      tailf:cli-sequence-commands {
        tailf:cli-reset-siblings;
      }
      key "direction";
      leaf direction {
        type enumeration {
          enum "in" {
            tailf:info
              "Input queue";
          }
          enum "out" {
            tailf:info
              "Output queue";
          }
        }
      }
      leaf queue-length {
        tailf:cli-drop-node-name;
        tailf:cli-prefix-key;
        type uint16 {
          tailf:info
            "<0-4096>;;Queue length";
          range "0..4096";
        }
      }
    }
    container mpls {
      tailf:info
        "Configure MPLS interface parameters";
      container accounting {
        tailf:info
          "Enable MPLS accounting on this interface";
        container experimental {
          tailf:info
            "Count packets by MPLS experimental value on this interface";
          leaf input {
            tailf:info
              "received packets";
            type empty;
          }
          leaf output {
            tailf:info
              "transmitted packets";
            type empty;
          }
        }
      }
      container bgp {
        tailf:info
          "MPLS BGP";
        leaf forwarding {
          tailf:info
            "Configure MPLS forwarding for directly connected BGP peers";
          type empty;
        }
      }
      container label {
        tailf:info
          "Label properties";
        leaf protocol {
          tailf:info
            "Configure label/tag distribution protocol (LDP/TDP)";
          type enumeration {
            enum "both" {
              tailf:info
                "Use LDP or TDP (Adapt to peer on multiaccess interface)";
            }
            enum "ldp" {
              tailf:info
                "Use LDP (default)";
            }
            enum "tdp" {
              tailf:info
                "Use TDP";
            }
          }
        }
      }
      container ldp {
        tailf:info
          "Configure Label Distribution Protocol (LDP) parameters";
        container igp {
          tailf:info
            "Configure IGP-related parameters";
          choice sync-choice {
            leaf sync {
              tailf:info
                "Allow LDP-IGP Synchronization on this interface";
              tailf:cli-boolean-no;
              tailf:cli-full-command;
              type boolean;
              default "true";
            }
            container sync-delay {
              tailf:cli-drop-node-name;
              container sync {
                tailf:info
                  "Allow LDP-IGP Synchronization on this interface";
                tailf:cli-incomplete-command;
                tailf:cli-incomplete-no;
                leaf delay {
                  tailf:info
                    "Configure LDP to IGP sync achieved notification delay time";
                  type uint8 {
                    tailf:info
                      "<5-60>;;Delay time (seconds)";
                    range "5..60";
                  }
                }
              }
            }
          }
        }
        container discovery {
          tailf:info
            "Configure interface LDP Discovery parameters";
          leaf transport-address {
            tailf:info
              "Specify interface LDP transport address";
            type ldp-discovery-address-type;
          }
        }
      }
      leaf mtu {
        tailf:info
          "Set MPLS Maximum Transmission Unit";
        tailf:cli-full-command;
        type union {
          type uint16 {
            tailf:info
              "<1501-1524>;;MTU (baby giants bytes)";
            range "1501..1524";
          }
          type uint16 {
            tailf:info
              "<64-1500>;;MTU (bytes)";
            range "64..1500";
          }
          type uint16 {
            tailf:info
              "<64-9216>;;MTU size in bytes";
            range "64..9216";
          }
        }
        default "1500";
      }
      container traffic-eng {
        tailf:info
          "Configure Traffic Engineering parameters";
        leaf administrative-weight {
          tailf:info
            "Set the administrative weight for the interface";
          tailf:cli-full-command;
          type uint32 {
            tailf:info
              "<0-4294967295>;;Weight";
            range "0..4294967295";
          }
        }
        leaf backup-path {
          tailf:info
            "Configure an MPLS TE backup for this interface";
          type string {
            tailf:info
              "Tunnel;;Tunnel interface";
          }
        }
        leaf attribute-flags {
          tailf:info
            "Set user-defined interface attibute flags";
          tailf:cli-full-command;
          type string {
            tailf:info
              "<0x0-0xFFFFFFFF>;;Attribute flags";
          }
        }
        container flooding {
          tailf:info
            "Set flooding parameters";
          container thresholds {
            tailf:info
              "Set flooding thresholds";
            leaf-list down {
              tailf:info
                "Set the thresholds for decreased resource availability";
              tailf:cli-flat-list-syntax;
              type uint8 {
                tailf:info
                  "<0-100>;;decreased bandwidth usage (percent)";
                range "0..100";
              }
            }
            leaf-list up {
              tailf:info
                "Set the thresholds for increased resource availability";
              tailf:cli-flat-list-syntax;
              type uint8 {
                tailf:info
                  "<0-100>;;increased bandwidth usage (percent)";
                range "0..100";
              }
            }
          }
        }
        leaf tunnels {
          tailf:info
            "enable MPLS Traffic Engineering tunnels";
          tailf:cli-full-command;
          type empty;
        }
      }
      leaf ip {
        tailf:info
          "Configure dynamic MPLS forwarding for IP";
        tailf:cli-full-command;
        type empty;
      }
      leaf propagate-cos {
        type empty;
      }
    }
    container isis {
      tailf:info
        "IS-IS commands";
      container bfd {
        tailf:info
          "Bidirectional Forwarding Protocol";
        tailf:cli-reset-container;
        tailf:cli-delete-when-empty;
        presence "true";
        leaf disable {
          tailf:info
            "disable bfd";
          type empty;
        }
      }
      leaf tag {
        tailf:info
          "Assign an admin tag to an ISIS interface IP route";
        type uint32 {
          tailf:info
            "<1-4294967295>;;Admin tag number";
        }
      }
      leaf circuit-type {
        tailf:info
          "Configure circuit type for interface";
        type enumeration {
          enum "level-1" {
            tailf:info
              "Level-1 only adjacencies are formed";
          }
          enum "level-1-2" {
            tailf:info
              "Level-1-2 adjacencies are formed";
          }
          enum "level-2-only" {
            tailf:info
              "Level-2 only adjacencies are formed";
          }
        }
        default "level-1-2";
      }
      leaf network {
        tailf:info
          "Network type";
        tailf:cli-full-command;
        type enumeration {
          enum "point-to-point" {
            tailf:info
              "Specify ISIS point-to-point network";
          }
        }
      }
      choice metric-choice {
        case default-case {
          leaf metric {
            tailf:info
              "Configure the metric for interface";
            type uint32 {
              tailf:info
                "<1-16777214>;;Default metric";
              range "1..16777214";
            }
          }
        }
        case level-case {
          container metric-level {
            tailf:cli-drop-node-name;
            list metric {
              tailf:cli-suppress-mode;
              tailf:cli-delete-when-empty;
              tailf:cli-compact-syntax;
              key "level";
              leaf level {
                type enumeration {
                  enum "level-1" {
                    tailf:info
                      "Apply metric to level-1 links";
                  }
                  enum "level-2" {
                    tailf:info
                      "Apply metric to level-2 links";
                  }
                }
              }
              leaf default {
                tailf:cli-drop-node-name;
                tailf:cli-prefix-key;
                type uint32 {
                  tailf:info
                    "<1-16777214>;;Default metric";
                  range "1..16777214";
                }
              }
            }
          }
        }
      }
      uses router-isis-interface-grouping;
      container ipv6 {
        tailf:info
          "IPv6 interface configuration";
        tailf:cli-diff-dependency "../../ipv6/enable" {
          tailf:xpath-root 3;
          tailf:cli-trigger-on-set;
        }
        choice metric-choice {
          leaf metric {
            tailf:info
              "Configure the metric for interface";
            type union {
              type uint32 {
                tailf:info
                  "<1-16777214>;;Default metric";
                range "1..16777214";
              }
              type enumeration {
                enum "maximum" {
                  tailf:info
                    "Maximum metric. All routers will exclude this link from their SPF";
                }
              }
            }
          }
          container metric-level {
            tailf:cli-drop-node-name;
            list metric {
              tailf:info
                "Configure the metric for interface";
              tailf:cli-suppress-mode;
              tailf:cli-delete-when-empty;
              tailf:cli-compact-syntax;
              tailf:cli-sequence-commands;
              key "level";
              leaf level {
                type enumeration {
                  enum "level-1" {
                    tailf:info
                      "Apply metric to level-1 links";
                  }
                  enum "level-2" {
                    tailf:info
                      "Apply metric to level-2 links";
                  }
                }
              }
              leaf value {
                tailf:cli-drop-node-name;
                tailf:cli-prefix-key;
                type union {
                  type uint32 {
                    tailf:info
                      "<1-16777214>;;Default metric";
                    range "1..16777214";
                  }
                  type enumeration {
                    enum "maximum" {
                      tailf:info
                        "Maximum metric. All routers will exclude this link from their SPF";
                    }
                  }
                }
              }
            }
          }
        }
      }
      leaf three-way-handshake {
        tailf:info
          "Select Cisco or IETF three-way handshake";
        tailf:cli-diff-dependency "../../ipv6/router/isis" {
          tailf:xpath-root 3;
          tailf:cli-trigger-on-set;
        }
        type enumeration {
          enum "cisco" {
            tailf:info
              "Cisco implementation of three-way handshake (default)";
          }
          enum "ietf" {
            tailf:info
              "IETF implementation of three-way handshake";
          }
        }
        default "cisco";
      }
      choice priority-choice {
        leaf priority {
          tailf:info
            "Set priority for Designated Router election";
          tailf:cli-full-command;
          type uint8 {
            tailf:info
              "<0-127>;;Priority value";
            range "0..127";
          }
        }
        container priority-level-1-2 {
          tailf:cli-drop-node-name;
          list priority {
            tailf:info
              "Set priority for Designated Router election";
            tailf:cli-suppress-mode;
            tailf:cli-delete-when-empty;
            tailf:cli-compact-syntax;
            tailf:cli-sequence-commands;
            key "level";
            leaf level {
              type enumeration {
                enum "level-1" {
                  tailf:info
                    "Specify priority for level-1 routing";
                }
                enum "level-2" {
                  tailf:info
                    "Specify priority for level-2 routing";
                }
              }
            }
            leaf priority {
              tailf:cli-drop-node-name;
              tailf:cli-prefix-key;
              type uint8 {
                tailf:info
                  "<0-127>;;Priority value";
                range "0..127";
              }
            }
          }
        }
      }
      container hello-multiplier {
        tailf:info
          "Set Hello multiplier";
        leaf seconds {
          tailf:cli-drop-node-name;
          type uint16 {
            tailf:info
              "<1-65535>;;Hello multiplier value";
            range "1..65535";
          }
        }
      }
      container hello-interval {
        tailf:info
          "Set Hello interval in seconds";
        choice hello-interval-choice {
          leaf seconds {
            tailf:cli-drop-node-name;
            type uint16 {
              tailf:info
                "<1-65535>;;Hello interval value";
              range "1..65535";
            }
          }
          leaf minimal {
            tailf:info
              "Holdtime 1 second, interval depends on multiplier";
            type empty;
          }
        }
      }
      choice csnp-interval-choice {
        leaf csnp-interval {
          tailf:info
            "Set CSNP interval in seconds";
          tailf:cli-full-command;
          type uint16 {
            tailf:info
              "<0-65535>;;CSNP interval value";
          }
        }
        container csnp-interval-level {
          tailf:cli-drop-node-name;
          list csnp-interval {
            tailf:cli-suppress-mode;
            tailf:cli-delete-when-empty;
            tailf:cli-compact-syntax;
            tailf:cli-sequence-commands;
            key "level";
            leaf level {
              type enumeration {
                enum "level-1" {
                  tailf:info
                    "Specify interval for level-1 CSNPs";
                }
                enum "level-2" {
                  tailf:info
                    "Specify interval for level-2 CSNPs";
                }
              }
            }
            leaf seconds {
              tailf:cli-drop-node-name;
              tailf:cli-prefix-key;
              type uint16 {
                tailf:info
                  "<0-65535>;;CSNP interval value";
              }
            }
          }
        }
      }
      choice password-choice {
        leaf password {
          tailf:info
            "Configure the authentication password for interface";
          tailf:cli-full-command;
          type string {
            tailf:info
              "WORD;;Password";
          }
        }
        container password-level-1-2 {
          tailf:cli-drop-node-name;
          list password {
            tailf:cli-sequence-commands;
            tailf:cli-compact-syntax;
            key "level";
            leaf password {
              tailf:cli-prefix-key;
              tailf:cli-drop-node-name;
              type string {
                tailf:info
                  "WORD;;Password";
              }
            }
            leaf level {
              type enumeration {
                enum "level-1" {
                  tailf:info
                    "Specify password for level-1 PDUs";
                }
                enum "level-2" {
                  tailf:info
                    "Specify password for level-2 PDUs";
                }
              }
            }
          }
        }
      }
    }
    choice vrf-choice {
      container ip-vrf {
        tailf:cli-drop-node-name;
        container ip {
          container vrf {
            leaf forwarding {
              tailf:info
                "Configure forwarding table";
              tailf:cli-diff-dependency "/ios:ip/vrf" {
                tailf:xpath-root 3;
              }
              tailf:non-strict-leafref {
                path "/ncs:devices/ncs:device/ncs:config/ios:ip/vrf/name" {
                  tailf:xpath-root 3;
                }
              }
              type string {
                tailf:info
                  "WORD;;VRF name";
              }
            }
          }
        }
      }
      container vrf {
        tailf:info
          "VPN Routing/Forwarding parameters on the interface";
        leaf forwarding {
          tailf:info
            "Configure forwarding table";
          tailf:cli-diff-dependency "/ios:vrf/definition" {
            tailf:xpath-root 3;
          }
          tailf:non-strict-leafref {
            path "/ncs:devices/ncs:device/ncs:config/ios:vrf/definition/name" {
              tailf:xpath-root 3;
            }
          }
          type string {
            tailf:info
              "WORD;;VRF name";
          }
        }
      }
    }
    container pm-path {
      tailf:info
        "Global pm-path configuration";
      tailf:cli-compact-syntax;
      tailf:cli-sequence-commands {
        tailf:cli-reset-siblings;
      }
      tailf:cli-diff-dependency "/ios:pm-agent" {
        tailf:xpath-root 3;
      }
      leaf name {
        tailf:cli-drop-node-name;
        tailf:cli-incomplete-command;
        type string {
          tailf:info
            "WORD;;Path name";
        }
      }
      leaf interface-id {
        tailf:info
          "Specify the interface-id";
        type uint32 {
          tailf:info
            "<1-4294967295>;;Specify the interface-id value";
          range "1..4294967295";
        }
      }
    }
    container ip {
      tailf:info
        "Interface Internet Protocol config commands";
      list access-group {
        tailf:info
          "Specify access control for packets";
        tailf:cli-suppress-mode;
        tailf:cli-delete-when-empty;
        tailf:cli-compact-syntax;
        tailf:cli-sequence-commands;
        key "direction";
        leaf direction {
          type enumeration {
            enum "in" {
              tailf:code-name "access_group_direction_in";
              tailf:info
                "inbound packets";
            }
            enum "out" {
              tailf:code-name "access_group_direction_out";
              tailf:info
                "outbound packets";
            }
          }
        }
        leaf access-list {
          tailf:cli-diff-dependency "/ios:ip/access-list" {
            tailf:xpath-root 3;
          }
          tailf:cli-drop-node-name;
          tailf:cli-prefix-key;
          type exp-ip-acl-type;
        }
      }
      container authentication {
        tailf:info
          "authentication subcommands";
        container mode {
          tailf:info
            "mode";
          list eigrp {
            tailf:info
              "Enhanced Interior Gateway Routing Protocol (EIGRP)";
            tailf:cli-suppress-mode;
            tailf:cli-delete-when-empty;
            tailf:cli-incomplete-command;
            key "as-no";
            leaf as-no {
              type uint16 {
                tailf:info
                  "<1-65535>;;Autonomous system number";
                range "1..65535";
              }
            }
            leaf md5 {
              tailf:info
                "Keyed message digest";
              type empty;
            }
          }
        }
        container key-chain {
          tailf:info
            "key-chain";
          list eigrp {
            tailf:info
              "Enhanced Interior Gateway Routing Protocol (EIGRP)";
            tailf:cli-suppress-mode;
            tailf:cli-delete-when-empty;
            tailf:cli-incomplete-command;
            key "as-no";
            leaf as-no {
              type uint16 {
                tailf:info
                  "<1-65535>;;Autonomous system number";
                range "1..65535";
              }
            }
            leaf key-chain {
              tailf:cli-drop-node-name;
              tailf:non-strict-leafref {
                path "/ncs:devices/ncs:device/ncs:config/ios:key/chain/name" {
                  tailf:xpath-root 3;
                }
              }
              type string {
                tailf:info
                  "WORD;;name of key-chain";
              }
            }
          }
        }
      }
      container accounting {
        tailf:info
          "Enable IP accounting on this interface";
        tailf:cli-delete-when-empty;
        presence "true";
        leaf output-packets {
          tailf:info
            "Account for IP packets output on this interface";
          tailf:cli-full-command;
          type empty;
        }
        container precedence {
          tailf:info
            "Count packets by IP precedence on this interface";
          leaf input {
            tailf:info
              "received packets";
            type empty;
          }
          leaf output {
            tailf:info
              "transmitted packets";
            type empty;
          }
        }
        leaf access-violations {
          tailf:info
            "Account for IP packets violating access lists on this interface";
          tailf:cli-full-command;
          type empty;
        }
      }
      container vrf {
        tailf:info
          "VPN Routing/Forwarding parameters on the interface";
        leaf receive {
          tailf:info
            "Add Interface Address into VRF Table";
          tailf:cli-full-command;
          type string {
            tailf:info
              "WORD;;Table name";
          }
        }
        leaf sitemap {
          tailf:info
            "Configure route-map for routesreceived from this site";
          tailf:cli-full-command;
          type string {
            tailf:info
              "WORD;;Name of the route-map";
          }
        }
      }
      container arp {
        tailf:info
          "Configure ARP features";
        container inspection {
          tailf:info
            "Arp Inspection configuration";
          leaf trust {
            tailf:info
              "Configure Trust state";
            type empty;
          }
          container limit {
            tailf:info
              "Configure Rate limit of incoming ARP packets";
            tailf:cli-compact-syntax;
            tailf:cli-sequence-commands {
              tailf:cli-reset-siblings;
            }
            choice limit-choice {
              leaf none {
                tailf:info
                  "No limit";
                type empty;
              }
              leaf rate {
                tailf:info
                  "Rate Limit";
                type uint16 {
                  tailf:info
                    "<0-10000>;;Packets per second";
                  range "0..10000";
                }
              }
            }
            container burst {
              tailf:info
                "Configure Burst parameters for ARP packets";
              tailf:cli-flatten-container;
              leaf interval {
                tailf:info
                  "Number of seconds to check the rate";
                type uint8 {
                  tailf:info
                    "<1-15>;;Burst interval in seconds";
                  range "1..15";
                }
              }
            }
          }
        }
      }
      choice address-choice {
        container unnumbered {
          tailf:info
            "Enable IP processing without an explicit address";
          uses interface-name-grouping;
        }
        container no-address {
          tailf:cli-drop-node-name;
          leaf address {
            tailf:cli-boolean-no;
            tailf:cli-full-command;
            tailf:cli-full-no;
            type boolean;
            default "true";
          }
        }
        container address {
          tailf:info
            "Set the IP address of an interface";
          tailf:cli-incomplete-command;
          tailf:cli-incomplete-no;
          choice address-choice {
            case fixed-case {
              container primary {
                tailf:cli-drop-node-name;
                tailf:cli-compact-syntax;
                tailf:cli-sequence-commands;
                tailf:cli-incomplete-command;
                tailf:cli-incomplete-no;
                tailf:cli-diff-dependency "/ios:l2vpn-xconnect/l2vpn/xconnect/context" {
                  tailf:xpath-root 3;
                  tailf:cli-trigger-on-set;
                }
                leaf address {
                  tailf:cli-drop-node-name;
                  tailf:cli-incomplete-command;
                  tailf:cli-incomplete-no;
                  type inet:ipv4-address {
                    tailf:info
                      "A.B.C.D;;IP address";
                  }
                }
                leaf mask {
                  tailf:cli-drop-node-name;
                  type inet:ipv4-address {
                    tailf:info
                      "A.B.C.D;;IP subnet mask";
                  }
                }
              }
              list secondary {
                tailf:cli-drop-node-name;
                tailf:cli-suppress-mode;
                tailf:cli-delete-when-empty;
                tailf:cli-compact-syntax;
                tailf:cli-incomplete-command;
                tailf:cli-incomplete-no;
                tailf:cli-diff-dependency "../primary/address" {
                  tailf:xpath-root 3;
                }
                key "address mask";
                leaf address {
                  tailf:cli-incomplete-no;
                  type inet:ipv4-address {
                    tailf:info
                      "A.B.C.D;;IP address";
                  }
                }
                leaf mask {
                  type inet:ipv4-address {
                    tailf:info
                      "A.B.C.D;;IP subnet mask";
                  }
                }
                leaf secondary {
                  tailf:info
                    "Make this IP address a secondary address";
                  type empty;
                }
              }
            }
            case dhcp-case {
              container dhcp {
                tailf:info
                  "IP Address negotiated via DHCP";
                tailf:cli-compact-syntax;
                tailf:cli-sequence-commands;
                presence "true";
                container client-id {
                  tailf:info
                    "Specify client-id to use";
                  tailf:cli-optional-in-sequence;
                  tailf:cli-flatten-container;
                  tailf:cli-compact-syntax;
                  uses interface-name-grouping;
                }
                leaf hostname {
                  tailf:info
                    "Specify value for hostname option";
                  type string {
                    tailf:info
                      "WORD;;hostname string";
                  }
                }
              }
            }
            case negotiated-case {
              container negotiated {
                tailf:info
                  "IP Address negotiated over PPP";
                tailf:cli-reset-container;
                tailf:cli-delete-when-empty;
                presence "true";
                leaf previous {
                  tailf:info
                    "IPCP attempts to negotiate previous address assigned";
                  type empty;
                }
              }
            }
          }
        }
      }
      container directed-broadcast {
        tailf:info
          "Enable forwarding of directed broadcasts";
        tailf:cli-delete-when-empty;
        presence "true";
        leaf access-list {
          tailf:cli-drop-node-name;
          type union {
            type uint16 {
              tailf:info
                "<1-199>;;A standard IP access list number";
              range "1..199";
            }
            type uint16 {
              tailf:info
                "<1300-2699>;;A standard IP expanded access list number";
              range "1300..2699";
            }
          }
        }
      }
      container split-horizon-eigrp {
        tailf:cli-drop-node-name;
        container split-horizon {
          tailf:info
            "Perform split horizon";
          tailf:cli-incomplete-command;
          tailf:cli-incomplete-no;
          container eigrp {
            tailf:info
              "Enhanced Interior Gateway Routing Protocol (EIGRP)";
            list no-list {
              tailf:info
                "'no ip split-horizon eigrp' entry";
              tailf:cli-suppress-mode;
              tailf:cli-delete-when-empty;
              key "as-no";
              leaf as-no {
                type uint16 {
                  tailf:info
                    "<1-65535>;;Autonomous System";
                  range "1..65535";
                }
              }
            }
          }
        }
      }
      leaf split-horizon {
        tailf:info
          "Perform split horizon";
        tailf:cli-boolean-no;
        tailf:cli-full-command;
        type boolean;
        default "true";
      }
      container router {
        tailf:info
          "IP router interface commands";
        container isis {
          tailf:info
            "IS-IS Routing for IP";
          tailf:cli-delete-when-empty;
          presence "true";
          leaf tag {
            tailf:cli-drop-node-name;
            type string {
              tailf:info
                "WORD;;Routing process tag";
            }
          }
        }
      }
      container flow {
        tailf:info
          "NetFlow related commands";
        leaf ingress {
          tailf:info
            "Enable inbound NetFlow";
          type empty;
        }
        leaf egress {
          tailf:info
            "Enable outbound NetFlow";
          type empty;
        }
        list monitor {
          tailf:info
            "Apply a Flow Monitor";
          tailf:cli-suppress-mode;
          tailf:cli-delete-when-empty;
          tailf:cli-compact-syntax;
          tailf:cli-sequence-commands {
            tailf:cli-reset-siblings;
          }
          key "direction";
          leaf direction {
            type enumeration {
              enum "input" {
                tailf:info
                  "Apply Flow Monitor on input traffic";
              }
              enum "output" {
                tailf:info
                  "Apply Flow Monitor on output traffic";
              }
            }
          }
          leaf name {
            tailf:cli-prefix-key;
            tailf:cli-drop-node-name;
            tailf:non-strict-leafref {
              path "/ncs:devices/ncs:device/ncs:config/ios:flow/monitor/name" {
                tailf:xpath-root 3;
              }
            }
            type string {
              tailf:info
                "WORD;;Flow Monitor name";
            }
          }
        }
      }
      container helper-address {
        tailf:info
          "Specify a destination address for UDP broadcasts";
        list helper-address-list {
          tailf:cli-drop-node-name;
          tailf:cli-suppress-mode;
          tailf:cli-delete-when-empty;
          tailf:cli-show-long-obu-diffs;
          ordered-by user;
          key "address";
          leaf address {
            type inet:ipv4-address {
              tailf:info
                "A.B.C.D;;IP destination address";
            }
          }
        }
        list vrf {
          tailf:cli-suppress-mode;
          tailf:cli-delete-when-empty;
          tailf:cli-show-long-obu-diffs;
          ordered-by user;
          key "vrf address";
          leaf vrf {
            type string {
              tailf:info
                "VRF name for helper-address";
            }
          }
          leaf address {
            type inet:ipv4-address {
              tailf:info
                "A.B.C.D;;IP destination address";
            }
          }
        }
      }
      container summary-address {
        tailf:info
          "Perform address summarization";
        list eigrp {
          tailf:info
            "Enhanced Interior Gateway Routing Protocol (EIGRP)";
          tailf:cli-delete-when-empty;
          tailf:cli-suppress-mode;
          key "as-no ip-address wildcard-mask";
          leaf as-no {
            type uint16 {
              tailf:info
                "<1-65535>;;Autonomous system number";
              range "1..65535";
            }
          }
          leaf ip-address {
            type inet:ipv4-address {
              tailf:info
                "A.B.C.D;;IP summary address";
            }
          }
          leaf wildcard-mask {
            type inet:ipv4-address {
              tailf:info
                "A.B.C.D;;Summary mask";
            }
          }
          leaf distance {
            tailf:cli-drop-node-name;
            type uint8 {
              tailf:info
                "<1-255>;;Administrative distance";
              range "1..255";
            }
          }
        }
      }
      container ospf {
        tailf:info
          "OSPF interface commands";
        list process-id {
          tailf:cli-drop-node-name;
          tailf:cli-suppress-mode;
          tailf:cli-delete-when-empty;
          tailf:cli-compact-syntax;
          tailf:cli-sequence-commands {
            tailf:cli-reset-siblings;
          }
          tailf:cli-incomplete-command;
          key "id";
          leaf id {
            tailf:cli-suppress-range;
            type uint16 {
              tailf:info
                "<1-65535>;;Process ID";
              range "1..65535";
            }
          }
          leaf area {
            tailf:info
              "Set the OSPF area ID";
            type union {
              type uint32 {
                tailf:info
                  "<0-4294967295>;;OSPF area ID as a decimal value";
              }
              type inet:ipv4-address {
                tailf:info
                  "A.B.C.D;;OSPF area ID in IP address format";
              }
            }
          }
          leaf secondaries {
            tailf:info
              "Include or exclude secondary IP addresses";
            type empty;
          }
          leaf none {
            tailf:info
              "Do not include secondary IP addresses";
            type empty;
          }
        }
        container authentication {
          tailf:info
            "Enable authentication";
          tailf:cli-delete-when-empty;
          presence "true";
          choice authentication-choice {
            leaf message-digest {
              tailf:info
                "Use message-digest authentication";
              type empty;
            }
            leaf null {
              tailf:info
                "Use no authentication";
              type empty;
            }
            leaf key-chain {
              tailf:info
                "Use a key-chain for cryptographic authentication keys";
              type string {
                tailf:info
                  "WORD;;Key-chain name";
              }
            }
          }
        }
        container authentication-key {
          tailf:info
            "Authentication password (key)";
          tailf:cli-compact-syntax;
          tailf:cli-sequence-commands;
          uses password-grouping;
        }
        list message-digest-key {
          tailf:info
            "Message digest authentication password (key)";
          tailf:cli-suppress-mode;
          tailf:cli-delete-when-empty;
          tailf:cli-compact-syntax;
          tailf:cli-sequence-commands;
          tailf:cli-remove-before-change;
          key "id";
          leaf id {
            type uint8 {
              tailf:info
                "<1-255>;;Key ID";
              range "1..255";
            }
          }
          container md5 {
            tailf:info
              "Use MD5 algorithm";
            tailf:cli-flatten-container;
            tailf:cli-compact-syntax;
            tailf:cli-sequence-commands;
            uses password-grouping;
          }
        }
        leaf-list network {
          tailf:info
            "Network type";
          tailf:cli-flat-list-syntax {
            tailf:cli-replace-all;
          }
          tailf:cli-full-command;
          max-elements 2;
          type enumeration {
            enum "point-to-multipoint" {
              tailf:info
                "Specify OSPF point-to-multipoint network";
            }
            enum "point-to-point" {
              tailf:info
                "Specify OSPF point-to-point network";
            }
            enum "broadcast" {
              tailf:info
                "Specify OSPF broadcast multi-access network";
            }
            enum "non-broadcast" {
              tailf:info
                "Specify OSPF NBMA network";
            }
          }
        }
        leaf hello-interval {
          tailf:info
            "Time between HELLO packets";
          type uint16 {
            tailf:info
              "<1-65535>;;Seconds";
            range "1..65535";
          }
        }
        container dead-interval {
          tailf:info
            "Interval after which a neighbor is declared dead";
          tailf:cli-compact-syntax;
          tailf:cli-sequence-commands {
            tailf:cli-reset-siblings;
          }
          choice dead-interva-choice {
            leaf seconds {
              tailf:cli-drop-node-name;
              type uint16 {
                tailf:info
                  "<1-65535>;;Seconds";
                range "1..65535";
              }
            }
            case minimal {
              leaf minimal {
                tailf:info
                  "Set to 1 second";
                type empty;
              }
              leaf hello-multiplier {
                tailf:info
                  "Set multiplier for Hellos";
                type uint8 {
                  tailf:info
                    "<3-20>;;Number of Hellos sent within 1 second";
                  range "3..20";
                }
              }
            }
          }
        }
        container bfd {
          tailf:info
            "BFD interface configuration commands";
          presence "true";
          leaf enable {
            tailf:cli-full-command;
            tailf:cli-drop-node-name;
            type enumeration {
              enum "disable" {
                tailf:info
                  "Disable BFD for this interface";
              }
            }
          }
        }
        leaf mtu-ignore {
          tailf:info
            "Ignores the MTU in DBD packets";
          tailf:cli-full-command;
          type empty;
        }
        leaf cost {
          tailf:info
            "Interface cost";
          tailf:cli-full-command;
          type uint16 {
            tailf:info
              "<1-65535>;;Cost";
            range "1..65535";
          }
        }
        container ttl-security {
          tailf:info
            "TTL security check";
          tailf:cli-delete-when-empty;
          presence "true";
          leaf hops {
            tailf:info
              "IP hops";
            type uint8 {
              tailf:info
                "<1-254>;;maximum number of hops allowed";
              range "1..254";
            }
          }
        }
        leaf priority {
          tailf:info
            "Router priority";
          tailf:cli-full-command;
          type uint8 {
            tailf:info
              "<0-255>;;Priority";
          }
        }
        container lls {
          tailf:info
            "Link-local Signaling (LLS) support";
          tailf:cli-delete-when-empty;
          presence "true";
          leaf disable {
            tailf:info
              "disable LLS";
            type empty;
          }
        }
        container database-filter {
          tailf:info
            "Filter OSPF LSA during synchronization and flooding";
          container all {
            tailf:info
              "Filter all LSA";
            leaf out {
              tailf:info
                "Outgoing LSA";
              type empty;
            }
          }
        }
      }
      container pim {
        tailf:info
          "PIM interface commands";
        leaf query-interval {
          tailf:info
            "PIM router query interval";
          type uint16 {
            tailf:info
              "<1-65535>;;Query interval in seconds or milliseconds";
            range "1..65535";
          }
          default "30";
        }
        leaf nbma-mode {
          tailf:info
            "Use Non-Broadcast Multi-Access (NBMA) mode on interface";
          type empty;
        }
        leaf mode {
          tailf:cli-drop-node-name;
          type enumeration {
            enum "sparse-mode" {
              tailf:info
                "Enable PIM sparse-mode operation";
            }
            enum "sparse-dense-mode" {
              tailf:info
                "Enable PIM sparse-dense-mode operation";
            }
          }
        }
        leaf dr-priority {
          tailf:info
            "PIM router DR priority";
          type uint32 {
            tailf:info
              "<0-4294967294>;;DR priority, preference given to larger value";
          }
        }
        leaf snooping {
          tailf:info
            "PIM Snooping enable for Catalyst Vlan";
          type empty;
        }
        leaf passive {
          tailf:info
            "Enable PIM passive interface operation";
          tailf:cli-full-command;
          type empty;
        }
      }
      container multicast {
        tailf:info
          "IP multicast interface commands";
        container boundary {
          tailf:info
            "Boundary for administratively scoped multicast addresses";
          tailf:cli-compact-syntax;
          tailf:cli-sequence-commands {
            tailf:cli-reset-siblings;
          }
          leaf access-list {
            tailf:cli-drop-node-name;
            type string {
              tailf:info
                "WORD;;ACL name or number";
            }
          }
          leaf filter-autorp {
            tailf:info
              "Filter AutoRP packet contents.";
            type empty;
          }
        }
        container limit {
          tailf:info
            "Limit multicast mroute state";
          list access-lists {
            tailf:cli-drop-node-name;
            tailf:cli-suppress-mode;
            tailf:cli-delete-when-empty;
            tailf:cli-incomplete-command;
            key "access-list";
            leaf access-list {
              tailf:cli-suppress-range;
              type ip-acl-type;
            }
            leaf allowed-state {
              tailf:cli-drop-node-name;
              type uint32 {
                tailf:info
                  "<0-2147483647>;;Max Allowed State on this interface";
                range "0..2147483647";
              }
            }
          }
          list connected {
            tailf:info
              "Limit connected incoming state";
            tailf:cli-suppress-mode;
            tailf:cli-delete-when-empty;
            tailf:cli-incomplete-command;
            key "access-list";
            leaf access-list {
              tailf:cli-suppress-range;
              type ip-acl-type;
            }
            leaf allowed-state {
              tailf:cli-drop-node-name;
              type uint32 {
                tailf:info
                  "<0-2147483647>;;Max Allowed State on this interface";
                range "0..2147483647";
              }
            }
          }
          list out {
            tailf:info
              "Limit outgoing state";
            tailf:cli-suppress-mode;
            tailf:cli-delete-when-empty;
            tailf:cli-incomplete-command;
            key "access-list";
            leaf access-list {
              tailf:cli-suppress-range;
              type ip-acl-type;
            }
            leaf allowed-state {
              tailf:cli-drop-node-name;
              type uint32 {
                tailf:info
                  "<0-2147483647>;;Max Allowed State on this interface";
                range "0..2147483647";
              }
            }
          }
          list rpf {
            tailf:info
              "Limit incoming state";
            tailf:cli-suppress-mode;
            tailf:cli-delete-when-empty;
            tailf:cli-incomplete-command;
            key "access-list";
            leaf access-list {
              tailf:cli-suppress-range;
              type ip-acl-type;
            }
            leaf allowed-state {
              tailf:cli-drop-node-name;
              type uint32 {
                tailf:info
                  "<0-2147483647>;;Max Allowed State on this interface";
                range "0..2147483647";
              }
            }
          }
        }
      }
      container policy {
        tailf:info
          "Enable policy routing";
        leaf route-map {
          tailf:info
            "Policy route-map";
          type string {
            tailf:info
              "WORD;;Route map name";
          }
        }
      }
      leaf unreachables {
        tailf:info
          "Enable sending ICMP Unreachable messages";
        tailf:cli-boolean-no;
        type boolean;
        default "true";
      }
      leaf proxy-arp {
        tailf:info
          "Enable proxy ARP";
        tailf:cli-boolean-no;
        type boolean;
        default "true";
      }
      container route-cache-conf {
        tailf:cli-drop-node-name;
        leaf route-cache {
          tailf:cli-boolean-no;
          tailf:cli-full-command;
          type boolean;
          default "true";
        }
      }
      container route-cache {
        tailf:info
          "Enable fast-switching cache for outgoing packets";
        tailf:cli-incomplete-no;
        tailf:cli-incomplete-command;
        leaf cef {
          tailf:info
            "Enable Cisco Express Forwarding";
          tailf:cli-boolean-no;
          type boolean;
          default "true";
        }
        leaf flow {
          tailf:info
            "Enable Flow fast-switching cache";
          tailf:cli-boolean-no;
          type boolean;
          default "false";
        }
        leaf policy {
          tailf:info
            "Enable fast-switching policy cache for outgoing packets";
          tailf:cli-boolean-no;
          type boolean;
          default "false";
        }
        leaf same-interface {
          tailf:info
            "Enable fast-switching on the same interface";
          tailf:cli-boolean-no;
          type boolean;
          default "false";
        }
      }
      leaf mroute-cache {
        tailf:info
          "Enable switching cache for incoming multicast packets";
        tailf:cli-boolean-no;
        tailf:cli-full-command;
        type boolean;
        default "true";
      }
      container igmp {
        tailf:info
          "IGMP interface commands";
        container max-groups {
          tailf:info
            "set maximum number of IGMP groups that can be joined";
          leaf number {
            tailf:cli-drop-node-name;
            tailf:cli-full-command;
            type uint32 {
              tailf:info
                "<0-4294967294>;;maximum # of groups";
            }
          }
          leaf action {
            tailf:info
              "action taken on exceeding the limit";
            tailf:cli-full-command;
            type enumeration {
              enum "deny" {
                tailf:info
                  "do not allow any more groups";
              }
              enum "replace" {
                tailf:info
                  "replace existing group with new";
              }
            }
            default "deny";
          }
        }
        leaf filter {
          tailf:info
            "set IGMP filter profile number";
          type uint32 {
            tailf:info
              "<1-4294967295>;;IGMP profile number";
            range "1..4294967295";
          }
        }
        list join-group {
          tailf:info
            "IGMP join multicast group";
          tailf:cli-suppress-mode;
          tailf:cli-delete-when-empty;
          tailf:cli-compact-syntax;
          key "address";
          leaf address {
            type inet:ipv4-address {
              tailf:info
                "A.B.C.D;;IP group address";
            }
          }
          leaf source {
            tailf:info
              "Include SSM source";
            type inet:ipv4-address {
              tailf:info
                "A.B.C.D;;IP source address";
            }
          }
        }
        container static-group {
          tailf:info
            "IGMP static multicast group";
          list groups {
            tailf:cli-drop-node-name;
            tailf:cli-suppress-mode;
            tailf:cli-delete-when-empty;
            key "name";
            leaf name {
              tailf:cli-suppress-range;
              type union {
                type inet:ipv4-address {
                  tailf:info
                    "A.B.C.D;;IP group address";
                }
                type enumeration {
                  enum "*" {
                    tailf:info
                      "Populated for all groups";
                  }
                }
              }
            }
          }
          list class-map {
            tailf:info
              "Class map of type multicast-flows";
            tailf:cli-suppress-mode;
            tailf:cli-delete-when-empty;
            key "id";
            leaf id {
              tailf:non-strict-leafref {
                path "/ncs:devices/ncs:device/ncs:config/ios:class-map/name" {
                  tailf:xpath-root 3;
                }
              }
              type string {
                tailf:info
                  "WORD;;Name of class-map of type multicast-flows";
              }
            }
          }
        }
        leaf version {
          tailf:info
            "IGMP version";
          type uint8 {
            tailf:info
              "<1-3>;;version number";
            range "1..3";
          }
        }
        leaf access-group {
          tailf:info
            "IGMP group access group";
          type exp-ip-acl-type;
        }
      }
      leaf redirects {
        tailf:info
          "Enable sending ICMP Redirect messages";
        tailf:cli-boolean-no;
        tailf:cli-full-command;
        type boolean;
        default "true";
      }
      container hello-interval {
        tailf:info
          "Configures EIGRP-IPv4 hello interval";
        list eigrp {
          tailf:info
            "Enhanced Interior Gateway Routing Protocol (EIGRP)";
          tailf:cli-suppress-mode;
          tailf:cli-delete-when-empty;
          tailf:cli-incomplete-command;
          key "as-number";
          leaf as-number {
            type uint16 {
              tailf:info
                "<1-65535>;;AS number";
            }
          }
          leaf seconds {
            tailf:cli-drop-node-name;
            type uint16 {
              tailf:info
                "<1-65535>;;Seconds between hello transmissions";
              range "1..65535";
            }
          }
        }
      }
      container hold-time {
        tailf:info
          "Configures EIGRP-IPv4 hold time";
        list eigrp {
          tailf:info
            "Enhanced Interior Gateway Routing Protocol (EIGRP)";
          tailf:cli-suppress-mode;
          tailf:cli-delete-when-empty;
          tailf:cli-incomplete-command;
          key "as-number";
          leaf as-number {
            type uint16 {
              tailf:info
                "<1-65535>;;AS number";
            }
          }
          leaf seconds {
            tailf:cli-drop-node-name;
            type uint16 {
              tailf:info
                "<1-65535>;;Seconds before neighbor is considered down";
              range "1..65535";
            }
          }
        }
      }
      container nbar {
        tailf:info
          "Network-Based Application Recognition";
        leaf protocol-discovery {
          tailf:info
            "Enable protocol discovery for both ipv4 and ipv6";
          type empty;
        }
      }
      container nhrp {
        tailf:info
          "NHRP interface subcommands";
        leaf authentication {
          tailf:info
            "Authentication string";
          type string {
            tailf:info
              "WORD;;authentication string";
          }
        }
        leaf group {
          tailf:info
            "NHRP group name";
          type string {
            tailf:info
              "WORD;;group name string";
          }
        }
        container map {
          tailf:info
            "Map dest IP addresses to NBMA addresses";
          list map-list {
            tailf:cli-drop-node-name;
            tailf:cli-suppress-mode;
            tailf:cli-delete-when-empty;
            key "ip-address";
            leaf ip-address {
              type inet:ipv4-address {
                tailf:info
                  "A.B.C.D;;IP address of destination";
              }
            }
            leaf nbma-address {
              tailf:cli-drop-node-name;
              type union {
                type inet:ipv4-address {
                  tailf:info
                    "A.B.C.D;;IP NBMA address";
                }
                type inet:ipv6-address {
                  tailf:info
                    "X:X:X:X::X;;IPv6 NBMA address";
                }
              }
            }
          }
          container multicast {
            tailf:info
              "Use this NBMA mapping for broadcasts/multicasts";
            leaf dynamic {
              tailf:info
                "Dynamically learn destinations from client registrations on hub";
              type empty;
            }
            list multicast-list {
              tailf:cli-drop-node-name;
              tailf:cli-suppress-mode;
              tailf:cli-delete-when-empty;
              key "nbma-address";
              leaf nbma-address {
                type union {
                  type inet:ipv4-address {
                    tailf:info
                      "A.B.C.D;;IP NBMA address";
                  }
                  type inet:ipv6-address {
                    tailf:info
                      "X:X:X:X::X;;IPv6 NBMA address";
                  }
                }
              }
            }
          }
          list group {
            tailf:info
              "NHRP group mapping";
            tailf:cli-suppress-mode;
            tailf:cli-delete-when-empty;
            tailf:cli-incomplete-command;
            key "name";
            leaf name {
              type string {
                tailf:info
                  "WORD;;NHRP group name";
              }
            }
            container service-policy {
              tailf:info
                "QoS service-policy";
              leaf output {
                tailf:info
                  "apply QoS service policy in the output direction";
                tailf:non-strict-leafref {
                  path "/ncs:devices/ncs:device/ncs:config/ios:policy-map/name" {
                    tailf:xpath-root 3;
                  }
                }
                type string {
                  tailf:info
                    "WORD;;QoS policy-map name";
                }
              }
            }
          }
        }
        leaf network-id {
          tailf:info
            "NBMA network identifier";
          type union {
            type uint32 {
              tailf:info
                "<1-4294967295>;;Network identifier";
            }
            type inet:ipv4-address {
              tailf:info
                "A.B.C.D;;IP address";
            }
          }
        }
        leaf holdtime {
          tailf:info
            "Advertised holdtime";
          type uint16 {
            tailf:info
              "<1-65535>;;Number of seconds";
            range "1..65535";
          }
        }
        container nhs {
          tailf:info
            "Specify a next hop server";
          list nhs-list {
            tailf:cli-drop-node-name;
            tailf:cli-suppress-mode;
            tailf:cli-delete-when-empty;
            tailf:cli-compact-syntax;
            key "nhs-address";
            leaf nhs-address {
              type inet:ipv4-address {
                tailf:info
                  "A.B.C.D;;Protocol IP address of NHS";
              }
            }
            leaf nbma {
              tailf:info
                "NBMA of NHS";
              type union {
                type inet:ipv4-address {
                  tailf:info
                    "A.B.C.D;;IPv4 address";
                }
                type inet:ipv6-address {
                  tailf:info
                    "X:X:X:X::X;;IPv6 address";
                }
                type string {
                  tailf:info
                    "WORD;;NHS FQDN string";
                }
              }
            }
            leaf multicast {
              when "../nbma" {
                tailf:xpath-root 3;
                tailf:dependency "../nbma";
              }
              tailf:info
                "Use this NBMA mapping for broadcasts/multicasts";
              type empty;
            }
          }
        }
        container server-only {
          tailf:info
            "Disable NHRP requests";
          tailf:cli-reset-container;
          tailf:cli-delete-when-empty;
          presence "true";
          leaf non-caching {
            tailf:info
              "Do not create NHRP cache entries";
            type empty;
          }
        }
        container registration {
          tailf:info
            "Settings for registration packets.";
          leaf no-unique {
            tailf:info
              "Do not set the 'Unique' flag in registration requests.";
            type empty;
          }
          leaf timeout {
            tailf:info
              "Time between periodic Registration messages";
            type uint16 {
              tailf:info
                "<1-65535>;;Number of seconds";
              range "1..65535";
            }
          }
        }
        container shortcut {
          tailf:info
            "Enable shortcut switching";
          tailf:cli-delete-when-empty;
          presence "true";
          leaf virtual-template {
            tailf:info
              "Virtual template interface number";
            type uint16 {
              tailf:info
                "<1-200>;;Virtual template number";
            }
          }
        }
        container redirect {
          tailf:info
            "Enable NHRP redirect traffic indication";
          tailf:cli-delete-when-empty;
          presence "true";
          leaf timeout {
            tailf:info
              "Specify interval over which to throttle";
            type uint8 {
              tailf:info
                "<2-30>;;Interval in seconds";
              range "2..30";
            }
          }
        }
      }
      container tcp {
        tailf:info
          "TCP header compression and other parameters";
        leaf adjust-mss {
          tailf:info
            "Adjust the mss of transit packets";
          type uint16 {
            tailf:info
              "<500-1460>;;Maximum segment size in bytes";
            range "500..1460";
          }
        }
        container header-compression {
          tailf:info
            "Enable TCP header compression";
          tailf:cli-delete-when-empty;
          presence "true";
          leaf type {
            tailf:cli-drop-node-name;
            type enumeration {
              enum "ietf-format" {
                tailf:info
                  "Compressing using IETF format";
              }
              enum "iphc-format" {
                tailf:info
                  "Using PPP  IPHC compression for TCP/UDP/RTP";
              }
              enum "passive" {
                tailf:info
                  "Compress only for destinations which send compressed headers";
              }
            }
          }
        }
        leaf compression-connections {
          tailf:info
            "Maximum number of compressed connections";
          type uint16 {
            tailf:info
              "<1-256>;;Number of connections";
            range "1..256";
          }
        }
      }
      container rtp {
        tailf:info
          "RTP parameters";
        container header-compression {
          tailf:info
            "Enable RTP header compression";
          tailf:cli-compact-syntax;
          tailf:cli-sequence-commands {
            tailf:cli-reset-siblings;
          }
          leaf type {
            tailf:cli-drop-node-name;
            tailf:cli-optional-in-sequence;
            type enumeration {
              enum "ietf-format" {
                tailf:info
                  "Compressing using IETF format";
              }
              enum "iphc-format" {
                tailf:info
                  "Compress using IPHC format";
              }
              enum "passive" {
                tailf:info
                  "Compress only for destinations which send compressed headers";
              }
            }
          }
          leaf periodic-refresh {
            tailf:info
              "Periodic context refresh";
            type empty;
          }
        }
        leaf compression-connections {
          tailf:info
            "Maximum number of compressed connections";
          type uint16 {
            tailf:info
              "<1-1000>;;Number of connections";
            range "1..1000";
          }
        }
      }
      container header-compression {
        tailf:info
          "IPHC options";
        leaf max-header {
          tailf:info
            "Maximim compressible header";
          type uint8 {
            tailf:info
              "<20-168>;;Maximim compressible header";
            range "20..168";
          }
        }
      }
      container mobile {
        tailf:info
          "Mobile IP support";
        container router-service {
          tailf:info
            "Mobile router support";
          container roam {
            tailf:info
              "Roaming interface";
            presence "true";
            leaf priority {
              tailf:info
                "Priority level";
              type uint8 {
                tailf:info
                  "<0-255>;;Priority level";
              }
            }
          }
          leaf description {
            tailf:info
              "roaming interface description";
            tailf:cli-multi-value;
            tailf:cli-preformatted;
            tailf:cli-full-command;
            type string {
              tailf:info
                "LINE;;roaming interface description";
            }
          }
          leaf link-type {
            tailf:info
              "Link type of the roaming interface";
            type string;
          }
          container tunnel {
            tailf:info
              "Tunnel parameters";
            leaf mode {
              tailf:info
                "Tunnel encapsulation mode";
              type enumeration {
                enum "gre" {
                  tailf:info
                    "Generic Routing Encapsulation";
                }
                enum "ipip" {
                  tailf:info
                    "IP-in-IP Encapsulation";
                }
              }
            }
          }
          container collocated {
            tailf:info
              "Collocated care-of address options";
            tailf:cli-compact-syntax;
            tailf:cli-sequence-commands;
            leaf gateway {
              tailf:info
                "Default gateway for static collocated care-of address";
              tailf:cli-optional-in-sequence;
              type inet:ipv4-address {
                tailf:info
                  "A.B.C.D;;IP address to use as the default gateway";
              }
            }
            leaf ccoa-only {
              tailf:info
                "Only register a collocated CoA";
              tailf:cli-optional-in-sequence;
              type empty;
            }
            container registration {
              tailf:info
                "Registration options";
              tailf:cli-break-sequence-commands;
              leaf retry {
                tailf:info
                  "Retry interval in seconds (1-65535)";
                type uint16 {
                  tailf:info
                    "<1-65535>;;Seconds (default 60; 65535 = never)";
                  range "1..65535";
                }
                default "60";
              }
              container nat {
                tailf:info
                  "NAT traversal settings";
                container traversal {
                  tailf:info
                    "Enable NAT traversal support";
                  tailf:cli-compact-syntax;
                  presence "true";
                  leaf keepalive {
                    tailf:info
                      "Keepalive message frequency (sec)";
                    type uint16 {
                      tailf:info
                        "<0-65535>;;keepalive value";
                    }
                  }
                  leaf force {
                    tailf:info
                      "Force home agent to use UDP encapsulation for the tunnel";
                    type empty;
                  }
                }
              }
            }
            leaf encapsulation {
              type enumeration {
                enum "slip";
                enum "ppp";
              }
            }
          }
        }
      }
      list inspect {
        tailf:cli-suppress-mode;
        tailf:cli-delete-when-empty;
        tailf:cli-compact-syntax;
        tailf:cli-sequence-commands {
          tailf:cli-reset-siblings;
        }
        key "direction";
        leaf direction {
          type enumeration {
            enum "in" {
              tailf:info
                "Inbound inspection";
            }
            enum "out" {
              tailf:info
                "Outbound inspection";
            }
          }
        }
        leaf name {
          tailf:cli-prefix-key;
          tailf:cli-drop-node-name;
          tailf:non-strict-leafref {
            path "/ncs:devices/ncs:device/ncs:config/ios:ip/inspect/name/name" {
              tailf:xpath-root 3;
            }
          }
          type string {
            tailf:info
              "WORD;;Name of inspection defined";
          }
        }
      }
      container virtual-reassembly {
        tailf:info
          "Enable Virtual Fragment Reassembly";
        tailf:cli-delete-when-empty;
        presence "true";
        leaf in {
          tailf:info
            "Enable VFR on Ingress";
          tailf:cli-full-command;
          type empty;
        }
        leaf out {
          tailf:info
            "Enable VFR on Egress";
          tailf:cli-full-command;
          type empty;
        }
        container conf {
          tailf:cli-drop-node-name;
          tailf:cli-compact-syntax;
          leaf drop-fragments {
            tailf:info
              "Drop all the incoming fragments";
            type empty;
          }
          leaf max-fragments {
            tailf:info
              "Specify max number of fragments per reassembly (datagram)";
            type uint8 {
              tailf:info
                "<1-64>;;Number of fragments per datagram";
              range "1..64";
            }
          }
          leaf max-reassemblies {
            tailf:info
              "Specify max number of concurrent reassemblies";
            type uint16 {
              tailf:info
                "<1-1024>;;Number of datagrams that can be reassembled at a time";
              range "1..1024";
            }
          }
          leaf timeout {
            tailf:info
              "Specify timeout value of the datagram being reassembled";
            type uint8 {
              tailf:info
                "<1-60>;;Timeout value of the datagram being reassembled";
            }
          }
          leaf percentage {
            tailf:info
              "Reserved Reassembly capacity for high priority packets";
            type uint8 {
              tailf:info
                "<1-100>;;Reserved Reassembly capacity percentage";
              range "1..100";
            }
          }
          leaf-list dscp {
            tailf:info
              "DSCP value";
            tailf:cli-flat-list-syntax;
            tailf:cli-full-command;
            type dscp-type;
          }
          leaf-list precedence {
            tailf:info
              "IP precedence";
            tailf:cli-flat-list-syntax;
            tailf:cli-full-command;
            type precedence-type;
          }
        }
      }
      container dns {
        tailf:info
          "Configure DNS server";
        leaf view-group {
          tailf:info
            "Configure a DNS view-list for use on this interface";
          tailf:non-strict-leafref {
            path "/ncs:devices/ncs:device/ncs:config/ios:ip/dns/view-list/name" {
              tailf:xpath-root 3;
            }
          }
          type string {
            tailf:info
              "WORD;;View-list name";
          }
        }
      }
      container dhcp {
        tailf:info
          "Configure DHCP parameters for this interface";
        container relay {
          tailf:info
            "DHCP relay configuration parameters";
          container information {
            tailf:info
              "DHCP relay information option";
            container check-reply {
              tailf:info
                "Validate relay information in BOOTREPLY";
              presence "true";
              leaf none {
                tailf:info
                  "Set to none";
                type empty;
              }
            }
            container option {
              tailf:info
                "DHCP relay information option";
              leaf subscriber-id {
                tailf:info
                  "Subscriber identifier sub option";
                type string {
                  tailf:info
                    "WORD;;Subscriber identifier string";
                }
              }
            }
            container option-insert {
              tailf:info
                "Insert relay information in BOOTREQUEST";
              presence "true";
              leaf none {
                tailf:info
                  "Set to none";
                type empty;
              }
            }
            leaf policy-action {
              tailf:info
                "Define reforwarding policy";
              type enumeration {
                enum "drop" {
                  tailf:info
                    "Do not forward BOOTREQUEST message";
                }
                enum "encapsulate" {
                  tailf:info
                    "Encapsulate existing information";
                }
                enum "keep" {
                  tailf:info
                    "Leave existing information alone";
                }
                enum "replace" {
                  tailf:info
                    "Replace existing information";
                }
              }
            }
            leaf trusted {
              tailf:info
                "Received DHCP packet may contain relay info option with zero giaddr";
              type empty;
            }
          }
        }
        container snooping {
          tailf:info
            "DHCP Snooping";
          container limit {
            tailf:info
              "DHCP Snooping limit";
            leaf rate {
              tailf:info
                "DHCP Snooping limit";
              type uint16 {
                tailf:info
                  "<1-2048>;;DHCP snooping rate limit";
                range "1..2048";
              }
            }
          }
          leaf trust {
            tailf:info
              "DHCP Snooping trust config";
            type empty;
          }
          list vlan {
            tailf:info
              "DHCP Snooping vlan";
            tailf:cli-suppress-mode;
            tailf:cli-delete-when-empty;
            tailf:cli-compact-syntax;
            key "id";
            leaf id {
              type uint16 {
                tailf:info
                  "<1-4094>;;DHCP Snooping vlan";
                range "1..4094";
              }
            }
            container information {
              tailf:info
                "DHCP Snooping information";
              tailf:cli-flatten-container;
              container option {
                tailf:info
                  "DHCP Snooping information option";
                container format-type {
                  tailf:info
                    "Option 82 information format";
                  container circuit-id {
                    tailf:info
                      "Circuit id option 82 format";
                    leaf string {
                      tailf:info
                        "User defined string for circuit id";
                      type string {
                        tailf:info
                          "WORD;;Use string for circuit id (3-63 chars)";
                        length "3..63";
                      }
                    }
                  }
                }
              }
            }
          }
          list bridge-domain {
            tailf:info
              "DHCP Snooping bridge-domain";
            tailf:cli-suppress-mode;
            tailf:cli-delete-when-empty;
            tailf:cli-compact-syntax;
            key "id";
            leaf id {
              type uint16 {
                tailf:info
                  "<1-4094>;;DHCP Snooping bridge-domain number";
                range "1..4094";
              }
            }
            container information {
              tailf:info
                "DHCP Snooping information";
              tailf:cli-flatten-container;
              container option {
                tailf:info
                  "DHCP Snooping information option";
                container format-type {
                  tailf:info
                    "Option 82 information format";
                  container circuit-id {
                    tailf:info
                      "Circuit id option 82 format";
                    leaf string {
                      tailf:info
                        "User defined string for circuit id";
                      type string {
                        tailf:info
                          "WORD;;Use string for circuit id";
                      }
                    }
                  }
                }
              }
            }
          }
        }
      }
      leaf mtu {
        tailf:info
          "Set IP Maximum Transmission Unit";
        type uint16 {
          tailf:info
            "<68-9216>;;MTU (bytes)";
          range "68..9216";
        }
      }
      container nat {
        tailf:info
          "NAT interface commands";
        leaf allow-static-host {
          tailf:info
            "Allow static-ip clients";
          type empty;
        }
        leaf enable {
          tailf:info
            "Enable Address Translation (NVI)";
          type empty;
        }
        choice nat-choice {
          leaf inside {
            tailf:info
              "Inside interface for address translation";
            type empty;
          }
          leaf outside {
            tailf:info
              "Outside interface for address translation";
            type empty;
          }
        }
      }
      container rsvp {
        tailf:info
          "RSVP Interface Commands";
        container bandwidth {
          tailf:info
            "RSVP Reservable Bandwidth (kbps)";
          tailf:cli-compact-syntax;
          tailf:cli-sequence-commands {
            tailf:cli-reset-siblings;
          }
          tailf:cli-delete-when-empty;
          presence "true";
          leaf interface-bandwidth {
            tailf:cli-drop-node-name;
            type uint32 {
              tailf:info
                "<1-10000000>;;Reservable Bandwidth (kbps)";
              range "1..10000000";
            }
          }
          leaf single-flow-bandwidth {
            tailf:cli-drop-node-name;
            type uint32 {
              tailf:info
                "<1-10000000>;;Largest Reservable Flow (kbps)";
              range "1..10000000";
            }
          }
        }
        container signalling {
          tailf:info
            "RSVP signalling";
          container hello {
            tailf:info
              "Enable neighbor-down detection";
            presence "true";
            container graceful-restart {
              tailf:info
                "Configure RSVP Graceful Restart";
              presence "true";
            }
          }
        }
        container resource-provider {
          tailf:info
            "RSVP resource provider";
          choice resource-provider-choice {
            leaf none {
              tailf:info
                "Associates NO resources with reservations";
              type empty;
            }
            leaf wfq {
              tailf:info
                "Associates WFQ resources with reservations";
              type enumeration {
                enum "interface" {
                  tailf:info
                    "Associates WFQ queues and bandwidth at the interface level with reservations";
                }
                enum "pvc" {
                  tailf:info
                    "Associates WFQ queues and bandwidth at the PVC level with reservations";
                }
              }
            }
          }
        }
      }
      container verify {
        tailf:info
          "Enable per packet validation";
        container unicast {
          tailf:info
            "Enable per packet validation for unicast";
          container reverse-path {
            tailf:info
              "Reverse path validation of source address (old command format)";
            presence "true";
          }
          container source {
            tailf:info
              "Validation of source address";
            tailf:cli-compact-syntax;
            tailf:cli-sequence-commands {
              tailf:cli-reset-all-siblings;
            }
            leaf reachable-via {
              tailf:info
                "Specify reachability check to apply to the source address";
              type enumeration {
                enum "any" {
                  tailf:info
                    "Source is reachable via any interface";
                }
                enum "rx" {
                  tailf:info
                    "Source is reachable via interface on which packet was received";
                }
              }
            }
            leaf allow-self-ping {
              tailf:cli-break-sequence-commands;
              tailf:info
                "Allow router to ping itself (opens vulnerability in verification)";
              type empty;
            }
            leaf allow-default {
              tailf:info
                "Allow default route to match when checking source address";
              type empty;
            }
            leaf access-list {
              tailf:cli-drop-node-name;
              tailf:cli-disallow-value "allow-self-ping|allow-default";
              type exp-ip-acl-type;
            }
          }
        }
        container source {
          tailf:info
            "source address";
          tailf:cli-delete-when-empty;
          presence "true";
          container vlan {
            tailf:info
              "vlan specification";
            container dhcp-snooping {
              tailf:info
                "snooping enable vlan";
              tailf:cli-reset-container;
              tailf:cli-delete-when-empty;
              presence "true";
              leaf port-security {
                tailf:info
                  "port security";
                type empty;
              }
            }
          }
        }
      }
      container rip {
        tailf:info
          "Router Information Protocol";
        container send {
          tailf:info
            "advertisement transmission";
          leaf version {
            tailf:info
              "version control";
            type enumeration {
              enum "1" {
                tailf:info
                  "RIP version 1";
              }
              enum "2" {
                tailf:info
                  "RIP version 2";
              }
            }
          }
        }
        container receive {
          tailf:info
            "advertisement reception";
          leaf version {
            tailf:info
              "version control";
            type enumeration {
              enum "1" {
                tailf:info
                  "RIP version 1";
              }
              enum "2" {
                tailf:info
                  "RIP version 2";
              }
            }
          }
        }
        container authentication {
          tailf:info
            "Authentication control";
          leaf mode {
            tailf:info
              "Authentication mode";
            type enumeration {
              enum "md5" {
                tailf:info
                  "Keyed message digest";
              }
              enum "text" {
                tailf:info
                  "Clear text authentication";
              }
            }
          }
          leaf key-chain {
            tailf:info
              "Authentication key-chain";
            tailf:non-strict-leafref {
              path "/ncs:devices/ncs:device/ncs:config/ios:key/chain/name" {
                tailf:xpath-root 3;
              }
            }
            type string {
              tailf:info
                "LINE;;name of key-chain";
            }
          }
        }
      }
      leaf mask-reply {
        tailf:info
          "Enable sending ICMP Mask Reply messages";
        tailf:cli-full-command;
        type empty;
      }
      container bandwidth-percent {
        tailf:info
          "Set EIGRP bandwidth limit";
        list eigrp {
          tailf:info
            "Enhanced Interior Gateway Routing Protocol (EIGRP)";
          tailf:cli-suppress-mode;
          tailf:cli-delete-when-empty;
          tailf:cli-incomplete-command;
          key "as-number";
          leaf as-number {
            type uint16 {
              tailf:info
                "<1-65535>;;AS number";
            }
          }
          leaf percent {
            tailf:cli-drop-node-name;
            type uint32 {
              tailf:info
                "<1-999999>;;Maximum bandwidth percentage that EIGRP may use";
              range "1..999999";
            }
          }
        }
      }
      container next-hop-self {
        tailf:info
          "Configures EIGRP-IPv4 next-hop-self";
        container eigrp {
          tailf:info
            "Enhanced Interior Gateway Routing Protocol (EIGRP)";
          list no-list {
            tailf:info
              "'no ip next-hop-self eigrp' entry";
            tailf:cli-suppress-mode;
            tailf:cli-delete-when-empty;
            key "as-number";
            leaf as-number {
              type uint16 {
                tailf:info
                  "<1-65535>;;AS number";
                range "1..65535";
              }
            }
          }
        }
      }
      container lisp {
        tailf:info
          "Locator/ID Separation Protocol";
        container source-locator {
          tailf:info
            "Choose IP source address for LISP packets egressing this interface";
          uses interface-name-grouping;
        }
      }
      container wccp {
        tailf:info
          "WCCP IPv4 interface commands";
        tailf:cli-diff-dependency "/ios:ip/wccp" {
          tailf:xpath-root 3;
        }
        uses interface-ip-wccp-grouping;
        list vrf {
          tailf:info
            "Configure WCCP for a VRF";
          tailf:cli-suppress-mode;
          tailf:cli-delete-when-empty;
          tailf:cli-compact-syntax;
          tailf:cli-incomplete-command;
          key "name";
          leaf name {
            tailf:cli-diff-dependency "/ios:vrf/definition" {
              tailf:xpath-root 3;
            }
            type string {
              tailf:info
                "WORD;;VRF name";
            }
          }
          uses interface-ip-wccp-grouping;
        }
      }
    }
    container ipv6 {
      tailf:info
        "IPv6 interface subcommands";
      container address {
        tailf:info
          "Configure IPv6 address on interface";
        choice address-choice {
          case autoconfig-case {
            container autoconfig {
              tailf:info
                "Obtain address using autoconfiguration";
              presence "true";
              leaf default {
                tailf:info
                  "Insert default route";
                type empty;
              }
            }
          }
          case dhcp-case {
            container dhcp {
              tailf:info
                "Obtain a ipv6 address using dhcp";
              tailf:cli-reset-container;
              tailf:cli-delete-when-empty;
              presence "true";
              leaf rapid-commit {
                tailf:info
                  "Enable Rapid-Commit";
                type empty;
              }
            }
          }
          case manual-case {
            list prefix-list {
              tailf:cli-drop-node-name;
              tailf:cli-suppress-mode;
              tailf:cli-delete-when-empty;
              key "prefix";
              leaf prefix {
                type union {
                  type ios:ipv6-prefix {
                    tailf:info
                      "X:X:X:X::X/<0-128>;;IPv6 prefix";
                  }
                  type inet:ipv6-address {
                    tailf:info
                      "X:X:X:X::X;;IPv6 link-local address";
                  }
                }
              }
              leaf link-local {
                tailf:info
                  "Use link-local address";
                tailf:cli-full-command;
                type empty;
              }
              leaf anycast {
                tailf:info
                  "Configure as an anycast";
                tailf:cli-full-command;
                type empty;
              }
              leaf eui-64 {
                tailf:info
                  "Use eui-64 interface identifier";
                tailf:cli-full-command;
                type empty;
              }
            }
          }
        }
      }
      leaf enable {
        tailf:info
          "Enable IPv6 on interface";
        type empty;
      }
      container unnumbered {
        tailf:info
          "Preferred interface for source address selection";
        uses interface-name-grouping;
      }
      list traffic-filter {
        tailf:info
          "Access control list for packets";
        tailf:cli-suppress-mode;
        tailf:cli-delete-when-empty;
        tailf:cli-compact-syntax;
        tailf:cli-sequence-commands;
        key "direction";
        leaf direction {
          type enumeration {
            enum "in" {
              tailf:info
                "inbound packets";
            }
            enum "out" {
              tailf:info
                "outbound packets";
            }
          }
        }
        leaf access-list {
          tailf:cli-drop-node-name;
          tailf:cli-prefix-key;
          type string {
            tailf:info
              "WORD;;Access-list name";
          }
        }
      }
      container nd {
        tailf:info
          "IPv6 interface Neighbor Discovery subcommands";
        container dad {
          tailf:info
            "Duplicate Address Detection";
          leaf attempts {
            tailf:info
              "Set IPv6 Duplicate Address Detection Transmits";
            type uint16 {
              tailf:info
                "<0-600>;;Number of attempts";
              range "0..600";
            }
          }
        }
        leaf reachable-time {
          tailf:info
            "Set advertised reachability time";
          type uint32 {
            tailf:info
              "<0-3600000>;;Reachability time in milliseconds";
            range "0..3600000";
          }
        }
        container prefix {
          tailf:info
            "Configure IPv6 Routing Prefix Advertisement";
          list prefix-list {
            tailf:cli-drop-node-name;
            tailf:cli-suppress-mode;
            tailf:cli-delete-when-empty;
            tailf:cli-compact-syntax;
            tailf:cli-sequence-commands {
              tailf:cli-reset-all-siblings;
            }
            tailf:cli-incomplete-command;
            key "ipv6-prefix";
            leaf ipv6-prefix {
              type union {
                type ipv6-prefix {
                  tailf:info
                    "X:X:X:X::X/<0-128>;;IPv6 prefix x:x::y/<z>";
                }
                type enumeration {
                  enum "default" {
                    tailf:info
                      "Specify prefix default parameters";
                  }
                }
              }
            }
            choice advertise-choice {
              case no-advertise {
                leaf no-advertise {
                  tailf:info
                    "Do not advertise prefix";
                  tailf:cli-full-command;
                  type empty;
                }
              }
              case advertise {
                leaf valid-lifetime {
                  tailf:cli-drop-node-name;
                  tailf:cli-incomplete-command;
                  type union {
                    type enumeration {
                      enum "infinite" {
                        tailf:info
                          "Infinite Valid Lifetime";
                      }
                    }
                    type uint32 {
                      tailf:info
                        "<0-4294967295>;;Valid Lifetime (secs)";
                    }
                  }
                }
                leaf preferred-lifetime {
                  tailf:cli-drop-node-name;
                  type union {
                    type enumeration {
                      enum "infinite" {
                        tailf:info
                          "Infinite Preferred Lifetime";
                      }
                    }
                    type uint32 {
                      tailf:info
                        "<0-4294967295>;;Preferred Lifetime (secs)";
                    }
                  }
                }
                leaf off-link {
                  tailf:cli-break-sequence-commands;
                  tailf:info
                    "Prefix is offlink";
                  type empty;
                }
                leaf no-autoconfig {
                  tailf:info
                    "Do not use prefix for autoconfiguration";
                  type empty;
                }
                leaf no-rtr-address {
                  tailf:info
                    "Do not send full router address in prefix advert";
                  type empty;
                }
                leaf no-onlink {
                  tailf:info
                    "Do not use prefix for onlink determination";
                  type empty;
                }
              }
            }
          }
        }
        leaf managed-config-flag {
          tailf:info
            "Hosts should use DHCP for address config";
          type empty;
        }
        leaf other-config-flag {
          tailf:info
            "Hosts should use DHCP for non-address config";
          type empty;
        }
        container ra {
          tailf:info
            "Router Advertisement control";
          container suppress {
            tailf:info
              "Suppress IPv6 Router Advertisements";
            tailf:cli-delete-when-empty;
            presence "true";
            leaf all {
              tailf:info
                "Suppress all ipv6 Router advertisements";
              type empty;
            }
          }
          container interval {
            choice interval-choice {
              leaf seconds {
                tailf:cli-drop-node-name;
                type uint16 {
                  tailf:info
                    "<4-1800>;;RA Interval (sec)";
                  range "4..1800";
                }
              }
              leaf msec {
                tailf:info
                  "Interval in milliseconds";
                type uint32 {
                  tailf:info
                    "<70-1800000>;;RA Interval (msec)";
                  range "70..1800000";
                }
              }
            }
          }
          leaf lifetime {
            tailf:info
              "Set IPv6 Router Advertisement Lifetime";
            tailf:cli-full-command;
            type uint16 {
              tailf:info
                "<0-9000>;;RA Lifetime (seconds)";
              range "0..9000";
            }
          }
        }
        container raguard {
          tailf:info
            "apply the router advertisements (RA) guard feature";
          presence "true";
        }
        container autoconfig {
          tailf:info
            "Automatic Configuration";
          leaf prefix {
            tailf:info
              "Prefix";
            tailf:cli-full-command;
            type empty;
          }
          leaf default-route {
            tailf:info
              "Default Route";
            tailf:cli-full-command;
            type empty;
          }
        }
      }
      container mld {
        tailf:info
          "interface commands";
        leaf access-group {
          tailf:info
            "source, group membership access";
          type string {
            tailf:info
              "WORD;;Named access list specifying access group range";
          }
        }
      }
      leaf redirects {
        tailf:info
          "Enable sending of ICMP Redirect messages";
        tailf:cli-boolean-no;
        tailf:cli-full-command;
        type boolean;
        default "true";
      }
      leaf unreachables {
        tailf:info
          "Enable sending of ICMP Unreachable messages";
        tailf:cli-boolean-no;
        tailf:cli-full-command;
        type boolean;
        default "true";
      }
      container tcp {
        tailf:info
          "TCP interface commands";
        leaf adjust-mss {
          tailf:info
            "Adjust the mss of IPV6 transit packets";
          type uint16 {
            tailf:info
              "<40-1454>;;Maximum segment size in bytes";
            range "40..1454";
          }
        }
      }
      container router {
        tailf:info
          "IPv6 Router interface commands";
        container isis {
          tailf:info
            "isis  IS-IS Routing for IPv6";
          tailf:cli-delete-when-empty;
          presence "true";
          leaf tag {
            tailf:cli-drop-node-name;
            type string {
              tailf:info
                "WORD;;Routing process tag";
            }
          }
        }
      }
      container ospf {
        tailf:info
          "OSPF interface commands";
        leaf network {
          tailf:info
            "Network type";
          tailf:cli-full-command;
          type enumeration {
            enum "broadcast" {
              tailf:info
                "Specify OSPF broadcast multi-access network";
            }
            enum "non-broadcast" {
              tailf:info
                "Specify OSPF NBMA network";
            }
            enum "point-to-multipoint" {
              tailf:info
                "Specify OSPF point-to-multipoint network";
            }
            enum "point-to-point" {
              tailf:info
                "Specify OSPF point-to-point network";
            }
          }
        }
        list process {
          tailf:cli-drop-node-name;
          tailf:cli-suppress-mode;
          tailf:cli-delete-when-empty;
          tailf:cli-compact-syntax;
          tailf:cli-sequence-commands {
            tailf:cli-reset-siblings;
          }
          key "id";
          leaf id {
            type uint16 {
              tailf:info
                "<1-65535>;;Process ID";
              range "1..65535";
            }
          }
          leaf area {
            tailf:info
              "Set the OSPF area ID";
            type union {
              type uint32 {
                tailf:info
                  "<0-4294967295>;;OSPF area ID as a decimal value";
                range "0..4294967295";
              }
              type inet:ipv4-address {
                tailf:info
                  "A.B.C.D;;OSPF area ID in IP address format";
              }
            }
          }
          leaf instance {
            tailf:info
              "Set the OSPF instance";
            type union {
              type uint8 {
                tailf:info
                  "<0-31>;;Instance ID";
                range "0..31";
              }
              type uint8 {
                tailf:info
                  "<32-255>;;Instance ID (DEPRECATED!)";
                range "32..255";
              }
            }
          }
        }
        container bfd {
          tailf:info
            "Enable BFD on this interface";
          presence "true";
          leaf disable {
            tailf:info
              "Disable BFD on this interface";
            type empty;
          }
        }
        leaf cost {
          tailf:info
            "Route cost of this interface";
          type uint16 {
            tailf:info
              "<1-65535>;;Route cost of this interface";
            range "1..65535";
          }
        }
        container database-filter {
          tailf:info
            "Filter OSPF LSA during synchronization and flooding";
          choice database {
            leaf all {
              tailf:info
                "Filter all LSA";
              type enumeration {
                enum "out" {
                  tailf:info
                    "Outgoing LSA";
                }
              }
            }
            leaf disable {
              tailf:info
                "Disable LSA Filter on this interface";
              type empty;
            }
          }
        }
        leaf dead-interval {
          tailf:info
            "Interval after which a neighbor is declared dead";
          type uint16 {
            tailf:info
              "<1-65535>;;Seconds";
            range "1..65535";
          }
        }
        container demand-circuit {
          tailf:info
            "OSPF demand circuit";
          presence "true";
          leaf disable {
            tailf:info
              "Disable demand circuit on this interface";
            type empty;
          }
        }
        container flood-reduction {
          tailf:info
            "OSPF Flood Reduction";
          presence "true";
          leaf disable {
            tailf:info
              "Disable Flood Reduction on this interface";
            type empty;
          }
        }
        leaf hello-interval {
          tailf:info
            "Time between HELLO packets";
          type uint16 {
            tailf:info
              "<1-65535>;;Seconds";
            range "1..65535";
          }
        }
        container mtu-ignore {
          tailf:info
            "Ignores the MTU in DBD packets";
          presence "true";
          leaf disable {
            tailf:info
              "Disable Ingore MTU on this interface";
            type empty;
          }
        }
        leaf priority {
          tailf:info
            "Router priority";
          type uint16 {
            tailf:info
              "<0-255>;;Priority";
            range "0..255";
          }
        }
        leaf retransmit-interval {
          tailf:info
            "Time between retransmitting lost link state advertisements";
          type uint16 {
            tailf:info
              "<1-65535>;;Seconds";
            range "1..65535";
          }
        }
        leaf transmit-delay {
          tailf:info
            "Link state transmit delay";
          type uint16 {
            tailf:info
              "<1-65535>;;Seconds";
            range "1..65535";
          }
        }
      }
      leaf-list eigrp {
        tailf:cli-list-syntax;
        tailf:cli-full-command;
        type uint16 {
          tailf:info
            "<1-65535>;;AS number";
          range "1..65535";
        }
      }
      leaf mtu {
        tailf:info
          "Set IPv6 Maximum Transmission Unit";
        type uint16 {
          tailf:info
            "<1280-9198>;;MTU (bytes)";
          range "1280..9198";
        }
      }
      container crypto {
        tailf:info
          "Encryption/Decryption commands";
        container map {
          tailf:info
            "Assign a Crypto Map";
          tailf:cli-compact-syntax;
          tailf:cli-sequence-commands {
            tailf:cli-reset-siblings;
          }
          tailf:cli-diff-dependency "/ios:crypto/map" {
            tailf:xpath-root 3;
          }
          leaf map-name {
            tailf:cli-drop-node-name;
            tailf:non-strict-leafref {
              path "/ncs:devices/ncs:device/ncs:config/ios:crypto/map/name" {
                tailf:xpath-root 3;
              }
            }
            type string {
              tailf:info
                "WORD;;Crypto Map tag";
            }
          }
          leaf redundancy {
            tailf:info
              "enable redundancy";
            type string {
              tailf:info
                "WORD;;Name of IP Redundancy Group";
            }
          }
          leaf stateful {
            tailf:info
              "enable stateful failover";
            when "../redundancy" {
              tailf:xpath-root 3;
              tailf:dependency "../redundancy";
            }
            type empty;
          }
        }
      }
      container hold-time {
        tailf:info
          "Configures EIGRP-IPv6 hold time";
        list eigrp {
          tailf:info
            "Enhanced Interior Gateway Routing Protocol (EIGRP)";
          tailf:cli-suppress-mode;
          tailf:cli-delete-when-empty;
          key "as-no";
          leaf as-no {
            type uint16 {
              tailf:info
                "<1-65535>;;AS number";
              range "1..65535";
            }
          }
          leaf seconds {
            tailf:cli-drop-node-name;
            type uint16 {
              tailf:info
                "<1-65535>;;Seconds before neighbor is considered down";
              range "1..65535";
            }
          }
        }
      }
      container hello-interval {
        tailf:info
          "Configures EIGRP-IPv6 hello interval";
        list eigrp {
          tailf:info
            "Enhanced Interior Gateway Routing Protocol (EIGRP)";
          tailf:cli-suppress-mode;
          tailf:cli-delete-when-empty;
          key "as-no";
          leaf as-no {
            type uint16 {
              tailf:info
                "<1-65535>;;AS number";
              range "1..65535";
            }
          }
          leaf seconds {
            tailf:cli-drop-node-name;
            type uint16 {
              tailf:info
                "<1-65535>;;Seconds between hello transmission";
              range "1..65535";
            }
          }
        }
      }
      container verify {
        tailf:info
          "Enable per packet validation";
        container unicast {
          tailf:info
            "Enable per packet validation for unicast";
          container source {
            tailf:info
              "Validation of source address";
            leaf reachable-via {
              tailf:info
                "Specify reachability check to apply to the source address";
              type enumeration {
                enum "any" {
                  tailf:info
                    "Source is reachable via any interface";
                }
                enum "rx" {
                  tailf:info
                    "Source is reachable via interface on which packet was received";
                }
              }
            }
          }
          container reverse-path {
            tailf:info
              "Reverse path validation of source address (old command format)";
            tailf:cli-delete-when-empty;
            presence "true";
            leaf access-list {
              tailf:cli-drop-node-name;
              type string {
                tailf:info
                  "WORD;;Access-list name";
              }
            }
          }
        }
      }
      container dhcp {
        tailf:info
          "IPv6 DHCP interface subcommands";
        container relay {
          tailf:info
            "Act as an IPv6 DHCP relay agent";
          list destination {
            tailf:info
              "Configure relay destination";
            tailf:cli-suppress-mode;
            tailf:cli-delete-when-empty;
            tailf:cli-compact-syntax;
            tailf:cli-sequence-commands {
              tailf:cli-reset-siblings;
            }
            key "ipv6-address";
            leaf ipv6-address {
              type inet:ipv6-address {
                tailf:info
                  "X:X:X:X::X;;IPv6 address";
              }
            }
            leaf source-address {
              tailf:info
                "Configure source address to use for relay-forward";
              type inet:ipv6-address {
                tailf:info
                  "X:X:X:X::X;;IPv6 src address";
              }
            }
            leaf link-address {
              tailf:info
                "Configure link-address to use for relay-forward";
              type inet:ipv6-address {
                tailf:info
                  "X:X:X:X::X;;IPv6 link address";
              }
            }
          }
          container source-interface {
            tailf:info
              "Set source interface for relayed messages";
            uses interface-name-grouping;
          }
        }
        container client {
          tailf:info
            "Act as an IPv6 DHCP client";
          container information {
            tailf:info
              "Configure information refresh option";
            container refresh {
              tailf:info
                "Configure information refresh parameters";
              leaf minimum {
                tailf:info
                  "Minimum information refresh time";
                type uint16 {
                  tailf:info
                    "<60-3600>;;Seconds";
                  range "60..3600";
                }
              }
            }
          }
        }
      }
      container nhrp {
        tailf:info
          "NHRP interface subcommands";
        container map {
          tailf:info
            "Map dest IPv6 address to NBMA address";
          list map-list {
            tailf:cli-drop-node-name;
            tailf:cli-suppress-mode;
            tailf:cli-delete-when-empty;
            tailf:cli-incomplete-command;
            key "ipv6-address";
            leaf ipv6-address {
              tailf:cli-drop-node-name;
              type ipv6-prefix {
                tailf:info
                  "X:X:X:X::X/<0-128>;;IPv6 address/mask of destination";
              }
            }
            leaf nbma-address {
              tailf:cli-drop-node-name;
              type union {
                type inet:ipv4-address {
                  tailf:info
                    "A.B.C.D;;IP NBMA address";
                }
                type inet:ipv6-address {
                  tailf:info
                    "X:X:X:X::X;;IPv6 NBMA address";
                }
              }
            }
          }
          container multicast {
            tailf:info
              "Use this NBMA mapping for broadcasts/multicasts";
            leaf dynamic {
              tailf:info
                "Dynamically learn destinations from client registrations on hub";
              type empty;
            }
            list multicast-list {
              tailf:cli-drop-node-name;
              tailf:cli-suppress-mode;
              tailf:cli-delete-when-empty;
              key "nbma-address";
              leaf nbma-address {
                type union {
                  type inet:ipv4-address {
                    tailf:info
                      "A.B.C.D;;IP NBMA address";
                  }
                  type inet:ipv6-address {
                    tailf:info
                      "X:X:X:X::X;;IPv6 NBMA address";
                  }
                }
              }
            }
          }
        }
        leaf network-id {
          tailf:info
            "NBMA network identifier";
          type uint32 {
            tailf:info
              "<1-4294967295>;;Network identifier";
            range "1..4294967295";
          }
        }
        leaf holdtime {
          tailf:info
            "Advertised holdtime";
          type uint16 {
            tailf:info
              "<1-65535>;;Number of seconds";
            range "1..65535";
          }
        }
        container nhs {
          tailf:info
            "Specify a next hop server";
          list nhs-list {
            tailf:cli-drop-node-name;
            tailf:cli-suppress-mode;
            tailf:cli-delete-when-empty;
            tailf:cli-compact-syntax;
            key "nhs-address";
            leaf nhs-address {
              type inet:ipv6-address {
                tailf:info
                  "X:X:X:X::X;;Protocol IPv6 address of NHS";
              }
            }
            leaf nbma {
              tailf:info
                "NBMA of NHS";
              type union {
                type inet:ipv4-address {
                  tailf:info
                    "A.B.C.D;;IPv4 address";
                }
                type inet:ipv6-address {
                  tailf:info
                    "X:X:X:X::X;;IPv6 address";
                }
                type string {
                  tailf:info
                    "WORD;;NHS FQDN string";
                }
              }
            }
            leaf multicast {
              when "../nbma" {
                tailf:xpath-root 3;
                tailf:dependency "../nbma";
              }
              tailf:info
                "Use this NBMA mapping for broadcasts/multicasts";
              type empty;
            }
          }
        }
        container server-only {
          tailf:info
            "Disable NHRP requests";
          tailf:cli-reset-container;
          tailf:cli-delete-when-empty;
          presence "true";
          leaf non-caching {
            tailf:info
              "Do not create NHRP cache entries";
            type empty;
          }
        }
        container registration {
          tailf:info
            "Settings for registration packets.";
          leaf no-unique {
            tailf:info
              "Do not set the 'Unique' flag in registration requests.";
            type empty;
          }
          leaf timeout {
            tailf:info
              "Time between periodic Registration messages";
            type uint16 {
              tailf:info
                "<1-65535>;;Number of seconds";
              range "1..65535";
            }
          }
        }
        container shortcut {
          tailf:info
            "Enable shortcut switching";
          presence "true";
        }
        container redirect {
          tailf:info
            "Enable NHRP redirect traffic indication";
          tailf:cli-delete-when-empty;
          presence "true";
          leaf timeout {
            tailf:info
              "Specify interval over which to throttle";
            type uint8 {
              tailf:info
                "<2-30>;;Interval in seconds";
              range "2..30";
            }
          }
        }
      }
      container summary-address {
        tailf:info
          "Perform address summarization";
        tailf:cli-diff-dependency "/ios:ipv6/unicast-routing" {
          tailf:xpath-root 3;
        }
        list eigrp {
          tailf:info
            "Enhanced Interior Gateway Routing Protocol (EIGRP)";
          tailf:cli-delete-when-empty;
          tailf:cli-suppress-mode;
          key "as-no ipv6-address";
          leaf as-no {
            type uint16 {
              tailf:info
                "<1-65535>;;Autonomous system number";
              range "1..65535";
            }
          }
          leaf ipv6-address {
            type ios:ipv6-prefix {
              tailf:info
                "X:X:X:X::X/<0-128>;;IPv6 prefix";
            }
          }
          leaf distance {
            tailf:cli-drop-node-name;
            type uint8 {
              tailf:info
                "<0-255>;;Administrative distance";
              range "0..255";
            }
          }
        }
      }
      list rip {
        tailf:info
          "Configure RIP routing protocol";
        tailf:cli-suppress-mode;
        tailf:cli-delete-when-empty;
        tailf:cli-incomplete-command;
        key "id";
        leaf id {
          type string {
            tailf:info
              "WORD;;User selected string identifying this RIP process";
          }
        }
        leaf enable {
          tailf:info
            "Enable/disable RIP routing";
          type empty;
        }
        container default-information {
          tailf:info
            "Configure handling of default route";
          tailf:cli-compact-syntax;
          tailf:cli-sequence-commands;
          leaf default-route {
            tailf:cli-drop-node-name;
            tailf:cli-reset-container;
            type enumeration {
              enum "only" {
                tailf:info
                  "Advertise only the default route";
              }
              enum "originate" {
                tailf:info
                  "Originate the default route";
              }
            }
          }
          leaf metric {
            tailf:info
              "Default route metric";
            type uint8 {
              tailf:info
                "<1-15>;;Metric value";
              range "1..15";
            }
          }
        }
      }
      container wccp {
        tailf:info
          "WCCP IPv4 interface commands";
        tailf:cli-diff-dependency "/ios:ipv6/wccp" {
          tailf:xpath-root 3;
        }
        uses interface-ip-wccp-grouping;
        list vrf {
          tailf:info
            "Configure WCCP for a VRF";
          tailf:cli-suppress-mode;
          tailf:cli-delete-when-empty;
          tailf:cli-compact-syntax;
          tailf:cli-incomplete-command;
          key "name";
          leaf name {
            tailf:cli-diff-dependency "/ios:vrf/definition" {
              tailf:xpath-root 3;
            }
            type string {
              tailf:info
                "WORD;;VRF name";
            }
          }
          uses interface-ip-wccp-grouping;
        }
      }
      container policy {
        tailf:info
          "Enable IPv6 policy routing";
        leaf route-map {
          tailf:info
            "IPv6 policy-based-routing routemap";
          type string {
            tailf:info
              "WORD;;Route-map name";
          }
        }
      }
    }
    container ospfv3 {
      tailf:info
        "OSPFv3 interface commands";
      tailf:cli-diff-dependency "/ios:ipv6/unicast-routing" {
        tailf:xpath-root 3;
      }
      uses interface-ospfv3-grouping;
      list ospfv3-list {
        tailf:cli-drop-node-name;
        tailf:cli-suppress-mode;
        tailf:cli-delete-when-empty;
        tailf:cli-incomplete-command;
        key "id";
        leaf id {
          tailf:cli-suppress-range;
          type uint16 {
            tailf:info
              "<1-65535>;;Process ID";
            range "1..65535";
          }
        }
        uses interface-ospfv3-grouping;
        container ipv4 {
          tailf:info
            "Specify parameters for IPv4";
          uses interface-ospfv3-grouping;
        }
        container ipv6 {
          tailf:info
            "Specify parameters for IPv6";
          uses interface-ospfv3-grouping;
        }
      }
    }
    container nhrp {
      tailf:info
        "NHRP Interface commands";
      leaf group {
        tailf:info
          "NHRP group name";
        tailf:cli-full-command;
        type string {
          tailf:info
            "WORD;;group name string";
        }
      }
      leaf route-watch {
        tailf:cli-boolean-no;
        tailf:cli-full-command;
        tailf:cli-diff-dependency "../../ip/nhrp" {
          tailf:xpath-root 3;
        }
        type boolean;
        default "true";
      }
    }
    container if-state {
      tailf:info
        "Allow applications to control interface state";
      leaf nhrp {
        tailf:info
          "Allow NHRP to control interface state";
        type empty;
      }
    }
    leaf delay {
      tailf:info
        "Specify interface throughput delay";
      type uint32 {
        tailf:info
          "<1-16777215>;;Throughput delay (tens of microseconds)";
      }
    }
    leaf load-interval {
      tailf:info
        "Specify interval for load calculation for an interface";
      type uint16 {
        tailf:info
          "<30-600>;;Load interval delay in seconds";
        range "0..600";
      }
    }
    container logging {
      tailf:info
        "Configure logging for interface";
      container event {
        tailf:info
          "Interface events";
        leaf link-status {
          tailf:info
            "UPDOWN and CHANGE messages";
          tailf:cli-boolean-no;
          type boolean;
          default "true";
        }
        leaf trunk-status {
          tailf:info
            "TRUNK status messages";
          tailf:cli-full-command;
          type empty;
        }
        leaf bundle-status {
          tailf:info
            "BUNDLE/UNBUNDLE messages";
          tailf:cli-full-command;
          type empty;
        }
        leaf subif-link-status {
          tailf:info
            "Sub-interface UPDOWN and CHANGE messages";
          tailf:cli-full-command;
          type empty;
        }
        container spanning-tree {
          tailf:info
            "Spanning-tree Interface events";
          leaf status {
            tailf:info
              "Spanning-tree state change messages";
            type empty;
          }
        }
        leaf nfas-status {
          tailf:info
            "NFAS D-channel status messages";
          tailf:cli-full-command;
          type empty;
        }
      }
    }
    leaf max-reserved-bandwidth {
      tailf:info
        "Maximum Reservable Bandwidth on an Interface";
      tailf:cli-full-command;
      type uint8 {
        tailf:info
          "<1-100>;;Max. reservable bandwidth as percent of interface bandwidth";
        range "1..100";
      }
    }
    container mls {
      tailf:info
        "mls sub/interface commands";
      container netflow {
        tailf:info
          "netflow command keyword";
        leaf sampling {
          tailf:info
            "sampling keyword";
          type empty;
        }
      }
      container qos {
        tailf:info
          "qos command keyword";
        container cos {
          tailf:info
            "Configure interface COS parameters";
          leaf cos-value {
            tailf:cli-drop-node-name;
            type uint8 {
              tailf:info
                "<0-7>;;Class of service value between 0 and 7";
              range "0..7";
            }
          }
          leaf override {
            tailf:info
              "Force default COS on all packets";
            type empty;
          }
        }
        leaf channel-consistency {
          tailf:info
            "enable or disable qos consistency checks";
          tailf:cli-boolean-no;
          tailf:cli-full-command;
          type boolean;
          default "true";
        }
        container trust {
          tailf:info
            "Configure trust state of interface";
          container device {
            tailf:info
              "trusted device class";
            leaf cisco-phone {
              tailf:info
                "Cisco IP Phone";
              type empty;
            }
          }
          choice trust-choice {
            container cos {
              tailf:info
                "Classify by packet COS";
              tailf:cli-reset-container;
              tailf:cli-delete-when-empty;
              tailf:cli-diff-dependency "../../vlan-based" {
                tailf:xpath-root 3;
                tailf:cli-trigger-on-set;
              }
              presence "true";
              container pass-through {
                tailf:info
                  "cos pass-through mode";
                leaf dscp {
                  tailf:info
                    "transmit without dscp modification";
                  type empty;
                }
              }
            }
            container dscp {
              tailf:info
                "Classify by packet DSCP";
              tailf:cli-diff-dependency "../../vlan-based" {
                tailf:xpath-root 3;
                tailf:cli-trigger-on-set;
              }
              presence "true";
              container pass-through {
                tailf:info
                  "dscp pass-through mode";
                leaf cos {
                  tailf:info
                    "transmit without cos modification";
                  type empty;
                }
              }
            }
            container ip-precedence {
              tailf:info
                "Classify by packet IP precedence";
              tailf:cli-diff-dependency "../../vlan-based" {
                tailf:xpath-root 3;
                tailf:cli-trigger-on-set;
              }
              presence "true";
            }
          }
        }
        container monitor {
          tailf:info
            "Collect QoS statistics";
          leaf-list dscp {
            tailf:info
              "Collect DSCP statistics";
            tailf:cli-flat-list-syntax;
            tailf:meta-data "max-values" {
              tailf:meta-value "4 :: 8";
            }
            max-elements 15;
            type uint8 {
              tailf:info
                "<0-63>;;dscp (up to 15 values total)";
              range "0..63";
            }
          }
        }
        leaf vlan-based {
          tailf:info
            "vlan-based keyword";
          tailf:cli-full-command;
          tailf:cli-diff-dependency "../../../service-policy/input" {
            tailf:xpath-root 3;
            tailf:cli-trigger-on-set;
          }
          tailf:cli-diff-dependency "../../../service-policy/output" {
            tailf:xpath-root 3;
            tailf:cli-trigger-on-set;
          }
          type empty;
        }
        leaf bridged {
          tailf:info
            "bridged keyword";
          tailf:cli-full-command;
          type empty;
        }
      }
    }
    container auto {
      tailf:info
        "Configure Automation";
      container qos {
        tailf:info
          "Configure AutoQoS";
        container voip {
          tailf:info
            "Configure AutoQoS for VoIP";
          leaf cisco-phone {
            tailf:info
              "Trust the QoS marking of Cisco IP Phone";
            type empty;
          }
          leaf trust {
            tailf:info
              "Trust the COS marking";
            type empty;
          }
        }
      }
    }
    leaf mtu {
      tailf:info
        "Set the interface Maximum Transmission Unit (MTU)";
      tailf:cli-full-command;
      type uint16 {
        tailf:info
          "<64-18000>;;MTU size in bytes";
        range "64..18000";
      }
    }
    container ntp {
      tailf:info
        "Configure NTP";
      container broadcast {
        tailf:info
          "Configure NTP broadcast service";
        presence "true";
        container client {
          tailf:info
            "Listen to NTP broadcasts";
          tailf:cli-full-command;
          presence "true";
        }
        list destination {
          tailf:info
            "Configure broadcast destination address";
          tailf:cli-suppress-mode;
          tailf:cli-delete-when-empty;
          tailf:cli-compact-syntax;
          tailf:cli-reset-container;
          key "address";
          leaf version {
            tailf:info
              "Configure NTP version";
            type uint8 {
              tailf:info
                "<1-4>;;NTP version number";
              range "1..4";
            }
          }
          leaf key {
            tailf:info
              "Configure broadcast authentication key";
            type uint32 {
              tailf:info
                "<0-4294967295>;;Broadcast key number";
            }
          }
          leaf address {
            type inet:ipv4-address {
              tailf:info
                "A.B.C.D;;Destination broadcast IP address";
            }
          }
        }
        container version-key {
          tailf:cli-drop-node-name;
          tailf:cli-compact-syntax;
          tailf:cli-reset-container;
          leaf version {
            tailf:info
              "Configure NTP version";
            type uint8 {
              tailf:info
                "<1-4>;;NTP version number";
              range "1..4";
            }
          }
          leaf key {
            tailf:info
              "Configure broadcast authentication key";
            type uint32 {
              tailf:info
                "<0-4294967295>;;Broadcast key number";
            }
          }
        }
      }
      leaf disable {
        tailf:info
          "Disable NTP traffic (both IP and IPv6)";
        tailf:cli-full-command;
        type empty;
      }
      container multicast {
        tailf:info
          "Configure NTP multicast service";
        tailf:cli-display-separated;
        tailf:cli-compact-syntax;
        presence "true";
        list address-list {
          tailf:cli-drop-node-name;
          tailf:cli-suppress-mode;
          tailf:cli-delete-when-empty;
          tailf:cli-compact-syntax;
          key "group-address";
          leaf group-address {
            type union {
              type inet:ipv4-address {
                tailf:info
                  "A.B.C.D;;Multicast group IP address";
              }
              type inet:ipv6-address {
                tailf:info
                  "X:X:X:X::X;;Multicast group IPv6 address";
              }
            }
          }
          leaf version {
            tailf:info
              "Configure NTP version";
            type uint8 {
              tailf:info
                "<1-4>;;NTP version number";
              range "1..4";
            }
          }
          leaf key {
            tailf:info
              "Configure multicast authentication key";
            type uint32 {
              tailf:info
                "<0-4294967295>;;Multicast key number";
            }
          }
          leaf ttl {
            tailf:info
              "TTL of the multicast packet";
            type uint8 {
              tailf:info
                "<1-255>;;TTL";
              range "1..255";
            }
          }
        }
        leaf version {
          tailf:info
            "Configure NTP version";
          type uint8 {
            tailf:info
              "<1-4>;;NTP version number";
            range "1..4";
          }
        }
        leaf key {
          tailf:info
            "Configure multicast authentication key";
          type uint32 {
            tailf:info
              "<0-4294967295>;;Multicast key number";
          }
        }
        leaf ttl {
          tailf:info
            "TTL of the multicast packet";
          type uint8 {
            tailf:info
              "<1-255>;;TTL";
            range "1..255";
          }
        }
        container client-list {
          tailf:cli-drop-node-name;
          leaf-list client {
            tailf:info
              "Listen to NTP multicasts";
            tailf:cli-list-syntax;
            tailf:cli-suppress-list-no;
            tailf:cli-incomplete-no;
            type union {
              type inet:ipv4-address {
                tailf:info
                  "A.B.C.D;;Multicast client IP address";
              }
              type inet:ipv6-address {
                tailf:info
                  "X:X:X:X::X;;Multicast client IPv6 address";
              }
            }
          }
        }
        leaf client {
          tailf:info
            "Listen to NTP multicasts";
          tailf:cli-full-command;
          type empty;
        }
      }
    }
    container power {
      tailf:info
        "Power configuration";
      container inline {
        tailf:info
          "Inline power configuration";
        tailf:cli-compact-syntax;
        tailf:cli-sequence-commands {
          tailf:cli-reset-siblings;
        }
        leaf consumption {
          tailf:info
            "Configure the inline device consumption";
          tailf:cli-optional-in-sequence;
          tailf:cli-full-command;
          type uint16 {
            tailf:info
              "<4000-15400>;;milli-watts";
            range "4000..15400";
          }
        }
        leaf mode {
          tailf:cli-drop-node-name;
          type enumeration {
            enum "auto" {
              tailf:info
                "Automatically detect and power inline devices";
            }
            enum "never" {
              tailf:info
                "Never apply inline power";
            }
            enum "static" {
              tailf:info
                "High priority inline power interface";
            }
          }
          default "auto";
        }
        leaf max {
          tailf:info
            "Maximum power allowed on this interface";
          when "../mode != 'never'" {
            tailf:xpath-root 3;
            tailf:dependency "../mode";
          }
          type uint16 {
            tailf:info
              "<4000-15400>;;milli-watts";
            range "4000..15400";
          }
        }
      }
      container client {
        tailf:info
          "Client radio requested maximum transmitter power level";
        leaf local {
          tailf:info
            "Set power to Access Point local power";
          type empty;
        }
      }
    }
    list rate-limit {
      tailf:info
        "Rate Limit";
      tailf:cli-suppress-mode;
      tailf:cli-delete-when-empty;
      tailf:cli-compact-syntax;
      key "dir bps bc be conform-action exceed-action";
      leaf dir {
        type enumeration {
          enum "input" {
            tailf:info
              "Rate limit on input";
          }
          enum "output" {
            tailf:info
              "Rate limit on output";
          }
        }
      }
      leaf dscp {
        tailf:info
          "Match dscp value";
        type uint8 {
          tailf:info
            "<0-63>;;dscp";
          range "0..63";
        }
      }
      leaf bps {
        tailf:info
          "<8000-2000000000>;;Bits per second";
        type police-bps-type;
      }
      leaf bc {
        type uint32 {
          tailf:info
            "<1000-512000000>;;Normal burst bytes";
          range "1000..512000000";
        }
      }
      leaf be {
        type uint32 {
          tailf:info
            "<2000-1024000000>;;Maximum burst bytes";
          range "2000..1024000000";
        }
      }
      leaf conform-action {
        tailf:cli-expose-key-name;
        type enumeration {
          enum "transmit";
        }
      }
      leaf exceed-action {
        tailf:cli-expose-key-name;
        type enumeration {
          enum "drop";
        }
      }
    }
    container service-policy {
      tailf:info
        "Configure QoS Service Policy";
      leaf history {
        tailf:cli-full-command;
        tailf:info
          "Keep history of QoS metrics";
        type empty;
      }
      uses service-policy-grouping;
      container type {
        tailf:info
          "Configure CPL Service Policy";
        container control {
          tailf:info
            "Apply a control policy to the interface";
          leaf subscriber {
            tailf:info
              "Apply a subscriber control policy to the interfac";
            tailf:non-strict-leafref {
              path "/ncs:devices/ncs:device/ncs:config/ios:policy-map-event-control/policy-map/name" {
                tailf:xpath-root 3;
              }
            }
            type string {
              tailf:info
                "WORD;;policy-map name";
            }
          }
        }
        container performance-monitor {
          tailf:info
            "Configure media monitor service-policy type";
          uses service-policy-grouping;
        }
      }
    }
    container service-insertion {
      tailf:info
        "Service-insertion AppNav Controller";
      leaf waas {
        tailf:info
          "Enable Service-insertion";
        type empty;
      }
    }
    container service-module {
      tailf:info
        "Configure service module";
      container t1 {
        tailf:info
          "Configure Serial T1 parameters";
        tailf:cli-compact-syntax;
        tailf:cli-sequence-commands;
        leaf-list timeslots {
          tailf:info
            "List of timeslots in the T1 group";
          tailf:cli-range-list-syntax;
          tailf:cli-replace-all;
          type uint8 {
            tailf:info
              "<1-24>;List of timeslots";
            range "1..24";
          }
        }
        leaf speed {
          type enumeration {
            enum "56";
            enum "64";
          }
        }
      }
    }
    leaf group {
      tailf:info
        "Add this subinterface to a group";
      tailf:cli-full-command;
      tailf:cli-diff-dependency "/ios:service-group" {
        tailf:xpath-root 3;
      }
      type uint16 {
        tailf:info
          "<1-65532>;;Group number";
        range "1..65532";
      }
    }
    leaf shutdown {
      tailf:info
        "Shutdown the selected interface";
      tailf:cli-show-no;
      tailf:cli-full-command;
      type empty;
    }
    container standby {
      tailf:info
        "HSRP interface configuration commands";
      leaf version {
        tailf:info
          "HSRP version";
        tailf:cli-full-command;
        type enumeration {
          tailf:info
            "<1-2>;;Version number";
          enum "1";
          enum "2";
        }
      }
      leaf bfd {
        tailf:info
          "Enable HSRP BFD";
        tailf:cli-boolean-no;
        tailf:cli-full-command;
        type boolean;
        default "true";
      }
      container delay {
        tailf:info
          "HSRP initialisation delay";
        tailf:cli-compact-syntax;
        leaf minimum {
          tailf:info
            "Minimum delay";
          type uint16 {
            tailf:info
              "<0-10000>;;Delay in seconds";
            range "0..10000";
          }
        }
        leaf reload {
          tailf:info
            "Delay after reload";
          type uint16 {
            tailf:info
              "<0-10000>;;Delay in seconds";
            range "0..10000";
          }
        }
      }
      leaf mac-refresh {
        tailf:info
          "Refresh MAC cache on switch by periodically sending packet from virtual mac address";
        type uint8 {
          tailf:info
            "<0-255>;;Interval to refresh MAC cache";
          range "0..255";
        }
      }
      container use-bia {
        tailf:info
          "HSRP uses interface's burned in address";
        presence "true";
        container scope {
          tailf:info
            "Specify the scope of use-bia";
          leaf interface {
            tailf:info
              "Use-bia applies to all groups on this interface or sub-interface";
            type empty;
          }
        }
      }
      list standby-list {
        tailf:cli-drop-node-name;
        tailf:cli-suppress-mode;
        tailf:cli-delete-when-empty;
        tailf:cli-incomplete-command;
        tailf:cli-diff-dependency "../version" {
          tailf:xpath-root 3;
        }
        key "group-number";
        leaf group-number {
          tailf:key-default "0";
          tailf:cli-suppress-range;
          type uint16 {
            tailf:info
              "<0-4095>;;group number";
          }
        }
        container authentication {
          tailf:info
            "Authentication";
          choice auth {
            leaf word {
              tailf:cli-drop-node-name;
              tailf:cli-disallow-value "md5|text";
              type string {
                tailf:info
                  "WORD;;Plain text authentication string (8 chars max)";
              }
            }
            container md5 {
              tailf:info
                "Use MD5 authentication";
              leaf key-chain {
                tailf:info
                  "Set key chain";
                type string {
                  tailf:info
                    "WORD;;Name of key-chain";
                }
              }
              container key-string {
                tailf:info
                  "Set key string";
                tailf:cli-flatten-container;
                tailf:cli-compact-syntax;
                tailf:cli-sequence-commands;
                uses password-grouping;
                leaf timeout {
                  tailf:info
                    "Set timeout";
                  type uint16 {
                    tailf:info
                      "<0-32767>;;Timeout until only accepting new key (seconds)";
                    range "0..32767";
                  }
                }
              }
            }
            leaf text {
              tailf:info
                "Plain text authentication";
              type string {
                tailf:info
                  "WORD;;Plain text authentication string (8 chars max)";
              }
            }
          }
        }
        leaf follow {
          tailf:info
            "Name of HSRP group to follow";
          type string {
            tailf:info
              "WORD;;name string (25 chars. max)";
          }
        }
        container ip {
          tailf:info
            "Enable HSRP and set the virtual IP address";
          tailf:cli-compact-syntax;
          tailf:cli-sequence-commands;
          tailf:cli-delete-when-empty;
          presence "true";
          leaf address {
            tailf:cli-drop-node-name;
            tailf:cli-diff-dependency "../../../../ip-vrf/ip/vrf/forwarding" {
              tailf:xpath-root 3;
              tailf:cli-trigger-on-set;
            }
            type inet:ipv4-address {
              tailf:info
                "A.B.C.D;;Virtual IP address";
            }
          }
          leaf secondary {
            tailf:info
              "Make this IP address a secondary virtual IP address";
            type empty;
          }
        }
        leaf ipv6 {
          tailf:info
            "Enable HSRP IPv6";
          type union {
            type inet:ipv6-address {
              tailf:info
                "X:X:X:X::X;;IPv6 link-local address";
            }
            type ios:ipv6-prefix;
            type enumeration {
              enum "autoconfig" {
                tailf:info
                  "Obtain address using autoconfiguration";
              }
            }
          }
        }
        leaf mac-address {
          tailf:info
            "Virtual MAC address";
          type string {
            tailf:info
              "H.H.H;;MAC address";
          }
        }
        leaf name {
          tailf:info
            "Redundancy name string";
          tailf:cli-full-command;
          type string {
            tailf:info
              "WORD;;name string";
          }
        }
        container redirect {
          tailf:info
            "Configure sending of ICMP Redirect messages with an HSRP virtual IP address as the gateway IP address";
          container advertisement {
            tailf:info
              "Redirect advertisement messages";
            container authentication {
              tailf:info
                "Authentication";
              container md5 {
                tailf:info
                  "Use MD5 authentication";
                leaf key-chain {
                  tailf:info
                    "Set key chain";
                  type string {
                    tailf:info
                      "WORD;;Name of key-chain";
                  }
                }
                container key-string {
                  tailf:info
                    "Set key string";
                  tailf:cli-flatten-container;
                  tailf:cli-compact-syntax;
                  tailf:cli-sequence-commands;
                  uses password-grouping;
                  leaf timeout {
                    tailf:info
                      "Set timeout";
                    type uint16 {
                      tailf:info
                        "<0-32767>;;Timeout until only accepting new key (seconds)";
                      range "0..32767";
                    }
                  }
                }
              }
            }
          }
          container timers {
            tailf:info
              "Adjust redirect timers";
            tailf:cli-compact-syntax;
            tailf:cli-sequence-commands {
              tailf:cli-reset-siblings;
            }
            leaf advertisement {
              tailf:cli-drop-node-name;
              type uint16 {
                tailf:info
                  "<10-180>;;Passive router advertisement interval in seconds";
                range "10..180";
              }
            }
            leaf holddown {
              tailf:cli-drop-node-name;
              type uint16 {
                tailf:info
                  "<30-3600>;;Passive router holddown interval in seconds";
                range "30..3600";
              }
            }
          }
          leaf unknown {
            tailf:info
              "Redirect to non-HSRP routers";
            type empty;
          }
        }
        container timers {
          tailf:info
            "Hello and hold timers";
          tailf:cli-compact-syntax;
          tailf:cli-sequence-commands {
            tailf:cli-reset-siblings;
          }
          container hello-interval {
            tailf:cli-drop-node-name;
            tailf:cli-flatten-container;
            tailf:cli-compact-syntax;
            choice hello-interval-choice {
              leaf seconds {
                tailf:cli-drop-node-name;
                tailf:cli-incomplete-command;
                type uint8 {
                  tailf:info
                    "<1-254>;;Hello interval in seconds";
                  range "1..254";
                }
              }
              leaf msec {
                tailf:info
                  "Specify hello interval in milliseconds";
                tailf:cli-incomplete-command;
                type uint16 {
                  tailf:info
                    "<15-999>;;Hello interval in milliseconds";
                  range "15..999";
                }
              }
            }
          }
          container hold-time {
            tailf:cli-drop-node-name;
            tailf:cli-flatten-container;
            tailf:cli-compact-syntax;
            choice hold-time-choice {
              leaf seconds {
                tailf:cli-drop-node-name;
                type uint8 {
                  tailf:info
                    "<1-255>;;Hold time in seconds";
                  range "1..255";
                }
              }
              leaf msec {
                tailf:info
                  "Specify hold time in milliseconds";
                type uint16 {
                  tailf:info
                    "<50-3000>;;Hello interval in milliseconds";
                  range "50..3000";
                }
              }
            }
          }
        }
        leaf priority {
          tailf:info
            "Priority level";
          tailf:cli-full-command;
          type uint8 {
            tailf:info
              "<0-255>;;Priority value";
          }
        }
        container preempt {
          tailf:info
            "Overthrow lower priority Active routers";
          tailf:cli-compact-syntax;
          tailf:meta-data "trim-delete-when-empty" {
            tailf:meta-value "( preempt)";
          }
          tailf:ned-data "." {
            tailf:xpath-root 3;
            tailf:transaction to;
          }
          presence "true";
          container delay {
            tailf:info
              "Wait before preempting";
            tailf:cli-compact-syntax;
            leaf minimum {
              tailf:info
                "Delay at least this long";
              type uint16 {
                tailf:info
                  "<0-3600>;;Number of seconds for minimum delay";
                range "0..3600";
              }
            }
            leaf reload {
              tailf:info
                "Delay after reload";
              type uint16 {
                tailf:info
                  "<0-3600>;;Number of seconds for reload delay";
                range "0..3600";
              }
            }
            leaf sync {
              tailf:info
                "Wait for IP redundancy client";
              type uint16 {
                tailf:info
                  "<0-3600>;;Number of seconds for sync delay";
                range "0..3600";
              }
            }
          }
        }
        list track {
          tailf:info
            "Priority tracking";
          tailf:cli-suppress-mode;
          tailf:cli-delete-when-empty;
          tailf:cli-incomplete-command;
          tailf:cli-compact-syntax;
          key "name";
          leaf name {
            tailf:cli-suppress-range;
            type union {
              type uint16 {
                tailf:info
                  "<0-1000>;;Tracked object number";
              }
              type string {
                tailf:info
                  "WORD;;Interface name";
              }
            }
          }
          choice options {
            case interface {
              leaf priority-decrement {
                tailf:cli-drop-node-name;
                type uint16 {
                  tailf:info
                    "<1-255>;;Decrement value";
                }
              }
            }
            case group-number {
              leaf decrement {
                tailf:info
                  "Priority decrement";
                tailf:cli-full-command;
                type uint16 {
                  tailf:info
                    "<1-255>;;Decrement value";
                }
              }
              leaf shutdown {
                tailf:info
                  "Shutdown group";
                tailf:cli-full-command;
                type empty;
              }
            }
          }
        }
      }
    }
    container storm-control {
      tailf:info
        "storm configuration";
      container action {
        tailf:info
          "Action to take for storm-control";
        leaf shutdown {
          tailf:info
            "Shutdown this interface if a storm occurs";
          tailf:cli-full-command;
          type empty;
        }
        leaf trap {
          tailf:info
            "Send SNMP trap if a storm occurs";
          tailf:cli-full-command;
          type empty;
        }
        leaf level {
          tailf:info
            "Set storm suppression level on this interface";
          tailf:cli-full-command;
          type decimal64 {
            fraction-digits 2;
            tailf:info
              "<0-100>;;Enter Integer part of level as percentage of bandwidth";
            range "0..100";
          }
        }
      }
      container broadcast {
        tailf:info
          "Broadcast address storm control";
        leaf level {
          tailf:info
            "Set storm suppression level on this interface";
          type decimal64 {
            fraction-digits 2;
            tailf:info
              "<0-100>;;Enter Integer part of level as percentage of bandwidth";
            range "0..100";
          }
        }
        uses storm-control-level-bps-pps-grouping;
        container include {
          tailf:info
            "include other traffic types";
          leaf multicast {
            tailf:info
              "Suppress broadcast and multicast traffic";
            type empty;
          }
        }
      }
      container multicast {
        tailf:info
          "Multicast address storm control";
        leaf level {
          tailf:info
            "Set storm suppression level on this interface";
          type decimal64 {
            fraction-digits 2;
            tailf:info
              "<0-100>;;Enter Integer part of level as percentage of bandwidth";
            range "0..100";
          }
        }
        uses storm-control-level-bps-pps-grouping;
      }
      container unicast {
        tailf:info
          "Unicast address storm control";
        leaf level {
          tailf:info
            "Set storm suppression level on this interface";
          type decimal64 {
            fraction-digits 2;
            tailf:info
              "<0-100>;;Enter Integer part of level as percentage of bandwidth";
            range "0..100";
          }
        }
        uses storm-control-level-bps-pps-grouping;
      }
    }
    container wrr-queue {
      tailf:info
        "Configure weighted round-robin xmt queues";
      container bandwidth {
        tailf:info
          "Configure WRR minimum bandwidth with weights or percentages";
        tailf:cli-compact-syntax;
        tailf:cli-sequence-commands {
          tailf:cli-reset-siblings;
        }
        choice bandwidth-choice {
          case a {
            leaf weight-1 {
              tailf:cli-drop-node-name;
              type uint8 {
                tailf:info
                  "<0-255>;;enter bandwidth weight";
                range "0..255";
              }
            }
            leaf weight-2 {
              tailf:cli-drop-node-name;
              type uint8 {
                tailf:info
                  "<0-255>;;enter bandwidth weight";
                range "0..255";
              }
            }
            leaf weight-3 {
              tailf:cli-drop-node-name;
              type uint8 {
                tailf:info
                  "<0-255>;;enter bandwidth weight";
                range "0..255";
              }
            }
            leaf weight-4 {
              tailf:cli-drop-node-name;
              type uint8 {
                tailf:info
                  "<0-255>;;enter bandwidth weight";
                range "0..255";
              }
            }
            leaf weight-5 {
              tailf:cli-drop-node-name;
              type uint8 {
                tailf:info
                  "<0-255>;;enter bandwidth weight";
                range "0..255";
              }
            }
            leaf weight-6 {
              tailf:cli-drop-node-name;
              type uint8 {
                tailf:info
                  "<0-255>;;enter bandwidth weight";
                range "0..255";
              }
            }
            leaf weight-7 {
              tailf:cli-drop-node-name;
              type uint8 {
                tailf:info
                  "<0-255>;;enter bandwidth weight";
                range "0..255";
              }
            }
          }
          case b {
            container percent {
              tailf:cli-compact-syntax;
              tailf:cli-sequence-commands {
                tailf:cli-reset-siblings;
              }
              leaf percent-1 {
                tailf:cli-drop-node-name;
                type uint8 {
                  tailf:info
                    "<0-100>;;enter bandwidth percent";
                  range "0..100";
                }
              }
              leaf percent-2 {
                tailf:cli-drop-node-name;
                type uint8 {
                  tailf:info
                    "<0-100>;;enter bandwidth percent";
                  range "0..100";
                }
              }
              leaf percent-3 {
                tailf:cli-drop-node-name;
                type uint8 {
                  tailf:info
                    "<0-100>;;enter bandwidth percent";
                  range "0..100";
                }
              }
              leaf percent-4 {
                tailf:cli-drop-node-name;
                type uint8 {
                  tailf:info
                    "<0-100>;;enter bandwidth percent";
                  range "0..100";
                }
              }
              leaf percent-5 {
                tailf:cli-drop-node-name;
                type uint8 {
                  tailf:info
                    "<0-100>;;enter bandwidth percent";
                  range "0..100";
                }
              }
              leaf percent-6 {
                tailf:cli-drop-node-name;
                type uint8 {
                  tailf:info
                    "<0-100>;;enter bandwidth percent";
                  range "0..100";
                }
              }
              leaf percent-7 {
                tailf:cli-drop-node-name;
                type uint8 {
                  tailf:info
                    "<0-100>;;enter bandwidth percent";
                  range "0..100";
                }
              }
            }
          }
        }
      }
      list dscp-map {
        tailf:info
          "Configure dscp-map for a queue threshold";
        tailf:cli-suppress-mode;
        tailf:cli-delete-when-empty;
        tailf:cli-compact-syntax;
        key "queue threshold";
        leaf queue {
          type uint8 {
            tailf:info
              "<1-7>;;enter dscp-map queue id";
          }
        }
        leaf threshold {
          type uint8 {
            tailf:info
              "<1-4>;;enter dscp-map threshold id";
          }
        }
        list values {
          tailf:cli-drop-node-name;
          tailf:cli-suppress-mode;
          tailf:cli-delete-when-empty;
          tailf:cli-show-long-obu-diffs;
          ordered-by user;
          key "value";
          leaf value {
            tailf:cli-multi-word-key;
            type string;
          }
        }
      }
      list cos-map {
        tailf:info
          "Configure cos-map for a queue threshold";
        tailf:cli-suppress-mode;
        tailf:cli-delete-when-empty;
        tailf:cli-compact-syntax;
        tailf:cli-sequence-commands {
          tailf:cli-reset-siblings;
        }
        key "queue-id threshold-id";
        leaf queue-id {
          type uint8 {
            tailf:info
              "<1-4>;;enter cos-map queue id";
            range "1..4";
          }
        }
        leaf threshold-id {
          type uint8 {
            tailf:info
              "<1-8>;;enter cos-map threshhold id";
            range "0..8";
          }
        }
        leaf-list cos-values {
          tailf:cli-drop-node-name;
          tailf:cli-flat-list-syntax;
          tailf:meta-data "max-values-copy-meta" {
            tailf:meta-value "4 :: 1";
          }
          tailf:meta-data "default-value" {
            tailf:meta-value "$1 $2<NL> <DEFAULT><NL>exit<NL> :: MAP=WRR-QUEUE-COSMAP";
          }
          max-elements 8;
          type uint8 {
            tailf:info
              "<0-7>;;cos values separated by spaces (up to 8 values total)";
            range "0..7";
          }
        }
      }
      container queue-limit {
        tailf:info
          "Configure queue-limit";
        tailf:cli-compact-syntax;
        tailf:cli-sequence-commands {
          tailf:cli-reset-siblings;
        }
        leaf weight-a {
          tailf:cli-drop-node-name;
          type uint8 {
            tailf:info
              "<0-100>;;enter queue size weight";
            range "0..100";
          }
        }
        leaf weight-b {
          tailf:cli-drop-node-name;
          type uint8 {
            tailf:info
              "<0-100>;;enter queue size weight";
            range "0..100";
          }
        }
        leaf weight-c {
          tailf:cli-drop-node-name;
          type uint8 {
            tailf:info
              "<0-100>;;enter queue size weight";
            range "0..100";
          }
        }
        leaf weight-d {
          tailf:cli-drop-node-name;
          type uint8 {
            tailf:info
              "<0-100>;;enter queue size weight";
            range "0..100";
          }
        }
        leaf weight-e {
          tailf:cli-drop-node-name;
          type uint8 {
            tailf:info
              "<0-100>;;enter queue size weight";
            range "0..100";
          }
        }
        leaf weight-f {
          tailf:cli-drop-node-name;
          type uint8 {
            tailf:info
              "<0-100>;;enter queue size weight";
            range "0..100";
          }
        }
        leaf weight-g {
          tailf:cli-drop-node-name;
          type uint8 {
            tailf:info
              "<0-100>;;enter queue size weight";
            range "0..100";
          }
        }
      }
      container random-detect {
        tailf:info
          "Configure random-detect";
        list max-threshold {
          tailf:info
            "Max threshold for WRED";
          tailf:cli-suppress-mode;
          tailf:cli-delete-when-empty;
          tailf:cli-compact-syntax;
          tailf:cli-sequence-commands {
            tailf:cli-reset-siblings;
          }
          key "id";
          leaf id {
            type uint8 {
              tailf:info
                "<1-3>;;enter queue id";
              range "1..3";
            }
          }
          uses queue-size-grouping;
        }
        list min-threshold {
          tailf:info
            "Min threshold for WRED";
          tailf:cli-suppress-mode;
          tailf:cli-delete-when-empty;
          tailf:cli-compact-syntax;
          tailf:cli-sequence-commands {
            tailf:cli-reset-siblings;
          }
          key "id";
          leaf id {
            type uint8 {
              tailf:info
                "<1-3>;;enter queue id";
              range "1..3";
            }
          }
          uses queue-size-grouping;
        }
      }
      list threshold {
        tailf:info
          "Configure queue tail-drop thresholds";
        tailf:cli-suppress-mode;
        tailf:cli-delete-when-empty;
        tailf:cli-compact-syntax;
        tailf:cli-sequence-commands {
          tailf:cli-reset-siblings;
        }
        key "id";
        leaf id {
          type uint8 {
            tailf:info
              "<1-3>;;enter queue id";
            range "1..3";
          }
        }
        uses queue-size-grouping;
      }
      list min-reserve {
        tailf:info
          "Configure min-reserve level";
        tailf:cli-suppress-mode;
        tailf:cli-delete-when-empty;
        tailf:cli-incomplete-command;
        key "id";
        leaf id {
          type uint8 {
            tailf:info
              "<1-4>;;queue id";
            range "1..4";
          }
        }
        leaf level {
          tailf:cli-drop-node-name;
          type uint8 {
            tailf:info
              "<1-8>;;min-reserve level";
            range "1..8";
          }
        }
      }
    }
    container no-list {
      tailf:info
        "no wrr-queue random-detect entry";
      container wrr-queue {
        tailf:info
          "Configure weighted round-robin xmt queues";
        list random-detect {
          tailf:info
            "Configure random-detect";
          tailf:cli-suppress-mode;
          tailf:cli-delete-when-empty;
          key "id";
          leaf id {
            type uint32;
          }
        }
      }
    }
    container priority-queue {
      tailf:info
        "Configure priority scheduling";
      leaf queue-limit {
        tailf:info
          "configure priority queue limit";
        tailf:cli-full-command;
        type uint8 {
          tailf:info
            "<0-100>;;enter queue size weight";
          range "0..100";
        }
      }
      list dscp-map {
        tailf:info
          "Configure dscp-map for a queue threshold";
        tailf:cli-suppress-mode;
        tailf:cli-delete-when-empty;
        tailf:cli-compact-syntax;
        tailf:cli-incomplete-command;
        key "id";
        leaf id {
          type uint8 {
            tailf:info
              "<1-1>;;enter priority queue id";
            range "1";
          }
        }
        list values {
          tailf:cli-drop-node-name;
          tailf:cli-suppress-mode;
          tailf:cli-delete-when-empty;
          tailf:cli-show-long-obu-diffs;
          ordered-by user;
          key "value";
          leaf value {
            tailf:cli-multi-word-key;
            type string;
          }
        }
      }
      container cos-map {
        tailf:info
          "Configure cos-map for a queue";
        tailf:cli-compact-syntax;
        tailf:cli-sequence-commands;
        leaf id {
          tailf:cli-drop-node-name;
          tailf:cli-incomplete-command;
          type uint8 {
            tailf:info
              "<1-1>;;enter cos-map queue id";
            range "1";
          }
        }
        leaf-list cos-values {
          tailf:cli-drop-node-name;
          tailf:cli-flat-list-syntax;
          tailf:meta-data "default-value" {
            tailf:meta-value "$1 $2<NL> <DEFAULT><NL>exit<NL> :: priority-queue cos-map 1 5";
          }
          max-elements 8;
          type uint8 {
            tailf:info
              "<0-7>;;cos values separated by spaces (up to 8 values total)";
            range "0..7";
          }
        }
      }
      leaf out {
        tailf:info
          "egress priority queue";
        tailf:cli-full-command;
        type empty;
      }
    }
    container rep {
      tailf:info
        "Resilient Ethernet Protocol characteristics";
      container block {
        tailf:info
          "Block port & VLANs for VLAN Load-balancing";
        container port {
          tailf:info
            "Specify port for VLAN Load-balancing";
          tailf:cli-sequence-commands {
            tailf:cli-reset-siblings;
          }
          tailf:cli-compact-syntax;
          choice port-choice {
            leaf neighbor-offset {
              tailf:cli-drop-node-name;
              type int16 {
                tailf:info
                  "<-256 - 256>;;Neighbor offset";
                range "-256..256";
              }
            }
            leaf id {
              tailf:info
                "REP port ID";
              type string {
                tailf:info
                  "WORD;;REP port ID (16 digit hexadecimal number)";
              }
            }
            leaf preferred {
              tailf:info
                "Preferred flag";
              type empty;
            }
          }
          leaf vlan {
            tailf:info
              "VLANs to block";
            type union {
              type string {
                tailf:info
                  "WORD;;VLAN list (1-4094) ex: 1-65,72,300-320";
              }
              type enumeration {
                enum "all" {
                  tailf:info
                    "All VLANs";
                }
              }
            }
          }
        }
      }
      container preempt {
        tailf:info
          "Preemption options";
        leaf delay {
          tailf:info
            "Delay timer in seconds";
          type uint16 {
            tailf:info
              "<15-300>;;number of seconds before automatic preemption takes place";
            range "15..300";
          }
        }
      }
      container segment {
        tailf:info
          "REP segment ID";
        tailf:cli-compact-syntax;
        tailf:cli-sequence-commands {
          tailf:cli-reset-siblings;
        }
        leaf id {
          tailf:cli-drop-node-name;
          type uint16 {
            tailf:info
              "<1-1024>;;Between 1 and 1024";
            range "1..1024";
          }
        }
        leaf edge {
          tailf:info
            "Edge Port";
          tailf:cli-optional-in-sequence;
          type empty;
        }
        leaf no-neighbor {
          tailf:info
            "No-Neighbor Edge Port";
          tailf:cli-optional-in-sequence;
          type empty;
        }
        leaf primary {
          tailf:info
            "Primary Edge Port";
          tailf:cli-optional-in-sequence;
          when "../edge" {
            tailf:xpath-root 3;
            tailf:dependency "../edge";
          }
          type empty;
        }
        leaf preferred {
          tailf:info
            "Preferred Alternate Port";
          type empty;
        }
      }
      container stcn {
        tailf:info
          "Segment Topology Change Notification";
        leaf segment {
          tailf:info
            "for REP segment";
          type string {
            tailf:info
              "WORD;;segment ID list (1-1024) ex: 1-3,6-9";
          }
        }
        leaf stp {
          tailf:info
            "for STP network";
          type empty;
        }
      }
    }
    container rcv-queue {
      tailf:info
        "Configure receive queue(s)";
      list cos-map {
        tailf:info
          "Configure cos-map for a queue threshold";
        tailf:cli-suppress-mode;
        tailf:cli-delete-when-empty;
        tailf:cli-compact-syntax;
        tailf:cli-sequence-commands {
          tailf:cli-reset-siblings;
        }
        key "queue-id threshold-id";
        leaf queue-id {
          type uint8 {
            tailf:info
              "<1-3>;;enter cos-map queue id";
            range "1..3";
          }
        }
        leaf threshold-id {
          type uint8 {
            tailf:info
              "<1-8>;;enter cos-map threshhold id";
            range "1..8";
          }
        }
        leaf-list cos-values {
          tailf:cli-drop-node-name;
          tailf:cli-flat-list-syntax;
          max-elements 8;
          type uint8 {
            tailf:info
              "<0-7>;;cos values separated by spaces (up to 8 values total)";
            range "0..7";
          }
        }
      }
    }
    container udld {
      tailf:info
        "Configure UDLD enabled or disabled and ignore global UDLD setting";
      container port {
        tailf:info
          "Enable UDLD protocol on this interface despite global UDLD setting";
        tailf:cli-delete-when-empty;
        presence "true";
        choice port-choice {
          leaf aggressive {
            tailf:info
              "Enable UDLD protocol in aggressive mode on this interface despite global UDLD setting";
            type empty;
          }
          leaf disable {
            tailf:info
              "Disable UDLD protocol on this interface despite global UDLD setting";
            type empty;
          }
        }
      }
    }
    container peer {
      tailf:info
        "Peer parameters for point to point interfaces";
      leaf neighbor-route {
        tailf:info
          "Create neighbor route to peer if needed";
        tailf:cli-boolean-no;
        tailf:cli-full-command;
        type boolean;
        default "true";
      }
      container default {
        tailf:info
          "Specify default parameters";
        container ip {
          tailf:info
            "Specify default IP parameters";
          container address {
            tailf:info
              "Specify default IP address";
            choice address-choice {
              leaf dhcp {
                tailf:info
                  "Use DHCP proxy client mechanism to allocate a peer IP address";
                type empty;
              }
              container dhcp-pool {
                tailf:info
                  "Use local DHCP pools to allocate a peer IP address";
                presence "true";
                leaf pools {
                  tailf:cli-drop-node-name;
                  tailf:cli-multi-value;
                  type string {
                    tailf:info
                      "LINE;;List of one or more DHCP address pools";
                  }
                }
              }
              container pool {
                tailf:info
                  "Use IP pool mechanism to allocate a peer IP address";
                presence "true";
                leaf pools {
                  tailf:cli-drop-node-name;
                  tailf:cli-multi-value;
                  type string {
                    tailf:info
                      "LINE;;List of one or more DHCP address pools";
                  }
                }
              }
            }
          }
        }
      }
    }
    container clns {
      tailf:info
        "CLNS interface subcommands";
      leaf mtu {
        tailf:info
          "Set MTU packet size for interface";
        type uint32 {
          tailf:info
            "<512-4294967295>;;CLNS MTU packet size for interface";
        }
      }
      container router {
        tailf:info
          "Enable CLNS routing protocol on interface";
        container isis {
          tailf:info
            "ISO IS-IS routing protocol";
          tailf:cli-delete-when-empty;
          presence "true";
          leaf tag {
            tailf:cli-drop-node-name;
            type string {
              tailf:info
                "WORD;;Routing process tag";
            }
          }
        }
      }
      leaf route-cache {
        tailf:info
          "Enable fast switching through the cache";
        tailf:cli-boolean-no;
        tailf:cli-full-command;
        type boolean;
        default "true";
      }
    }
    container dsu {
      leaf bandwidth {
        tailf:cli-full-command;
        type uint32;
      }
      leaf mode {
        tailf:cli-full-command;
        type enumeration {
          enum "1" {
            tailf:info
              "DSU mode 1";
          }
          enum "2" {
            tailf:info
              "DSU mode 2";
          }
        }
      }
    }
    leaf framing {
      tailf:info
        "Framing interface subcommands";
      tailf:cli-full-command;
      type enumeration {
        enum "bypass";
        enum "g751" {
          tailf:info
            "G.751 framing";
        }
        enum "c-bit";
        enum "m13";
      }
    }
    leaf cablelength {
      tailf:cli-full-command;
      type uint32;
    }
    container isdn {
      tailf:info
        "ISDN Interface configuration commands";
      leaf switch-type {
        tailf:info
          "Select the Interface ISDN switch type";
        tailf:cli-full-command;
        type string {
          tailf:info
            "WORD;;Switch type";
        }
      }
      leaf protocol-emulate {
        tailf:info
          "Protocol (L2/L3) emulation network/user side";
        tailf:cli-full-command;
        type enumeration {
          enum "network" {
            tailf:info
              "ISDN protocol emulation network side";
          }
          enum "user" {
            tailf:info
              "ISDN protocol emulation user side (default)";
          }
        }
      }
      container incoming-voice {
        tailf:info
          "Specify options for incoming calls.";
        choice incoming-voice-choice {
          leaf voice {
            tailf:info
              "Incoming voice calls will be handled as voice.";
            type empty;
          }
          container data {
            tailf:info
              "Incoming voice calls will be handled as data.";
            tailf:cli-delete-when-empty;
            presence "true";
            leaf kbps {
              tailf:cli-drop-node-name;
              type enumeration {
                enum "56" {
                  tailf:info
                    "B Channel Bandwidth of 56Kb/s";
                }
                enum "64" {
                  tailf:info
                    "B Channel Bandwidth of 64Kb/s";
                }
              }
            }
          }
          container modem {
            tailf:info
              "Incoming voice calls will be handled as modems.";
            tailf:cli-delete-when-empty;
            presence "true";
            leaf kbps {
              tailf:cli-drop-node-name;
              type enumeration {
                enum "56" {
                  tailf:info
                    "56  B Channel Bandwidth of 56Kb/s  ";
                }
                enum "64" {
                  tailf:info
                    "64  B Channel Bandwidth of 64Kb/s";
                }
              }
            }
          }
        }
      }
      container supp-service {
        tailf:info
          "Specify the subscribed supplementary service";
        container name {
          tailf:info
            "Specify the subscribed name service";
          container calling {
            tailf:info
              "calling name service";
            tailf:cli-delete-when-empty;
            presence "true";
          }
        }
      }
      container termination {
        tailf:info
          "To connect the TR pair and to in turn enable internal termination";
        leaf multidrop {
          tailf:info
            "Enable multidrop Internal termination";
          type empty;
        }
      }
      leaf point-to-point-setup {
        tailf:info
          "Bri send point-to-point SETUP";
        tailf:cli-full-command;
        type empty;
      }
    }
    leaf scramble {
      tailf:cli-full-command;
      type empty;
    }
    container clock {
      tailf:info
        "Configure interface clock source";
      leaf source {
        type enumeration {
          enum "internal" {
            tailf:info
              "Internal clock source";
          }
          enum "external" {
            tailf:info
              "External clock source";
          }
          enum "line" {
            tailf:info
              "Line clock source";
          }
        }
      }
      leaf rate {
        tailf:info
          "Clock rate";
        type uint32 {
          tailf:info
            "NUM;;Clock rate, round of to the nearest supported value by device. Please set exact to avoid diff.";
        }
      }
    }
    leaf down-when-looped {
      tailf:info
        "Force looped serial interface down";
      tailf:cli-full-command;
      type empty;
    }
    leaf crc {
      tailf:info
        "CRC interface subcommands";
      tailf:cli-full-command;
      type enumeration {
        enum "16" {
          tailf:info
            "Setting CRC-16";
        }
        enum "32" {
          tailf:info
            "Setting CRC-32";
        }
      }
    }
    container carrier-delay {
      tailf:info
        "Specify delay for interface transitions";
      uses carrier-delay-grouping;
      container up {
        tailf:info
          "Carrier Up Transitions";
        uses carrier-delay-grouping;
      }
      container down {
        tailf:info
          "Carrier Down Transitions";
        uses carrier-delay-grouping;
      }
    }
    leaf trunk-group {
      tailf:info
        "Configure interface to be in a trunk group";
      tailf:non-strict-leafref {
        path "/ncs:devices/ncs:device/ncs:config/ios:trunk/group/name" {
          tailf:xpath-root 3;
        }
      }
      type string {
        tailf:info
          "WORD;;Trunk group label";
      }
    }
    container crypto {
      tailf:info
        "Encryption/Decryption commands";
      container engine {
        tailf:info
          "";
        tailf:cli-compact-syntax;
        tailf:cli-sequence-commands {
          tailf:cli-reset-all-siblings;
        }
        leaf slot {
          tailf:info
            "WORD;;<integer>/<integer>";
          type string;
        }
        leaf location {
          tailf:info
            "";
          tailf:cli-drop-node-name;
          type enumeration {
            enum "inside";
            enum "outside";
          }
        }
      }
      container map {
        tailf:info
          "Assign a Crypto Map";
        container ipv4 {
          tailf:cli-drop-node-name;
          tailf:cli-compact-syntax;
          tailf:cli-sequence-commands {
            tailf:cli-reset-siblings;
          }
          leaf map-name {
            tailf:cli-drop-node-name;
            tailf:cli-disallow-value "ipv6";
            tailf:non-strict-leafref {
              path "/ncs:devices/ncs:device/ncs:config/ios:crypto/map/name" {
                tailf:xpath-root 3;
              }
            }
            type string {
              tailf:info
                "WORD;;Crypto Map tag";
            }
          }
          leaf redundancy {
            tailf:info
              "enable redundancy";
            type string {
              tailf:info
                "WORD;;Name of IP Redundancy Group";
            }
          }
          leaf stateful {
            tailf:info
              "enable stateful failover";
            when "../redundancy" {
              tailf:xpath-root 3;
              tailf:dependency "../redundancy";
            }
            type empty;
          }
        }
        container ipv6 {
          tailf:cli-compact-syntax;
          tailf:cli-sequence-commands {
            tailf:cli-reset-siblings;
          }
          leaf map-name {
            tailf:cli-drop-node-name;
            tailf:non-strict-leafref {
              path "/ncs:devices/ncs:device/ncs:config/ios:crypto/map/name" {
                tailf:xpath-root 3;
              }
            }
            type string {
              tailf:info
                "WORD;;Crypto Map tag";
            }
          }
          leaf redundancy {
            tailf:info
              "enable redundancy";
            type string {
              tailf:info
                "WORD;;Name of IP Redundancy Group";
            }
          }
          leaf stateful {
            tailf:info
              "enable stateful failover";
            when "../redundancy" {
              tailf:xpath-root 3;
              tailf:dependency "../redundancy";
            }
            type empty;
          }
        }
      }
    }
    container routing {
      tailf:info
        "Per-interface routing configuration";
      leaf dynamic {
        tailf:info
          "participates in routing protocols";
        tailf:cli-boolean-no;
        tailf:cli-full-command;
        type boolean;
        default "true";
      }
    }
    container autonomic {
      tailf:info
        "Autonomic Networking";
      leaf connect {
        tailf:info
          "Connect to External Device";
        type empty;
      }
    }
    container performance {
      tailf:info
        "Global performance monitor configuration";
      container monitor {
        tailf:info
          "monitor";
        leaf context {
          tailf:info
            "Select ezPM context";
          tailf:cli-diff-dependency "/ios:performance/monitor/context[name=current()]/exporter/destination" {
            tailf:xpath-root 3;
          }
          tailf:non-strict-leafref {
            path "/ncs:devices/ncs:device/ncs:config/ios:performance/monitor/context/name" {
              tailf:xpath-root 3;
            }
          }
          type string {
            tailf:info
              "WORD;;User defined ezPM context";
          }
        }
      }
    }
    container qos {
      tailf:info
        "QoS configuration";
      container trust {
        tailf:info
          "Trust state of the interface";
        choice trust-choice {
          leaf dscp {
            tailf:info
              "Trust DSCP";
            type empty;
          }
          leaf cos {
            tailf:info
              "Trust CoS";
            type empty;
          }
          leaf device {
            tailf:info
              "trusted device class";
            type enumeration {
              enum "cisco-phone" {
                tailf:info
                  "Cisco IP Phone";
              }
            }
          }
        }
      }
      leaf pre-classify {
        tailf:info
          "Enable QOS classification before packets are tunnel encapsulated";
        type empty;
      }
    }
    list tx-queue {
      tailf:info
        "Configure interface transmit queue";
      tailf:cli-mode-name "config-if-tx-queue";
      key "id";
      leaf id {
        type uint8 {
          tailf:info
            "<1-4>;;Transmit queue number";
          range "1..4";
        }
      }
      container bandwidth {
        tailf:info
          "Bandwidth for this queue";
        tailf:cli-compact-syntax;
        tailf:cli-sequence-commands {
          tailf:cli-reset-siblings;
        }
        choice bandwidth-choice {
          case numeric {
            leaf value {
              tailf:cli-drop-node-name;
              type string {
                tailf:info
                  "<16000-1000000000>;;Bandwidth (Sharing rate) (postfix k, m, g optional; decimal point allowed)";
              }
            }
            leaf unit {
              tailf:cli-drop-node-name;
              type string {
                tailf:info
                  "UNIT;;kbps | mbps | gbps";
              }
            }
          }
          leaf percent {
            tailf:info
              "% of the link bandwidth";
            type uint8 {
              tailf:info
                "<1-100>;;percent";
              range "1..100";
            }
          }
        }
      }
      leaf priority {
        tailf:info
          "Priority of this queue";
        type enumeration {
          enum "high" {
            tailf:info
              "High priority queue";
          }
        }
      }
    }
    container link {
      tailf:info
        "Configure Link";
      container state {
        tailf:info
          "Configure link state";
        container group {
          tailf:info
            "Configure link state group";
          tailf:cli-compact-syntax;
          tailf:cli-sequence-commands {
            tailf:cli-reset-siblings;
          }
          leaf number {
            tailf:cli-drop-node-name;
            tailf:cli-incomplete-command;
            type uint8 {
              tailf:info
                "<1-10>;;Link state group number";
              range "1..10";
            }
          }
          leaf direction {
            tailf:cli-drop-node-name;
            type enumeration {
              enum "downstream" {
                tailf:info
                  "Downstream interface";
              }
              enum "upstream" {
                tailf:info
                  "Upstream interface";
              }
            }
          }
        }
      }
    }
    container source {
      tailf:info
        "Get config from another source";
      leaf template {
        tailf:info
          "Get config from a template";
        tailf:non-strict-leafref {
          path "/ncs:devices/ncs:device/ncs:config/ios:template/name" {
            tailf:xpath-root 3;
          }
        }
        type string {
          tailf:info
            "WORD;;Template name";
        }
      }
    }
    container l2protocol {
      tailf:info
        "Configure l2 control protocol processing";
      container peer {
        tailf:info
          "peer L2 control protocol packets as data";
        tailf:cli-delete-when-empty;
        presence "true";
        leaf-list protocol {
          tailf:cli-drop-node-name;
          tailf:cli-flat-list-syntax;
          type l2protocol-type;
        }
      }
      container forward {
        tailf:info
          "forward L2 control protocol packets as data";
        tailf:cli-delete-when-empty;
        presence "true";
        leaf-list protocol {
          tailf:cli-drop-node-name;
          tailf:cli-flat-list-syntax;
          type l2protocol-type;
        }
      }
    }
    container zone-member {
      tailf:info
        "Apply zone name";
      leaf security {
        tailf:info
          "Security zone";
        tailf:cli-diff-dependency "../../vrf/forwarding" {
          tailf:xpath-root 3;
        }
        tailf:non-strict-leafref {
          path "/ncs:devices/ncs:device/ncs:config/ios:zone/security/id" {
            tailf:xpath-root 3;
          }
        }
        type string {
          tailf:info
            "WORD;;Zone";
        }
      }
    }
  }

  grouping interface-common-grouping {
    uses interface-common-grouping0 {
      refine "ip/helper-address/vrf/vrf" {
        tailf:cli-diff-dependency "../../../../../../ip/vrf" {
          tailf:xpath-root 3;
        }
        tailf:cli-diff-dependency "../../../../../../vrf/definition" {
          tailf:xpath-root 3;
        }
      }
      refine "crypto/map/ipv4/map-name" {
        tailf:cli-diff-dependency "../../../../../../crypto/map" {
          tailf:xpath-root 3;
        }
      }
      refine "crypto/map/ipv6/map-name" {
        tailf:cli-diff-dependency "../../../../../../crypto/map" {
          tailf:xpath-root 3;
        }
      }
      refine "ip/mobile/router-service/roam" {
        tailf:cli-diff-dependency "../../../../../../router/mobile" {
          tailf:xpath-root 3;
        }
      }
      refine "ip/pim/mode" {
        tailf:cli-diff-dependency "../../../../../ip/multicast-routing" {
          tailf:xpath-root 3;
        }
      }
    }
  }

  grouping sub-interface-common-grouping {
    uses interface-common-grouping0 {
      refine "ip/helper-address/vrf/vrf" {
        tailf:cli-diff-dependency "../../../../../../../ip/vrf" {
          tailf:xpath-root 3;
        }
        tailf:cli-diff-dependency "../../../../../../../vrf/definition" {
          tailf:xpath-root 3;
        }
      }
      refine "crypto/map/ipv4/map-name" {
        tailf:cli-diff-dependency "../../../../../../../crypto/map" {
          tailf:xpath-root 3;
        }
      }
      refine "crypto/map/ipv6/map-name" {
        tailf:cli-diff-dependency "../../../../../../../crypto/map" {
          tailf:xpath-root 3;
        }
      }
      refine "ip/mobile/router-service/roam" {
        tailf:cli-diff-dependency "../../../../../../../router/mobile" {
          tailf:xpath-root 3;
        }
      }
      refine "ip/pim/mode" {
        tailf:cli-diff-dependency "../../../../../../ip/multicast-routing" {
          tailf:xpath-root 3;
        }
      }
    }
  }

  grouping interface-common-switch-grouping {
    uses interface-common-grouping {
      refine "ip/dhcp/snooping" {
        tailf:cli-diff-dependency "../../../switchport" {
          tailf:xpath-root 3;
        }
      }
      refine "ip/verify" {
        tailf:cli-diff-dependency "../../switchport" {
          tailf:xpath-root 3;
        }
      }
      refine "ip/igmp" {
        tailf:cli-diff-dependency "../../switchport" {
          tailf:xpath-root 3;
          tailf:cli-trigger-on-set;
        }
        tailf:cli-diff-dependency "../../switchport" {
          tailf:xpath-root 3;
        }
      }
      refine "ip/ospf" {
        tailf:cli-diff-dependency "../../switchport" {
          tailf:xpath-root 3;
          tailf:cli-trigger-on-set;
        }
      }
      refine "ip/redirects" {
        tailf:cli-diff-dependency "../../switchport" {
          tailf:xpath-root 3;
          tailf:cli-trigger-on-set;
        }
      }
      refine "standby" {
        tailf:cli-diff-dependency "../switchport" {
          tailf:xpath-root 3;
          tailf:cli-trigger-on-set;
        }
      }
      refine "service-policy/input" {
        tailf:cli-diff-dependency "../../switchport" {
          tailf:xpath-root 3;
          tailf:cli-trigger-on-set;
        }
      }
      refine "service-policy/output" {
        tailf:cli-diff-dependency "../../switchport" {
          tailf:xpath-root 3;
          tailf:cli-trigger-on-set;
        }
      }
      refine "udld" {
        tailf:cli-diff-dependency "../switchport" {
          tailf:xpath-root 3;
          tailf:cli-trigger-on-set;
        }
      }
    }
  }

  grouping sub-interface-common-switch-grouping {
    uses sub-interface-common-grouping {
      refine "ip/dhcp/snooping" {
        tailf:cli-diff-dependency "../../../switchport" {
          tailf:xpath-root 3;
        }
      }
      refine "ip/verify" {
        tailf:cli-diff-dependency "../../switchport" {
          tailf:xpath-root 3;
        }
      }
      refine "ip/igmp" {
        tailf:cli-diff-dependency "../../switchport" {
          tailf:xpath-root 3;
          tailf:cli-trigger-on-set;
        }
        tailf:cli-diff-dependency "../../switchport" {
          tailf:xpath-root 3;
        }
      }
      refine "ip/ospf" {
        tailf:cli-diff-dependency "../../switchport" {
          tailf:xpath-root 3;
          tailf:cli-trigger-on-set;
        }
      }
      refine "ip/redirects" {
        tailf:cli-diff-dependency "../../switchport" {
          tailf:xpath-root 3;
          tailf:cli-trigger-on-set;
        }
      }
      refine "standby" {
        tailf:cli-diff-dependency "../switchport" {
          tailf:xpath-root 3;
          tailf:cli-trigger-on-set;
        }
      }
      refine "service-policy/input" {
        tailf:cli-diff-dependency "../../switchport" {
          tailf:xpath-root 3;
          tailf:cli-trigger-on-set;
        }
      }
      refine "service-policy/output" {
        tailf:cli-diff-dependency "../../switchport" {
          tailf:xpath-root 3;
          tailf:cli-trigger-on-set;
        }
      }
      refine "udld" {
        tailf:cli-diff-dependency "../switchport" {
          tailf:xpath-root 3;
          tailf:cli-trigger-on-set;
        }
      }
    }
  }

  grouping interface-tunnel-grouping {
    container tunnel {
      tailf:info
        "protocol-over-protocol tunneling";
      leaf source {
        tailf:info
          "source of tunnel packets";
        type string;
      }
      leaf destination {
        tailf:info
          "destination of tunnel";
        type inet:host {
          tailf:info
            "Hostname, A.B.C.D or X:X:X:X::X;;Destination address";
        }
      }
      container mode {
        tailf:info
          "tunnel encapsulation method";
        choice mode-choice {
          container ipsec {
            tailf:info
              "IPSec tunnel encapsulation";
            container ipv4 {
              tailf:info
                "over IPv4";
              tailf:cli-delete-when-empty;
              presence "true";
            }
          }
          container mpls {
            tailf:info
              "MPLS encapsulations";
            container traffic-eng {
              tailf:info
                "Traffic engineering tunnels";
              tailf:cli-delete-when-empty;
              presence "true";
              leaf gre-ip {
                type empty;
              }
              leaf point-to-multipoint {
                tailf:info
                  "point-to-multipoint tunnel mode";
                tailf:cli-full-command;
                type empty;
              }
            }
          }
          container gre {
            tailf:info
              "generic route encapsulation protocol";
            choice gre-choice {
              container multipoint {
                tailf:info
                  "over IPv4 (multipoint)";
                presence "true";
                leaf ipv6 {
                  tailf:info
                    "over IPv6";
                  type empty;
                }
              }
              leaf ip {
                tailf:info
                  "over IP";
                type empty;
              }
              leaf ipv6 {
                tailf:info
                  "over IPv6";
                type empty;
              }
              default "ip";
            }
          }
          leaf eon {
            tailf:info
              "EON compatible CLNS tunnel";
            type empty;
          }
          leaf ipv6 {
            tailf:info
              "Generic packet tunneling in IPv6";
            type empty;
          }
        }
      }
      leaf key {
        tailf:info
          "security or selector key";
        type uint32 {
          tailf:info
            "<0-4294967295>;;key";
          range "0..4294967295";
        }
      }
      leaf vrf {
        tailf:info
          "set tunnel vrf membership";
        tailf:cli-diff-dependency "../../../../ip/vrf" {
          tailf:xpath-root 3;
        }
        tailf:cli-diff-dependency "../../../../vrf/definition" {
          tailf:xpath-root 3;
        }
        type string {
          tailf:info
            "WORD;;vrf table name";
        }
      }
      container path-mtu-discovery {
        tailf:info
          "Enable Path MTU Discovery on tunnel";
        presence "true";
      }
      container protection {
        tailf:info
          "Enable tunnel protection";
        container ipsec {
          tailf:info
            "Use ipsec to protect this tunnel interface";
          tailf:cli-compact-syntax;
          tailf:cli-sequence-commands {
            tailf:cli-reset-all-siblings;
          }
          leaf profile {
            tailf:info
              "Determine the ipsec policy profile to use.";
            tailf:non-strict-leafref {
              path "../../../../../../crypto/ipsec/profile/name";
            }
            type string {
              tailf:info
                "WORD;;IPSec policy profile";
            }
          }
          choice profile-choice {
            leaf isakmp-profile {
              tailf:info
                "Specify isakmp profile for the crypto connection.";
              tailf:non-strict-leafref {
                path "../../../../../../crypto/isakmp/profile/name";
              }
              type string {
                tailf:info
                  "WORD;;Profile name.";
              }
            }
            leaf ikev2-profile {
              tailf:info
                "Specify ikev2 profile for the crypto connection.";
              tailf:non-strict-leafref {
                path "../../../../../../crypto/ikev2/profile/name";
              }
              type string {
                tailf:info
                  "WORD;;Profile name.";
              }
            }
            leaf shared {
              tailf:info
                "Use a shared socket for the crypto connection.";
              type empty;
            }
          }
        }
      }
      container mpls {
        tailf:info
          "MPLS tunnel commands";
        container traffic-eng {
          tailf:info
            "Configure traffic engineering tunnel parameters";
          tailf:cli-diff-dependency "../../mode/mpls/traffic-eng" {
            tailf:xpath-root 3;
          }
          leaf name {
            tailf:info
              "specify a name describing the TE tunnel";
            tailf:cli-full-command;
            type string {
              tailf:info
                "WORD;;Name of tunnel (max of 63 characters)";
            }
          }
          container affinity {
            tailf:info
              "desired link attributes for links comprising tunnel";
            tailf:cli-compact-syntax;
            tailf:cli-sequence-commands {
              tailf:cli-reset-siblings;
            }
            leaf attributes {
              tailf:cli-drop-node-name;
              type string {
                tailf:info
                  "<0x0-0xFFFFFFFF>;;affinity value";
              }
            }
            leaf mask {
              tailf:info
                "mask on desired link attributes";
              type string {
                tailf:info
                  "<0x0-0xFFFFFFFF>;;affinity mask value";
              }
            }
          }
          container autoroute {
            tailf:info
              "parameters for routing over tunnel";
            leaf announce {
              tailf:info
                "announce tunnel to IGP";
              tailf:cli-full-command;
              type empty;
            }
          }
          container priority {
            tailf:info
              "tunnel priority";
            tailf:cli-sequence-commands {
              tailf:cli-reset-siblings;
            }
            tailf:cli-compact-syntax;
            leaf setup-priority {
              tailf:cli-drop-node-name;
              type uint8 {
                tailf:info
                  "<0-7>;;setup priority";
                range "0..7";
              }
            }
            leaf hold-priority {
              tailf:cli-drop-node-name;
              type uint8 {
                tailf:info
                  "<0-7>;;hold priority";
                range "0..7";
              }
            }
          }
          container bandwidth {
            tailf:info
              "tunnel bandwidth requirement";
            leaf requirement {
              tailf:cli-drop-node-name;
              type uint32 {
                tailf:info
                  "<0-4294967295>;;bandwidth requirement in kbps";
              }
            }
          }
          list path-option {
            tailf:info
              "a primary or fallback path setup option";
            tailf:cli-suppress-mode;
            tailf:cli-delete-when-empty;
            tailf:cli-compact-syntax;
            tailf:cli-sequence-commands {
              tailf:cli-reset-siblings;
            }
            tailf:cli-incomplete-command;
            key "id";
            leaf id {
              tailf:cli-suppress-range;
              type uint16 {
                tailf:info
                  "<1-1000>;;preference for this path option";
              }
            }
            leaf protect {
              tailf:info
                "a path protection setup option";
              tailf:cli-optional-in-sequence;
              tailf:cli-prefix-key;
              type empty;
            }
            choice path-option-choice {
              container dynamic {
                tailf:info
                  "setup based on dynamically calculcated path";
                presence "true";
              }
              container explicit {
                tailf:info
                  "setup based on preconfigured path";
                tailf:cli-flatten-container;
                tailf:cli-compact-syntax;
                choice explicit-choice {
                  leaf name {
                    tailf:info
                      "Specify an IP explicit path by name";
                    type string {
                      tailf:info
                        "WORD;;Name of ip explicit path";
                    }
                  }
                  leaf identifier {
                    tailf:info
                      "Specify an IP explicit path by number";
                    type uint16 {
                      tailf:info
                        "<1-65535>;;Number of ip explicit path";
                    }
                  }
                }
              }
            }
            leaf lockdown {
              tailf:info
                "not a candidate for reoptimization";
              tailf:cli-optional-in-sequence;
              type empty;
            }
            leaf verbatim {
              type empty;
            }
          }
          container auto-bw {
            tailf:info
              "Specify mpls tunnel should automatically change bw";
            presence "true";
          }
          container fast-reroute {
            tailf:info
              "Specify mpls tunnel can be fast-rerouted";
            presence "true";
          }
        }
      }
    }
    container domain {
      tailf:info
        "Specify a domain";
      tailf:cli-compact-syntax;
      tailf:cli-sequence-commands {
        tailf:cli-reset-all-siblings;
      }
      leaf domain-name {
        tailf:cli-drop-node-name;
        tailf:cli-optional-in-sequence;
        tailf:non-strict-leafref {
          path "/ncs:devices/ncs:device/ncs:config/ios:domain/name" {
            tailf:xpath-root 3;
          }
        }
        type string {
          tailf:info
            "WORD;;Domain name";
        }
      }
      leaf path {
        tailf:info
          "Specify a service provider for this interface";
        type string {
          tailf:info
            "WORD;;Specify the color of service provider";
        }
      }
      leaf path-id {
        tailf:cli-break-sequence-commands;
        tailf:info
          "Specify Path ID";
        type uint8 {
          tailf:info
            "<1-62>;;Path ID";
          range "1..62";
        }
      }
      leaf internet-bound {
        tailf:info
          "Specify Internet-bound interface";
        tailf:cli-full-command;
        type empty;
      }
      leaf zero-sla {
        tailf:info
          "Specify if you want this interface to be a 0-sla interface";
        tailf:cli-full-command;
        type empty;
      }
      leaf path-last-resort {
        tailf:info
          "Specify if you want this interface to be a path of last resort";
        tailf:cli-full-command;
        type empty;
      }
    }
  }

  grouping interface-ethernet-pre-grouping {
    leaf port-type {
      tailf:info
        "Set port type";
      type enumeration {
        enum "eni" {
          tailf:info
            "Set port-type to ENI";
        }
        enum "nni" {
          tailf:info
            "Set port-type to NNI";
        }
        enum "uni" {
          tailf:info
            "Set port-type to UNI";
        }
      }
    }
    container platform {
      tailf:info
        "Configure platform";
      container ring {
        tailf:info
          "Configure ring entries commands";
        leaf rx {
          tailf:info
            "Configure receiver ring entries";
          type uint16 {
            tailf:info
              "<1-4096>;;Number of ring entries for the Rx ring";
            range "1..4096";
          }
        }
        leaf tx {
          tailf:info
            "Configure transmit ring entries";
          type uint16 {
            tailf:info
              "<1-4096>;;Number of ring entries for the Tx ring";
            range "1..4096";
          }
        }
      }
    }
    container encapsulation {
      tailf:info
        "Set encapsulation type for an interface";
      container dot1Q {
        tailf:info
          "IEEE 802.1Q Virtual LAN";
        tailf:cli-compact-syntax;
        tailf:cli-sequence-commands;
        leaf vlan-id {
          tailf:cli-drop-node-name;
          type uint16 {
            tailf:info
              "<1-4094>;;IEEE 802.1Q VLAN ID required";
            range "1..4094";
          }
        }
        leaf second-dot1q {
          tailf:info
            "Configure this subinterface as a 1Q-in-1Q subinterface";
          tailf:cli-optional-in-sequence;
          tailf:cli-full-command;
          type union {
            type enumeration {
              enum "any" {
                tailf:info
                  "All Inner VLAN IDs not configured on another subinterface";
              }
            }
            type string {
              tailf:info
                "Second (inner) VLAN IDs e.g. 100,200-300,400,500-600";
            }
          }
        }
        leaf native {
          tailf:info
            "Make this as native vlan";
          type empty;
        }
      }
    }
  }

  grouping interface-ethernet-grouping0 {
    container mac {
      tailf:info
        "MAC interface commands";
      list access-group {
        tailf:info
          "MAC access-group configuration commands";
        tailf:cli-suppress-mode;
        tailf:cli-delete-when-empty;
        tailf:cli-compact-syntax;
        tailf:cli-sequence-commands;
        key "direction";
        leaf direction {
          type enumeration {
            enum "in" {
              tailf:info
                "Apply to Ingress";
            }
            enum "out" {
              tailf:info
                "Apply to Egress";
            }
          }
        }
        leaf access-list {
          tailf:cli-drop-node-name;
          tailf:cli-prefix-key;
          tailf:non-strict-leafref {
            path "/ncs:devices/ncs:device/ncs:config/ios:mac/access-list/extended/id" {
              tailf:xpath-root 3;
            }
          }
          type string {
            tailf:info
              "WORD;;ACL name";
          }
        }
      }
    }
    container spanning-tree {
      tailf:info
        "Spanning Tree Subsystem";
      leaf bpdufilter {
        tailf:info
          "Don't send or receive BPDUs on this interface";
        type enumeration {
          enum "disable" {
            tailf:info
              "Disable BPDU filtering for this interface";
          }
          enum "enable" {
            tailf:info
              "Enable BPDU filtering for this interface";
          }
        }
      }
      container bpduguard {
        tailf:info
          "Don't accept BPDUs on this interface";
        choice bpduguard-choice {
          leaf disable {
            tailf:info
              "Disable BPDU guard for this interface";
            type empty;
          }
          leaf enable {
            type empty;
            tailf:info
              "Enable BPDU guard for this interface";
          }
        }
      }
      leaf cost {
        tailf:info
          "To set the path cost of the interface";
        tailf:cli-full-command;
        type uint32 {
          range "1..200000000";
        }
      }
      leaf guard {
        tailf:info
          "Change an interface's spanning tree guard mode";
        tailf:cli-full-command;
        type enumeration {
          enum "loop" {
            tailf:info
              "Set guard mode to loop guard on interface";
          }
          enum "none" {
            tailf:info
              "Set guard mode to none";
          }
          enum "root" {
            tailf:info
              "Set guard mode to root guard on interface";
          }
        }
      }
      leaf link-type {
        tailf:info
          "Specify a link type for spanning tree tree protocol use";
        tailf:cli-full-command;
        type enumeration {
          enum "auto" {
            tailf:code-name "link_type_auto";
            tailf:info
              "Determine link type based on media duplex of this interface";
          }
          enum "none" {
            tailf:info
              "Consider the interface as point-to-point";
          }
          enum "point-to-point" {
            tailf:info
              "Consider the interface as point-to-point";
          }
          enum "root" {
            tailf:info
              "Consider the interface as shared";
          }
        }
      }
      container mst {
        tailf:info
          "Multiple spanning tree";
        choice mst-choice {
          list instance-range {
            tailf:cli-drop-node-name;
            tailf:cli-suppress-mode;
            tailf:cli-delete-when-empty;
            tailf:cli-compact-syntax;
            tailf:cli-range-list-syntax;
            key "id";
            leaf id {
              type uint16 {
                tailf:info
                  "MST instance list, example 0,2-4,6,8-12";
              }
            }
            leaf cost {
              tailf:info
                "Change the interface spanning tree path cost for an instance";
              type uint32 {
                tailf:info
                  "<1-200000000>;;Change the interface spanning tree path cost for an instance";
                range "1..200000000";
              }
            }
            leaf port-priority {
              tailf:info
                "Change the spanning tree port priority for an instance";
              type uint16 {
                tailf:info
                  "<0-240>;;port priority in increments of 16";
                range "0..240" {
                  tailf:step "16";
                }
              }
            }
          }
          leaf pre-standard {
            tailf:info
              "Force pre-standard MST BPDU transmission on port";
            type empty;
          }
        }
      }
      container portfast {
        tailf:info
          "Spanning tree portfast options";
        tailf:cli-compact-syntax;
        tailf:cli-delete-when-empty;
        presence "true";
        choice portfast-choice {
          leaf disable {
            tailf:info
              "Disable portfast for this interface";
            type empty;
          }
          leaf network {
            tailf:info
              "Enable portfast network on the interface";
            type empty;
          }
          case trunk-mode {
            leaf edge {
              tailf:info
                "Enable portfast edge on the interface";
              type empty;
            }
            leaf trunk {
              tailf:info
                "Enable portfast edge on the interface even in trunk mode";
              type empty;
            }
          }
        }
      }
      container loopguard {
        tailf:info
          "Spanning tree loopguard options";
        leaf default {
          tailf:info
            "Enable loopguard by default on all ports";
          type empty;
        }
      }
    }
    container srr-queue {
      tailf:info
        "Configure shaped round-robin transmit queues";
      container bandwidth {
        tailf:info
          "Configure shared bandwidth";
        leaf limit {
          tailf:info
            "Configure bandwidth-limit for this interface";
          type uint8 {
            tailf:info
              "<10-90>;;enter bandwidth limit for interface as percentage";
            range "10..90";
          }
        }
        container shape {
          tailf:info
            "Configure shaping on transmit queues";
          tailf:cli-compact-syntax;
          tailf:cli-sequence-commands;
          tailf:cli-reset-container;
          leaf weight1 {
            tailf:cli-drop-node-name;
            tailf:cli-incomplete-command;
            type uint16 {
              tailf:info
                "<0-65535>;;enter bandwidth weight for queue id 1";
            }
          }
          leaf weight2 {
            tailf:cli-drop-node-name;
            tailf:cli-incomplete-command;
            type uint16 {
              tailf:info
                "<0-65535>;;enter bandwidth weight for queue id 2";
            }
          }
          leaf weight3 {
            tailf:cli-drop-node-name;
            tailf:cli-incomplete-command;
            type uint16 {
              tailf:info
                "<0-65535>;;enter bandwidth weight for queue id 3";
            }
          }
          leaf weight4 {
            tailf:cli-drop-node-name;
            type uint16 {
              tailf:info
                "<0-65535>;;enter bandwidth weight for queue id 4";
            }
          }
        }
        container share {
          tailf:info
            "Configure shared bandwidth";
          tailf:cli-compact-syntax;
          tailf:cli-sequence-commands;
          tailf:cli-reset-container;
          leaf weight1 {
            tailf:cli-drop-node-name;
            tailf:cli-incomplete-command;
            type uint8 {
              tailf:info
                "<1-255>;;enter bandwidth weight for queue id 1";
              range "1..255";
            }
          }
          leaf weight2 {
            tailf:cli-drop-node-name;
            tailf:cli-incomplete-command;
            type uint8 {
              tailf:info
                "<1-255>;;enter bandwidth weight for queue id 2";
              range "1..255";
            }
          }
          leaf weight3 {
            tailf:cli-drop-node-name;
            tailf:cli-incomplete-command;
            type uint8 {
              tailf:info
                "<1-255>;;enter bandwidth weight for queue id 3";
              range "1..255";
            }
          }
          leaf weight4 {
            tailf:cli-drop-node-name;
            type uint8 {
              tailf:info
                "<1-255>;;enter bandwidth weight for queue id 4";
              range "1..255";
            }
          }
        }
      }
    }
    leaf queue-set {
      tailf:info
        "Choose a queue set for this queue";
      type uint8 {
        tailf:info
          "<1-2>;;the qset to which this port is mapped";
      }
    }
    container dot1x {
      tailf:info
        "Interface Config Commands for IEEE 802.1X";
      container pae {
        tailf:info
          "Set 802.1x interface pae type";
        leaf authenticator {
          tailf:info
            "Set pae type as Authenticator";
          type empty;
        }
      }
      container timeout {
        tailf:info
          "Various Timeouts";
        leaf quiet-period {
          tailf:info
            "QuietPeriod in Seconds";
          type uint16 {
            tailf:info
              "<1-65535>;;Enter a value between 1 and 65535";
            range "1..65535";
          }
        }
        leaf tx-period {
          tailf:info
            "Timeout for supplicant retries";
          type uint16 {
            tailf:info
              "<1-65535>;;Enter a value between 1 and 65535";
            range "1..65535";
          }
        }
        leaf supp-period {
          tailf:info
            "Timeout for supplicant reply";
          type uint16 {
            tailf:info
              "<1-65535>;;Enter a value between 1 and 65535";
            range "1..65535";
          }
        }
        leaf ratelimit-period {
          tailf:info
            "Ratelimit Period in seconds";
          type uint16 {
            tailf:info
              "<1-65535>;;Enter a value between 1 and 65535";
            range "1..65535";
          }
        }
        leaf held-period {
          tailf:info
            "Timeout for authentication retries";
          type uint16 {
            tailf:info
              "<1-65535>;;Enter a value between 1 and 65535";
            range "1..65535";
          }
        }
      }
    }
    leaf media-type {
      tailf:info
        "Media type";
      tailf:cli-full-command;
      tailf:meta-data "inject-interface-config-duplex" {
        tailf:meta-value "duplex :: duplex :: after :: create";
      }
      tailf:meta-data "inject-interface-config-speed" {
        tailf:meta-value "speed :: speed :: after :: create";
      }
      tailf:ned-data "../duplex" {
        tailf:xpath-root 3;
        tailf:transaction to;
      }
      tailf:ned-data "../speed" {
        tailf:xpath-root 3;
        tailf:transaction to;
      }
      type enumeration {
        enum "rj45" {
          tailf:info
            "Copper";
        }
        enum "sfp" {
          tailf:info
            "Fiber";
        }
        enum "auto-select" {
          tailf:info
            "Auto Select";
        }
        enum "gbic";
      }
      default "auto-select";
    }
    container mdix {
      tailf:info
        "Set Media Dependent Interface with Crossover";
      leaf auto {
        tailf:info
          "Enable automatic MDI crossover detection on this interface";
        tailf:cli-boolean-no;
        type boolean;
        default "true";
      }
    }
    leaf channel-protocol {
      tailf:info
        "Select the channel protocol (LACP, PAgP)";
      type enumeration {
        enum "lacp" {
          tailf:info
            "Prepare interface for LACP protocol";
        }
        enum "pagp" {
          tailf:info
            "Prepare interface for PAgP protocol";
        }
      }
    }
    container lacp {
      tailf:info
        "LACP interface subcommands";
      leaf rate {
        tailf:info
          "Rate at which the LACP packets are requested to be ingressed to this interface";
        type enumeration {
          enum "fast" {
            tailf:info
              "Request LACP packets to be ingressed at the 1 second rate for this interface";
          }
          enum "normal" {
            tailf:info
              "Request LACP packets to be ingressed at the 30 second rate once the link is established";
          }
        }
        default "normal";
      }
      leaf fast-switchover {
        tailf:info
          "Enable LACP fast switchover on this port channel";
        type empty;
      }
      leaf min-bundle {
        tailf:info
          "LACP minimum number of ports to bundle in this port channel";
        type uint8 {
          tailf:info
            "<1-8>;;Minimum number of ports to bundle in this Port Channel";
          range "1..8";
        }
      }
      leaf max-bundle {
        tailf:info
          "LACP maximum number of ports to bundle in this port channel";
        type uint8 {
          tailf:info
            "<1-8>;;Max number of ports to bundle in this Port Channel";
          range "1..8";
        }
      }
    }
    container ethernet {
      tailf:info
        "Ethernet interface parameters";
      container oam-conf {
        tailf:cli-drop-node-name;
        container oam {
          tailf:info
            "To enable Ethernet Link OAM";
          leaf max-rate {
            tailf:info
              "Maximum transmission rate(number of OAMPDUs per second)";
            type uint8 {
              tailf:info
                "<1-10>;;Set the rate in number of packets per second";
              range "1..10";
            }
          }
          leaf min-rate {
            tailf:info
              "Minimum transmission rate(one OAMPDU per number of seconds)";
            type uint8 {
              tailf:info
                "<1-10>;;Set the rate in number of seconds";
              range "1..10";
            }
          }
          leaf mode {
            tailf:info
              "Ethernet OAM client mode";
            type enumeration {
              enum "active" {
                tailf:info
                  "Active mode";
              }
              enum "passive" {
                tailf:info
                  "Passive mode";
              }
            }
          }
          container remote-loopback {
            tailf:info
              "Ethernet OAM Remote Loopback";
            leaf supported {
              tailf:info
                "Support remote loopback functionality";
              type empty;
            }
          }
          leaf timeout {
            tailf:info
              "Ethernet OAM client link timeout setting";
            type uint8 {
              tailf:info
                "<2-30>;;Set timeout value in number of seconds";
              range "2..30";
            }
            default "5";
          }
          container link-monitor {
            tailf:info
              "Ethernet OAM Link Monitor";
            leaf supported {
              tailf:info
                "Support link monitoring on the interface";
              tailf:cli-boolean-no;
              tailf:cli-full-command;
              type boolean;
              default "true";
            }
            leaf on {
              tailf:info
                "Enable link monitoring on the interface";
              tailf:cli-boolean-no;
              tailf:cli-full-command;
              type boolean;
              default "true";
            }
            container receive-crc {
              tailf:info
                "Received frames with CRC errors in a period";
              leaf window {
                tailf:info
                  "Window size of a polling period";
                type uint16 {
                  tailf:info
                    "<10-1800>;;Set window size in multiple of 100 milliseconds (will be rounded off to second)";
                  range "10..1800";
                }
              }
            }
          }
        }
      }
      leaf oam {
        tailf:info
          "Operations, Administration and Maintenance";
        type empty;
      }
      container dot1ad {
        tailf:info
          "dot1ad port";
        choice dot1ad-choice {
          leaf nni {
            tailf:info
              "dot1ad nni port";
            type empty;
          }
          container uni {
            tailf:info
              "dot1ad uni";
            choice uni-choice {
              container c-port {
                tailf:info
                  "dot1ad uni customer bridge port";
                tailf:cli-delete-when-empty;
                presence "true";
                leaf isolate {
                  tailf:info
                    "split horizon";
                  type empty;
                }
              }
              container s-port {
                tailf:info
                  "dot1ad uni s bridge port";
                tailf:cli-delete-when-empty;
                presence "true";
                leaf isolate {
                  tailf:info
                    "split horizon";
                  type empty;
                }
              }
            }
          }
        }
      }
      container cfm {
        tailf:info
          "Ethernet CFM interface commands";
        container mip {
          tailf:info
            "Maintenance Intermediate Point";
          list level {
            tailf:info
              "Maintenance Level";
            tailf:cli-suppress-mode;
            tailf:cli-delete-when-empty;
            tailf:cli-incomplete-command;
            key "level";
            leaf level {
              type uint8 {
                tailf:info
                  "<0-7>;;maintenance level number";
                range "0..7";
              }
            }
            leaf-list vlan {
              tailf:info
                "Specify vlan (range 1-4094)";
              tailf:cli-range-list-syntax;
              type uint16 {
                tailf:info
                  "<1-4094>;;VLAN id";
                range "1..4094";
              }
            }
          }
        }
        container mep {
          tailf:info
            "Maintenance End Point";
          list mep-list {
            tailf:cli-drop-node-name;
            tailf:cli-suppress-mode;
            tailf:cli-delete-when-empty;
            tailf:cli-compact-syntax;
            tailf:cli-sequence-commands;
            key "mpid";
            leaf mpid {
              tailf:info
                "Maintenance End Point Identifier";
              tailf:cli-expose-key-name;
              type uint16 {
                tailf:info
                  "<1-8191>;;Maintenance End Point Identifier";
                range "1..8191";
              }
            }
            leaf domain {
              tailf:info
                "maintenance domain";
              tailf:cli-prefix-key;
              type string {
                tailf:info
                  "WORD;;maintenance domain name";
              }
            }
            leaf vlan {
              tailf:info
                "Specify vlan (range 1-4094)";
              tailf:cli-optional-in-sequence;
              tailf:cli-full-command;
              type uint16 {
                tailf:info
                  "<1-4094>;;VLAN id";
              }
            }
            container service {
              tailf:info
                "Maintenance Association within Domain";
              tailf:cli-flatten-container;
              tailf:cli-compact-syntax;
              choice service-choice {
                leaf short-ma-name {
                  tailf:cli-drop-node-name;
                  type string {
                    tailf:info
                      "WORD;;service instance id - short MA name";
                  }
                }
                leaf number {
                  tailf:info
                    "Maintenance Association number value";
                  type uint16 {
                    tailf:info
                      "<0-65535>;;Maintenance Association number";
                  }
                }
              }
            }
          }
        }
        leaf enable {
          tailf:info
            "CFM interface enabling";
          tailf:cli-boolean-no;
          tailf:cli-full-command;
          type boolean;
          default "true";
        }
        leaf interface {
          tailf:info
            "CFM interface enable";
          tailf:cli-boolean-no;
          type boolean;
        }
      }
      container uni {
        tailf:info
          "Configure Ether UNI";
        leaf id {
          tailf:info
            "Configure Ether UNI ID";
          type string {
            tailf:info
              "WORD;;UNI ID of length <1-64>";
            length "0..64";
          }
        }
        container bundle {
          tailf:info
            "bundling service without multiplexing";
          tailf:cli-delete-when-empty;
          presence "true";
          leaf all-to-one {
            tailf:info
              "all-to-one bundling service";
            type empty;
          }
        }
      }
      container lmi {
        tailf:info
          "Ethernet LMI interface commands";
        leaf interface {
          tailf:info
            "Enable Ethernet LMI on this interface";
          tailf:cli-boolean-no;
          type boolean;
        }
      }
    }
    container negotiation {
      tailf:info
        "Select autonegotiation mode";
      leaf auto {
        tailf:info
          "Enable link autonegotiation";
        tailf:cli-boolean-no;
        type boolean;
      }
    }
    container synchronous {
      tailf:info
        "Synchronous";
      leaf mode {
        tailf:info
          "Mode";
        type empty;
      }
    }
    container esmc {
      tailf:info
        "Ethernet Synchronization Messaging Channe";
      container mode {
        tailf:info
          "ESMC mode";
        leaf direction {
          tailf:cli-drop-node-name;
          tailf:cli-full-command;
          type enumeration {
            enum "rx" {
              tailf:info
                "ESMC receive-only mode";
            }
            enum "tx" {
              tailf:info
                "ESMC transmit-only mode";
            }
          }
        }
        leaf ql-disabled {
          tailf:info
            "QL disabled";
          type empty;
        }
      }
    }
    leaf speed {
      tailf:info
        "Configure speed operation.";
      tailf:cli-no-value-on-delete;
      tailf:cli-full-command;
      tailf:cli-diff-dependency "../negotiation" {
        tailf:xpath-root 3;
      }
      tailf:cli-diff-dependency "../media-type" {
        tailf:xpath-root 3;
        tailf:cli-trigger-on-set;
      }
      tailf:meta-data "patch-interface-speed";
      type enumeration {
        enum "10" {
          tailf:info
            "Force 10 Mbps operation";
        }
        enum "100" {
          tailf:info
            "Force 100 Mbps operation";
        }
        enum "1000" {
          tailf:info
            "Force 1000 Mbps operation";
        }
        enum "10000" {
          tailf:info
            "Force 10000 Mbps operation";
        }
        enum "auto" {
          tailf:info
            "Enable AUTO speed configuration";
        }
        enum "nonegotiate" {
          tailf:info
            "Do not negotiate speed";
        }
      }
      default "auto";
    }
    leaf duplex {
      tailf:info
        "Configure duplex operation.";
      tailf:cli-no-value-on-delete;
      tailf:cli-full-command;
      tailf:cli-diff-dependency "../negotiation" {
        tailf:xpath-root 3;
      }
      tailf:cli-diff-dependency "../speed" {
        tailf:xpath-root 3;
      }
      type enumeration {
        enum "auto" {
          tailf:code-name "duplex_auto";
          tailf:info
            "Enable AUTO duplex configuration";
        }
        enum "full" {
          tailf:code-name "duplex_full";
          tailf:info
            "Force full duplex operation";
        }
        enum "half" {
          tailf:code-name "duplex_half";
          tailf:info
            "Force half-duplex operation";
        }
      }
      default "auto";
    }
    uses xconnect-interface-grouping;
    container pppoe {
      tailf:info
        "pppoe interface subcommands";
      container enable {
        tailf:info
          "Enable pppoe";
        presence "true";
        leaf group {
          tailf:info
            "attach a BBA group";
          type union {
            type string {
              tailf:info
                "WORD;;BBA Group name";
            }
            type enumeration {
              enum "global" {
                tailf:info
                  "Attach global PPPoE group";
              }
            }
          }
        }
      }
      leaf max-sessions {
        tailf:info
          "Maximum PPPOE sessions";
        type uint16 {
          tailf:info
            "<1-4085>;;Maximum PPPOE sessions";
          range "1..4085";
        }
      }
    }
    container vlan-id {
      tailf:info
        "Process VLAN-encapsulated packets with a specific VLAN ID";
      list dot1q {
        tailf:info
          "802.1Q VLAN";
        tailf:cli-mode-name "config-if-vlan-id";
        tailf:cli-exit-command "exit-vlan-config" {
          tailf:info
            "Exit from VLAN configuration mode";
        }
        key "id";
        leaf id {
          type uint16 {
            tailf:info
              "<1-4094>;;VLAN ID";
            range "1..4094";
          }
        }
      }
    }
    container service {
      tailf:info
        "Configure Ether Service";
      list instance {
        tailf:info
          "Configure Ether Service Instance";
        tailf:cli-mode-name "config-if-srv";
        tailf:cli-compact-syntax;
        tailf:cli-sequence-commands;
        tailf:cli-incomplete-command;
        key "id";
        leaf id {
          tailf:cli-diff-dependency "../../../service-policy/output" {
            tailf:xpath-root 3;
            tailf:cli-trigger-on-set;
          }
          tailf:cli-diff-dependency "../../../service-policy/input" {
            tailf:xpath-root 3;
            tailf:cli-trigger-on-set;
          }
          tailf:cli-diff-dependency "../../../cdp/enable" {
            tailf:xpath-root 3;
            tailf:cli-trigger-on-set;
          }
          tailf:cli-diff-dependency "../../../ip/no-address/address" {
            tailf:xpath-root 3;
            tailf:cli-trigger-on-set;
          }
          type uint32 {
            tailf:info
              "<1-4294967295>;;Service Instance Identifier";
            range "1..4294967295";
          }
        }
        leaf trunk {
          tailf:cli-optional-in-sequence;
          tailf:cli-prefix-key;
          type empty;
        }
        leaf ethernet {
          tailf:info
            "Configure an Ethernet Instance";
          tailf:cli-hide-in-submode;
          type empty;
        }
        leaf ethernet-evc-name {
          tailf:cli-drop-node-name;
          tailf:cli-hide-in-submode;
          tailf:non-strict-leafref {
            path "/ncs:devices/ncs:device/ncs:config/ios:ethernet/evc/name" {
              tailf:xpath-root 3;
            }
          }
          type string {
            tailf:info
              "WORD;;Attach an EVC to the service instance";
          }
        }
        leaf description {
          tailf:cli-break-sequence-commands;
          tailf:info
            "Service instance specific description";
          tailf:cli-multi-value;
          tailf:cli-preformatted;
          tailf:cli-full-command;
          type string {
            tailf:info
              "LINE;;Up to 240 characters describing this service instance";
            length "0..240";
          }
        }
        container encapsulation {
          tailf:info
            "Configure ethernet frame match criteria";
          choice encapsulation-choice {
            container dot1q {
              tailf:info
                "IEEE 802.1Q Virtual LAN or S-VLAN";
              tailf:cli-compact-syntax;
              tailf:cli-sequence-commands {
                tailf:cli-reset-siblings;
              }
              tailf:cli-diff-dependency "../untagged" {
                tailf:xpath-root 3;
                tailf:cli-trigger-on-set;
              }
              uses if-srv-encapsulation-dot1q-grouping;
            }
            container dot1ad {
              tailf:info
                "IEEE 802.1ad VLAN-tagged packets";
              tailf:cli-compact-syntax;
              tailf:cli-sequence-commands {
                tailf:cli-reset-siblings;
              }
              leaf-list id {
                tailf:cli-drop-node-name;
                tailf:cli-replace-all;
                tailf:cli-range-list-syntax;
                type uint16 {
                  tailf:info
                    "<1-4094>;;VLAN id";
                  range "1..4094";
                }
              }
              leaf-list dot1q {
                tailf:info
                  "IEEE 802.1Q VLAN-tagged packets";
                tailf:cli-range-list-syntax;
                tailf:cli-replace-all;
                type uint16 {
                  tailf:info
                    "<1-4094>;;Single VLAN id";
                  range "1..4094";
                }
              }
            }
            container untagged {
              tailf:info
                "Untagged encapsulation";
              tailf:cli-compact-syntax;
              tailf:cli-sequence-commands {
                tailf:cli-reset-siblings;
              }
              tailf:cli-delete-when-empty;
              tailf:cli-diff-dependency "../dot1q" {
                tailf:xpath-root 3;
                tailf:cli-trigger-on-set;
              }
              tailf:meta-data "diff-interface-move-encap-untagged-1" {
                tailf:meta-value "no rewrite ingress tag pop \\d+ symmetric :: before :: encapsulation untagged";
              }
              presence "true";
              leaf comma {
                tailf:info
                  "comma";
                tailf:alt-name ",";
                type empty;
              }
              container dot1q {
                tailf:info
                  "IEEE 802.1Q Virtual LAN or S-VLAN";
                tailf:cli-flatten-container;
                tailf:cli-compact-syntax;
                tailf:cli-sequence-commands {
                  tailf:cli-reset-siblings;
                }
                uses if-srv-encapsulation-dot1q-grouping;
              }
            }
            container default {
              tailf:info
                "catch-all unconfigured encapsulation";
              presence "true";
            }
          }
        }
        container rewrite {
          tailf:info
            "Configure ethernet rewrite criteria";
          container ingress {
            tailf:info
              "Ingress Rewrite";
            container tag {
              tailf:info
                "Configure Rewrite Tag";
              tailf:cli-compact-syntax;
              tailf:cli-sequence-commands {
                tailf:cli-reset-siblings;
              }
              tailf:cli-diff-dependency "../../../encapsulation" {
                tailf:xpath-root 3;
              }
              choice tag-choice {
                leaf pop {
                  tailf:info
                    "Pop the tag";
                  type enumeration {
                    enum "1" {
                      tailf:info
                        "Pop the outermost tag";
                    }
                    enum "2" {
                      tailf:info
                        "Pop two outermost tags";
                    }
                  }
                }
                case push {
                  leaf push {
                    tailf:info
                      "Rewrite Operation of push";
                    type enumeration {
                      enum "dot1ad" {
                        tailf:info
                          "Push dot1ad tag";
                      }
                      enum "dot1q" {
                        tailf:info
                          "Push dot1q tag";
                      }
                    }
                  }
                  leaf vlan-id {
                    tailf:cli-drop-node-name;
                    type uint16 {
                      tailf:info
                        "<1-4094>;;VLAN id";
                      range "1..4094";
                    }
                  }
                }
                case translate {
                  leaf translate {
                    tailf:info
                      "Translate Tag";
                    tailf:cli-incomplete-command;
                    type enumeration {
                      enum "1-to-1" {
                        tailf:info
                          "Translate 1-to-1";
                      }
                      enum "1-to-2" {
                        tailf:info
                          "Translate 1-to-2";
                      }
                      enum "2-to-1" {
                        tailf:info
                          "Translate 2-to-1";
                      }
                      enum "2-to-2" {
                        tailf:info
                          "Translate 2-to-2";
                      }
                    }
                  }
                  leaf dot1ad {
                    tailf:info
                      "Ethertype dot1ad of the translation";
                    tailf:cli-optional-in-sequence;
                    type uint16 {
                      tailf:info
                        "<1-4094>;;VLAN id";
                      range "1..4094";
                    }
                  }
                  leaf dot1q {
                    tailf:info
                      "Ethertype dot1q of the translation";
                    type uint16 {
                      tailf:info
                        "<1-4094>;;VLAN id";
                      range "1..4094";
                    }
                  }
                  leaf second-dot1q {
                    tailf:info
                      "Second dot1q tag";
                    tailf:cli-optional-in-sequence;
                    type uint16 {
                      tailf:info
                        "<1-4094>;;VLAN id";
                      range "1..4094";
                    }
                  }
                  leaf vlan-type {
                    tailf:info
                      "Vlan protocol type";
                    tailf:cli-optional-in-sequence;
                    type enumeration {
                      enum "0x88A8" {
                        tailf:info
                          "vlan protocol type 0x88A8";
                      }
                      enum "0x9100" {
                        tailf:info
                          "vlan protocol type 0x9100";
                      }
                      enum "0x9200" {
                        tailf:info
                          "vlan protocol type 0x9200";
                      }
                    }
                  }
                }
              }
              leaf mode {
                tailf:cli-drop-node-name;
                type enumeration {
                  enum "symmetric" {
                    tailf:info
                      "Tag egress packets as specified in encapsulation";
                  }
                }
              }
            }
          }
        }
        container storm-control {
          tailf:info
            "storm configuration";
          container broadcast {
            tailf:info
              "Broadcast address storm control";
            leaf cir {
              tailf:info
                "Committed Information Rate";
              type string {
                tailf:info
                  "<8000-1000000000>;;Target Bit Rate (biTs per second)";
              }
            }
          }
          container multicast {
            tailf:info
              "Multicast address storm control";
            leaf cir {
              tailf:info
                "Committed Information Rate";
              type string {
                tailf:info
                  "<8000-1000000000>;;Target Bit Rate (biTs per second)";
              }
            }
          }
        }
        leaf group {
          tailf:info
            "Join a service group";
          tailf:cli-full-command;
          tailf:cli-diff-dependency "/ios:service-group" {
            tailf:xpath-root 3;
          }
          type uint16 {
            tailf:info
              "<1-65532>;;Service group ID number";
            range "1..65532";
          }
        }
        container errdisable {
          tailf:info
            "Configure error disable";
          container recovery {
            tailf:info
              "enable auto recovery";
            container cause {
              tailf:info
                "error disable cause";
              leaf mac-security {
                tailf:info
                  "mac-security violation";
                type uint32 {
                  tailf:info
                    "<30-86400>;;timer interval(sec)";
                  range "30..86400";
                }
              }
            }
          }
        }
        container snmp {
          tailf:info
            "Modify SNMP service instance parameters";
          container trap {
            tailf:info
              "Allow a specific SNMP trap";
            leaf link-status {
              tailf:info
                "Allow SNMP LINKUP and LINKDOWN traps";
              type empty;
            }
          }
          container ifindex {
            tailf:info
              "Persist ifindex for the service instance";
            leaf persist {
              tailf:info
                "Enable/Disable ifIndex persistence";
              type empty;
            }
          }
        }
        leaf shutdown {
          tailf:info
            "Take the Service Instance out of Service";
          type empty;
        }
        container mac {
          tailf:info
            "Commands for MAC Address-based features";
          container security {
            tailf:info
              "MAC Security commands";
            tailf:cli-display-separated;
            tailf:cli-delete-when-empty;
            presence "true";
            list address {
              tailf:info
                "MAC Address";
              tailf:cli-suppress-mode;
              tailf:cli-delete-when-empty;
              key "operation mac-address";
              leaf operation {
                type enumeration {
                  enum "deny" {
                    tailf:info
                      "Specify an address that must not be learnt";
                  }
                  enum "permit" {
                    tailf:info
                      "Specify an address to statically configure in the MAC table";
                  }
                }
              }
              leaf mac-address {
                type string {
                  tailf:info
                    "H.H.H;;Specify the 48-bit MAC Address to deny/permit";
                }
              }
            }
            container maximum {
              tailf:info
                "Configure an upper bound";
              leaf addresses {
                tailf:info
                  "Maximum addresses that can be learnt on this service instance";
                type uint16 {
                  tailf:info
                    "<1-1000>;;Address count";
                  range "1..1000";
                }
              }
            }
            leaf violation {
              tailf:info
                "Configure the response when a MAC security policy is violated";
              tailf:cli-full-command;
              type enumeration {
                enum "protect" {
                  tailf:info
                    "Protect mode - don't report violations, drop violating frames";
                }
                enum "restrict" {
                  tailf:info
                    "Restrict mode - report violations, drop violating frames";
                }
              }
            }
          }
          container static {
            tailf:info
              "static MAC address";
            list address {
              tailf:info
                "MAC Address";
              tailf:cli-suppress-mode;
              tailf:cli-delete-when-empty;
              key "mac-addr";
              leaf mac-addr {
                type string {
                  tailf:info
                    "H.H.H;;Specify the 48-bit Static MAC Address";
                }
              }
            }
          }
          list access-group {
            tailf:info
              "Specify access control for packets";
            tailf:cli-suppress-mode;
            tailf:cli-delete-when-empty;
            tailf:cli-compact-syntax;
            tailf:cli-sequence-commands;
            key "direction";
            leaf direction {
              type enumeration {
                enum "in" {
                  tailf:info
                    "Apply to Ingress";
                }
                enum "out" {
                  tailf:info
                    "Apply to Egress";
                }
              }
            }
            leaf access-list {
              tailf:cli-drop-node-name;
              tailf:cli-prefix-key;
              type string {
                tailf:info
                  "WORD;;ACL name";
              }
            }
          }
        }
        container l2protocol {
          tailf:info
            "Configure l2 control protocol processing";
          container peer {
            tailf:info
              "peer L2 control protocol packets as data";
            tailf:cli-delete-when-empty;
            presence "true";
            leaf-list protocol {
              tailf:cli-drop-node-name;
              tailf:cli-flat-list-syntax;
              type l2protocol-type;
            }
          }
          container forward {
            tailf:info
              "forward L2 control protocol packets as data";
            tailf:cli-delete-when-empty;
            presence "true";
            leaf-list protocol {
              tailf:cli-drop-node-name;
              tailf:cli-flat-list-syntax;
              type l2protocol-type;
            }
          }
          container tunnel {
            tailf:info
              "tunnel L2 control protocol packets as data";
            tailf:cli-delete-when-empty;
            presence "true";
            leaf-list protocol {
              tailf:cli-drop-node-name;
              tailf:cli-flat-list-syntax;
              type l2protocol-type;
            }
          }
        }
        container bridge-domain {
          tailf:info
            "Bridge-domain";
          tailf:cli-compact-syntax;
          tailf:cli-sequence-commands {
            tailf:cli-reset-all-siblings;
          }
          tailf:cli-diff-dependency "../encapsulation" {
            tailf:xpath-root 3;
          }
          leaf from-encapsulation {
            tailf:info
              "Derive bridge domains from encapsulation vlan list,";
            tailf:cli-optional-in-sequence;
            tailf:cli-full-command;
            type empty;
          }
          leaf bridge-id {
            tailf:cli-drop-node-name;
            tailf:non-strict-leafref {
              path "/ncs:devices/ncs:device/ncs:config/ios:bridge-domain/bridge-domain-list/id" {
                tailf:xpath-root 3;
              }
            }
            type uint16 {
              tailf:info
                "<1-16384>;;Bridge-domain number";
              range "1..16384";
            }
          }
          container split-horizon {
            tailf:info
              "Configure this port as a member of a split horizon group";
            tailf:cli-flatten-container;
            leaf group {
              tailf:info
                "Split-horizon group";
              type uint8 {
                tailf:info
                  "<0-2>;;Split-horizon group number";
                range "0..2";
              }
            }
          }
        }
        container service-policy {
          tailf:info
            "Attach a policy-map to an EFP";
          list input {
            tailf:info
              "service policy input";
            tailf:cli-suppress-mode;
            tailf:cli-delete-when-empty;
            max-elements 1;
            key "name";
            leaf name {
              tailf:non-strict-leafref {
                path "/ncs:devices/ncs:device/ncs:config/ios:policy-map/name" {
                  tailf:xpath-root 3;
                }
              }
              type string {
                tailf:info
                  "WORD;;input Policy-map name";
              }
            }
          }
          list output {
            tailf:info
              "service policy output";
            tailf:cli-suppress-mode;
            tailf:cli-delete-when-empty;
            max-elements 1;
            key "name";
            leaf name {
              tailf:non-strict-leafref {
                path "/ncs:devices/ncs:device/ncs:config/ios:policy-map/name" {
                  tailf:xpath-root 3;
                }
              }
              type string {
                tailf:info
                  "WORD;;output Policy-map name";
              }
            }
          }
        }
        uses xconnect-grouping {
          refine "xconnect-choice/xconnect/xconnect" {
            tailf:cli-diff-dependency "../encapsulation" {
              tailf:xpath-root 3;
            }
          }
          refine "xconnect-choice/xconnect/xconnect/mtu" {
            tailf:cli-diff-dependency "../../../../mtu" {
              tailf:xpath-root 3;
            }
          }
        }
        container cfm {
          tailf:info
            "Ethernet CFM EFP subcommands";
          container mip {
            leaf level {
              type uint8 {
                tailf:info
                  "<0-7>;;maintenance level number";
                range "0..7";
              }
            }
          }
          container mep {
            tailf:info
              "Maintenance End Point";
            tailf:cli-add-mode;
            tailf:cli-mode-name "config-if-srv-ecfm-mep";
            tailf:cli-compact-syntax;
            tailf:cli-sequence-commands;
            leaf domain {
              tailf:info
                "Configure a domain for this mep";
              tailf:cli-hide-in-submode;
              tailf:cli-incomplete-command;
              tailf:cli-diff-dependency "/ios:ethernet/cfm/domain" {
                tailf:xpath-root 3;
              }
              type string {
                tailf:info
                  "WORD;;maintenance domain name";
              }
            }
            leaf mpid {
              tailf:info
                "Maintenance End Point Identifier";
              tailf:cli-hide-in-submode;
              type uint16 {
                tailf:info
                  "<1-8191>;;Maintenance End Point Identifier";
                range "1..8191";
              }
            }
            container continuity-check {
              tailf:info
                "Enable Continuity Check for this local MEP";
              tailf:cli-break-sequence-commands;
              container static {
                tailf:info
                  "Verify MEP in received CCM is valid";
                leaf rmep {
                  tailf:info
                    "MEP defined using rmep mpid";
                  type empty;
                }
              }
            }
            container rmep {
              tailf:info
                "Static Remote MEP associated with this DOWN MEP";
              leaf mpid {
                tailf:info
                  "Maintenance End Point Identifier";
                type uint16 {
                  tailf:info
                    "<1-8191>;;Identifier value";
                  range "1..8191";
                }
              }
            }
            leaf cos {
              tailf:info
                "Specify Class of Service sent in CFM mssages for EFP MEP";
              type uint8 {
                tailf:info
                  "<0-7>;;CoS value";
                range "0..7";
              }
            }
          }
        }
        container ethernet-if-srv {
          tailf:cli-drop-node-name;
          container ethernet {
            tailf:info
              "ethernet";
            container lmi {
              tailf:info
                "Configure ether lmi parameters";
              container ce-vlan {
                tailf:info
                  "Configure ether lmi customer vlans";
                leaf-list map {
                  tailf:info
                    "Configure ether lmi ce-vlan/evc map";
                  tailf:cli-replace-all;
                  tailf:cli-range-list-syntax;
                  type union {
                    type uint16 {
                      tailf:info
                        "<1-4094>;;VLAN id";
                      range "1..4094";
                    }
                    type enumeration {
                      enum "default" {
                        tailf:info
                          "Default EFP";
                      }
                      enum "untagged" {
                        tailf:info
                          "Untagged frames";
                      }
                    }
                  }
                }
              }
            }
            container loopback {
              tailf:info
                "Ethernet Dataplane Loopback";
              container permit {
                tailf:info
                  "Allow data plane loopback to be activated";
                leaf external {
                  tailf:info
                    "Allow to loopback the traffic from the wire";
                  type empty;
                }
                leaf internal {
                  tailf:info
                    "Allow to loopback the traffic from the relay";
                  type empty;
                }
              }
            }
          }
        }
      }
    }
    container channel-group {
      tailf:info
        "Add this interface to an Etherchannel group";
      tailf:cli-compact-syntax;
      tailf:cli-sequence-commands {
        tailf:cli-reset-siblings;
      }
      leaf number {
        tailf:cli-drop-node-name;
        tailf:cli-diff-dependency "../../mls/qos/trust" {
          tailf:xpath-root 3;
        }
        tailf:cli-diff-dependency "../../mls" {
          tailf:xpath-root 3;
          tailf:cli-trigger-on-set;
        }
        tailf:cli-diff-dependency "../../ip" {
          tailf:xpath-root 3;
          tailf:cli-trigger-on-set;
        }
        tailf:cli-diff-dependency "../../ipv6" {
          tailf:xpath-root 3;
          tailf:cli-trigger-on-set;
        }
        tailf:cli-diff-dependency "../../service-policy" {
          tailf:xpath-root 3;
          tailf:cli-trigger-on-set;
        }
        tailf:cli-diff-dependency "../../mtu" {
          tailf:xpath-root 3;
          tailf:cli-trigger-on-set;
        }
        tailf:cli-diff-dependency "../../storm-control" {
          tailf:xpath-root 3;
          tailf:cli-trigger-on-set;
        }
        tailf:cli-diff-dependency "../../port-type" {
          tailf:xpath-root 3;
        }
        type uint16 {
          tailf:info
            "<1-512>;;Channel group number";
          range "1..512";
        }
      }
      leaf mode {
        tailf:info
          "Etherchannel Mode of the interface";
        type enumeration {
          enum "active" {
            tailf:info
              "Enable LACP unconditionally";
          }
          enum "auto" {
            tailf:info
              "Enable PAgP only if a PAgP device is detected";
          }
          enum "desirable" {
            tailf:info
              "Enable PAgP unconditionally";
          }
          enum "on" {
            tailf:info
              "Enable Etherchannel only";
          }
          enum "passive" {
            tailf:info
              "Enable LACP only if a LACP device is detected";
          }
        }
      }
    }
    container soak {
      tailf:info
        "Soak hardware link notification";
      container link {
        tailf:info
          "link";
        leaf notification {
          tailf:info
            "notification";
          type uint16 {
            tailf:info
              "<0-300>;;duration";
            range "0..300";
          }
        }
      }
    }
  }

  grouping interface-ethernet-grouping {
    uses interface-ethernet-grouping0 {
      refine "service/instance/service-policy" {
        tailf:cli-diff-dependency "../../../../../policy-map" {
          tailf:xpath-root 3;
        }
      }
      refine "service/instance/bridge-domain/bridge-id" {
        tailf:cli-diff-dependency "../../../../../../vlan/vlan-list" {
          tailf:xpath-root 3;
        }
      }
      refine "channel-group/number" {
        tailf:cli-diff-dependency "../../../../interface/Port-channel" {
          tailf:xpath-root 3;
        }
      }
    }
  }

  grouping sub-interface-ethernet-grouping {
    uses interface-ethernet-grouping0 {
      refine "service/instance/service-policy" {
        tailf:cli-diff-dependency "../../../../../../policy-map" {
          tailf:xpath-root 3;
        }
      }
      refine "service/instance/bridge-domain/bridge-id" {
        tailf:cli-diff-dependency "../../../../../../../vlan/vlan-list" {
          tailf:xpath-root 3;
        }
      }
      refine "channel-group/number" {
        tailf:cli-diff-dependency "../../../../../interface/Port-channel" {
          tailf:xpath-root 3;
        }
      }
    }
  }

  grouping interface-ethernet-switch-grouping {
    uses interface-ethernet-grouping {
      refine "service/instance" {
        tailf:cli-diff-dependency "../../switchport" {
          tailf:xpath-root 3;
        }
      }
      refine "channel-group/number" {
        tailf:cli-diff-dependency "../../switchport" {
          tailf:xpath-root 3;
        }
      }
    }
  }

  grouping sub-interface-ethernet-switch-grouping {
    uses sub-interface-ethernet-grouping {
      refine "service/instance" {
        tailf:cli-diff-dependency "../../switchport" {
          tailf:xpath-root 3;
        }
      }
      refine "channel-group/number" {
        tailf:cli-diff-dependency "../../switchport" {
          tailf:xpath-root 3;
        }
      }
    }
  }

  grouping interface-ethernet-post-grouping0 {
    leaf bridge-group {
      tailf:info
        "Transparent bridging interface parameters";
      tailf:cli-remove-before-change;
      tailf:cli-full-command;
      type uint8 {
        tailf:info
          "<1-255>;;Assign an interface to a Bridge Group.";
        range "1..255";
      }
    }
    container bridge-group-conf {
      tailf:cli-drop-node-name;
      when "../bridge-group" {
        tailf:xpath-root 3;
        tailf:dependency "../bridge-group";
      }
      list bridge-group {
        tailf:info
          "Transparent bridging interface parameters";
        tailf:cli-suppress-mode;
        tailf:cli-delete-when-empty;
        tailf:cli-incomplete-command;
        tailf:cli-incomplete-no;
        max-elements 1;
        key "id";
        leaf id {
          type uint8 {
            tailf:info
              "<1-255>;;Assign an interface to a Bridge Group.";
            range "1..255";
          }
        }
        leaf subscriber-loop-control {
          tailf:info
            "Configure subscriber loop control";
          tailf:cli-full-command;
          type empty;
        }
        leaf block-unknown-source {
          tailf:info
            "block traffic which come from unknown source MAC address";
          tailf:cli-full-command;
          type empty;
        }
        leaf source-learning {
          tailf:info
            "learn source MAC address";
          tailf:cli-boolean-no;
          tailf:cli-full-command;
          type boolean;
          default "true";
        }
        leaf unicast-flooding {
          tailf:info
            "flood packets with unknown unicast destination MAC addresses";
          tailf:cli-boolean-no;
          tailf:cli-full-command;
          type boolean;
          default "true";
        }
        leaf spanning-disabled {
          tailf:info
            "Disable spanning tree on a bridge group";
          tailf:cli-full-command;
          type empty;
        }
      }
    }
    list vrrp {
      tailf:info
        "VRRP Interface configuration commands";
      tailf:cli-suppress-mode;
      tailf:cli-delete-when-empty;
      key "id";
      leaf id {
        type uint8 {
          tailf:info
            "<1-255>;;Group number";
          range "1..255";
        }
      }
      container authentication {
        tailf:info
          "Authentication";
        choice auth {
          leaf word {
            tailf:cli-drop-node-name;
            tailf:cli-disallow-value "md5|text";
            type string {
              tailf:info
                "WORD;;Plain text authentication string";
            }
          }
          container md5 {
            tailf:info
              "Use MD5 authentication";
            leaf key-chain {
              tailf:info
                "Set key chain";
              type string {
                tailf:info
                  "WORD;;Name of key-chain";
              }
            }
            container key-string {
              tailf:info
                "Set key string";
              tailf:cli-flatten-container;
              tailf:cli-compact-syntax;
              tailf:cli-sequence-commands;
              uses password-grouping;
              leaf timeout {
                tailf:info
                  "Set timeout";
                type uint16 {
                  tailf:info
                    "<0-32767>;;Timeout until only accepting new key (seconds)";
                  range "0..32767";
                }
              }
            }
          }
          leaf text {
            tailf:info
              "Plain text authentication";
            type string {
              tailf:info
                "WORD;;Plain text authentication string (8 chars max)";
            }
          }
        }
      }
      uses interface-vrrp-grouping;
      container ip {
        tailf:info
          "Enable Virtual Router Redundancy Protocol (VRRP) for IP";
        tailf:cli-compact-syntax;
        tailf:cli-sequence-commands {
          tailf:cli-reset-siblings;
        }
        leaf address {
          tailf:cli-drop-node-name;
          type inet:ipv4-address {
            tailf:info
              "A.B.C.D;;VRRP group IP address";
          }
        }
        leaf secondary {
          tailf:info
            "Specify an additional VRRP address for this group";
          type empty;
        }
      }
    }
    container vrrv3p-v3 {
      when "/ios:fhrp/version/vrrp = 'v3'" {
        tailf:xpath-root 3;
        tailf:dependency "/ncs:devices/ncs:device/ncs:config/ios:fhrp/version/vrrp";
      }
      tailf:cli-drop-node-name;
      list vrrp {
        tailf:cli-mode-name "config-if-vrrp";
        tailf:cli-full-command;
        tailf:cli-exit-command "exit-vrrp" {
          tailf:info
            "Exit from VRRP group configuration mode";
        }
        key "id address-family";
        leaf id {
          type uint8 {
            tailf:info
              "<1-255>;;Group number";
            range "1..255";
          }
        }
        leaf address-family {
          tailf:cli-expose-key-name;
          tailf:info
            "Address family of the group";
          type enumeration {
            enum "ipv4" {
              tailf:info
                "ipv4 Address family";
            }
            enum "ipv6" {
              tailf:info
                "ipv6 Address family";
            }
          }
        }
        uses interface-vrrp-grouping;
        container address {
          tailf:info
            "IPv4 address config";
          list primary-list {
            tailf:cli-drop-node-name;
            tailf:cli-suppress-mode;
            tailf:cli-delete-when-empty;
            max-elements 1;
            key "address";
            leaf address {
              type union {
                type inet:ipv4-address {
                  tailf:info
                    "A.B.C.D;;IP address";
                }
                type inet:ipv6-address {
                  tailf:info
                    "X:X:X:X::X;;IPv6 address";
                }
              }
            }
            leaf primary {
              tailf:info
                "Primary Address";
              type empty;
            }
          }
          list secondary-list {
            tailf:cli-drop-node-name;
            tailf:cli-suppress-mode;
            tailf:cli-delete-when-empty;
            key "address";
            leaf address {
              type union {
                type inet:ipv4-address {
                  tailf:info
                    "A.B.C.D;;IP address";
                }
                type ios:ipv6-prefix {
                  tailf:info
                    "X:X:X:X::X/<0-128>;;IPv6 address and prefix";
                }
              }
            }
            leaf secondary {
              tailf:info
                "Secondary Address";
              type empty;
            }
          }
        }
      }
    }
    container vrrs {
      tailf:info
        "VRRS Interface configuration commands";
      list pathway {
        tailf:info
          "Configure a VRRS pathway";
        tailf:cli-mode-name "config-if-vrrs-pw";
        tailf:cli-exit-command "exit-vrrs-pw";
        key "name";
        leaf name {
          type string {
            tailf:info
              "WORD;;Name of the VRRS tag to associate with pathway";
          }
        }
        uses description-grouping;
        list address {
          tailf:info
            "IPv4/IPv6 Address configuration";
          tailf:cli-suppress-mode;
          tailf:cli-delete-when-empty;
          key "address";
          leaf address {
            type union {
              type inet:ipv4-address {
                tailf:info
                  "A.B.C.D;;IP address";
              }
              type inet:ipv6-address {
                tailf:info
                  "X:X:X:X::X;;IPv6 link-local address";
              }
              type ios:ipv6-prefix {
                tailf:info
                  "X:X:X:X::X/<0-128>;;IPv6 address and prefix";
              }
            }
          }
        }
      }
    }
  }

  grouping interface-ethernet-post-grouping {
    uses interface-ethernet-post-grouping0 {
      refine "vrrv3p-v3" {
        tailf:cli-diff-dependency "../../../fhrp/version/vrrp" {
          tailf:xpath-root 3;
        }
      }
    }
  }

  grouping sub-interface-ethernet-post-grouping {
    uses interface-ethernet-post-grouping0 {
      refine "vrrv3p-v3" {
        tailf:cli-diff-dependency "../../../../fhrp/version/vrrp" {
          tailf:xpath-root 3;
        }
      }
    }
  }

  grouping interface-pointtopoint-grouping {
    container encapsulation-pointtopoint {
      tailf:cli-drop-node-name;
      container encapsulation {
        tailf:info
          "Set encapsulation type for an interface";
        container isl {
          tailf:info
            "Inter Switch Link - Virtual LAN encapsulation";
          tailf:cli-compact-syntax;
          tailf:cli-sequence-commands;
          leaf vlan-id {
            tailf:cli-drop-node-name;
            type uint16 {
              tailf:info
                "<1-4095>;;Virtual LAN Identifier.";
              range "1..4095";
            }
          }
        }
        container ppp {
          tailf:info
            "Point-to-Point protocol";
          presence "true";
        }
        container slip {
          tailf:info
            "Serial Line IP";
          presence "true";
        }
        container frame-relay {
          tailf:info
            "Frame Relay networks";
          tailf:cli-delete-when-empty;
          presence "true";
          leaf IETF {
            tailf:info
              "Use RFC1490/RFC2427 encapsulation";
            tailf:cli-full-command;
            type empty;
          }
          leaf MFR {
            tailf:info
              "Multilink Frame Relay bundle interface";
            tailf:cli-allow-join-with-value {
              tailf:cli-display-joined;
            }
            tailf:cli-full-command;
            tailf:non-strict-leafref {
              path "/ncs:devices/ncs:device/ncs:config/ios:interface/MFR/name" {
                tailf:xpath-root 3;
              }
            }
            type uint32 {
              tailf:info
                "<0-2147483647>;;MFR interface number";
            }
          }
        }
        container hdlc {
          tailf:cli-delete-when-empty;
          presence "true";
        }
      }
    }
    container dialer {
      tailf:info
        "Dial-on-demand routing (DDR) commands";
      container in-band {
        tailf:info
          "Set v.25bis dialing for interface";
        tailf:cli-delete-when-empty;
        presence "true";
        leaf parity {
          tailf:cli-drop-node-name;
          type enumeration {
            enum "no-parity" {
              tailf:info
                "No parity";
            }
            enum "odd-parity" {
              tailf:info
                "Odd parity";
            }
          }
        }
      }
      container idle-timeout {
        tailf:info
          "Specify idle timeout before disconnecting line";
        tailf:cli-compact-syntax;
        tailf:cli-sequence-commands {
          tailf:cli-reset-siblings;
        }
        leaf seconds {
          tailf:cli-drop-node-name;
          type uint32 {
            tailf:info
              "<0-2147483>;;Idle timeout before disconnecting a call";
          }
        }
        leaf direction {
          tailf:cli-drop-node-name;
          type enumeration {
            enum "either" {
              tailf:info
                "Reset idle timer based on both inbound and outbound traffic";
            }
            enum "inbound" {
              tailf:info
                "Reset idle timer based on inbound traffic only";
            }
          }
        }
      }
      leaf enable-timeout {
        tailf:info
          "Set length of time an interface stays down before it is available for dialing";
        type uint32 {
          tailf:info
            "<1-2147483>;;Enable timeout in seconds";
          range "1..2147483";
        }
      }
      leaf string {
        tailf:info
          "Specify telephone number to be passed to DCE device";
        type string {
          tailf:info
            "WORD;;Dialer string (quote strings containing #)";
        }
      }
      leaf pool {
        tailf:info
          "Specify dialer pool to be used";
        type uint8 {
          tailf:info
            "<1-255>;;Dialer pool number";
          range "1..8";
        }
      }
      container map {
        tailf:info
          "Define multiple dial-on-demand numbers";
        list ip {
          tailf:info
            "IP";
          tailf:cli-suppress-mode;
          tailf:cli-delete-when-empty;
          tailf:cli-compact-syntax;
          key "address";
          leaf address {
            type inet:ipv4-address {
              tailf:info
                "A.B.C.D;;Protocol specific address";
            }
          }
          leaf name {
            tailf:info
              "Map to a host";
            type string {
              tailf:info
                "WORD;;Hostname to map";
            }
          }
          leaf class {
            tailf:info
              "dialer map class";
            type string {
              tailf:info
                "WORD;;name of dialer map class";
            }
          }
        }
      }
      leaf watch-group {
        tailf:info
          "Assign interface to dialer-watch-list";
        type uint16 {
          tailf:info
            "<1-255>;;Dialer watch group number";
          range "1..255";
        }
        tailf:non-strict-leafref {
          path "/ncs:devices/ncs:device/ncs:config/ios:dialer/watch-list/id" {
            tailf:xpath-root 3;
          }
        }
      }
    }
    leaf dialer-group {
      tailf:info
        "Assign interface to dialer-list";
      type uint8 {
        tailf:info
          "<1-128>;;Dialer list number";
        range "1..128";
      }
    }
    container ppp {
      tailf:info
        "Point-to-Point Protocol";
      container mtu {
        tailf:info
          "PPP MTU configuration";
        leaf adaptive {
          tailf:info
            "Adapt MTU to peer's MRU";
          tailf:cli-diff-dependency "../../../dialer" {
            tailf:xpath-root 3;
          }
          type empty;
        }
      }
      container pfc {
        tailf:info
          "Options for Protocol Field Compression";
        leaf local {
          tailf:info
            "Specify use of PFC option in outbound Config-Requests";
          type enumeration {
            enum "forbid" {
              tailf:info
                "Do not include PFC option in our Config-Requests, ever";
            }
            enum "request" {
              tailf:info
                "Include PFC option in our Config-Requests";
            }
          }
        }
      }
      container acfc {
        tailf:info
          "Options for HDLC Address & Control Field Compression";
        leaf local {
          tailf:info
            "Specify use of ACFC option in outbound Config-Requests";
          type enumeration {
            enum "forbid" {
              tailf:info
                "Do not include ACFC option in our Config-Requests, ever";
            }
            enum "request" {
              tailf:info
                "Include ACFC option in our Config-Requests";
            }
          }
        }
        leaf remote {
          tailf:info
            "Specify handling of ACFC option in inbound Config-Requests";
          type enumeration {
            enum "apply" {
              tailf:info
                "Do ACFC if peer indicates it can receive such frames";
            }
            enum "ignore" {
              tailf:info
                "Accept ACFC option, but do not apply ACFC on outbound frames";
            }
            enum "reject" {
              tailf:info
                "Explicitly reject the ACFC option and disallow ACFC";
            }
          }
        }
      }
      leaf accounting {
        tailf:info
          "Set PPP network accounting method";
        type union {
          type string {
            tailf:info
              "WORD;;Named accounting list.";
          }
          type enumeration {
            enum "default" {
              tailf:info
                "The default accounting list.";
            }
          }
        }
      }
      container authentication {
        tailf:info
          "Set PPP link authentication method";
        tailf:cli-compact-syntax;
        tailf:cli-sequence-commands;
        leaf method {
          tailf:cli-drop-node-name;
          type enumeration {
            enum "chap" {
              tailf:info
                "Challenge Handshake Authentication Protocol (CHAP)";
            }
            enum "eap" {
              tailf:info
                "Extensible Authentication Protocol (EAP)";
            }
            enum "ms-chap" {
              tailf:info
                "Microsoft Challenge Handshake Authentication Protocol (MS-CHAP)";
            }
            enum "ms-chap-v2" {
              tailf:info
                "Microsoft CHAP Version 2 (MS-CHAP-V2)";
            }
            enum "pap" {
              tailf:info
                "Password Authentication Protocol (PAP)";
            }
          }
        }
        leaf list-name {
          tailf:cli-break-sequence-commands;
          tailf:cli-drop-node-name;
          type string {
            tailf:info
              "WORD;;Use an authentication list with this name";
          }
          tailf:cli-disallow-value "(callback)|(callin)|(callout)|(default)|(eap)|(ms-chap)|(ms-chap-v2)|(one-time)|(optional)|(pap)";
        }
        leaf chap {
          when "not(../method = 'chap')" {
            tailf:xpath-root 3;
            tailf:dependency "../method";
          }
          tailf:info
            "Challenge Handshake Authentication Protocol (CHAP)";
          type empty;
        }
        leaf callback {
          tailf:info
            "Authenticate remote on callback only";
          type empty;
        }
        leaf callin {
          tailf:info
            "Authenticate remote on incoming call only";
          type empty;
        }
        leaf callout {
          tailf:info
            "Authenticate remote on outgoing call only";
          type empty;
        }
        leaf default {
          tailf:info
            "Use the default authentication list";
          type empty;
        }
        leaf eap {
          when "not(../method = 'eap')" {
            tailf:xpath-root 3;
            tailf:dependency "../method";
          }
          tailf:info
            "Extensible Authentication Protocol (EAP)";
          type empty;
        }
        leaf ms-chap {
          when "not(../method = 'ms-chap')" {
            tailf:xpath-root 3;
            tailf:dependency "../method";
          }
          tailf:info
            "Microsoft Challenge Handshake Authentication Protocol (MS-CHAP)";
          type empty;
        }
        leaf ms-chap-v2 {
          when "not(../method = 'ms-chap-v2')" {
            tailf:xpath-root 3;
            tailf:dependency "../method";
          }
          tailf:info
            "Microsoft CHAP Version 2 (MS-CHAP-V2)";
          type empty;
        }
        leaf one-time {
          tailf:info
            "Allow use of username*OTP for one-time passwords";
          type empty;
        }
        leaf optional {
          tailf:info
            "Allow peer to refuse to authenticate";
          type empty;
        }
        leaf pap {
          when "not(../method = 'pap')" {
            tailf:xpath-root 3;
            tailf:dependency "../method";
          }
          tailf:info
            "Password Authentication Protocol (PAP)";
          type empty;
        }
      }
      leaf authorization {
        tailf:info
          "Set PPP network authorization method";
        type union {
          type string {
            tailf:info
              "WORD;;Named authorization list.";
          }
          type enumeration {
            enum "default" {
              tailf:info
                "The default authorization list.";
            }
          }
        }
      }
      container chap {
        tailf:info
          "Set CHAP authentication parameters";
        leaf hostname {
          tailf:info
            "Set alternate CHAP hostname";
          type string {
            tailf:info
              "WORD;;Alternate CHAP hostname";
          }
        }
        container password {
          tailf:info
            "Set default CHAP password";
          tailf:cli-compact-syntax;
          tailf:cli-sequence-commands;
          uses password-grouping;
        }
      }
      container ipcp {
        tailf:info
          "Set IPCP negotiation options";
        container address {
          tailf:info
            "Additional ipcp address options";
          tailf:cli-compact-syntax;
          leaf accept {
            tailf:info
              "Accept any non zero IP address from our peer";
            tailf:cli-full-command;
            type empty;
          }
          leaf proxy {
            tailf:info
              "Peer proxy IP address (XCONNECT)";
            tailf:cli-full-command;
            type inet:ipv4-address;
          }
          leaf request {
            tailf:info
              "Request any address from our peer";
            tailf:cli-full-command;
            type enumeration {
              enum "ignore" {
                tailf:info
                  "Ignore negotiated address";
              }
            }
          }
          leaf required {
            tailf:info
              "Disconnect peers with no IP address negotiated";
            tailf:cli-full-command;
            type empty;
          }
          leaf unique {
            tailf:info
              "Disconnect if peer IP address already in use";
            tailf:cli-full-command;
            type empty;
          }
        }
        container dns {
          tailf:info
            "Specify DNS negotiation options";
          tailf:cli-compact-syntax;
          tailf:cli-sequence-commands;
          choice dns-choice {
            case dns-address {
              leaf primary {
                tailf:cli-drop-node-name;
                type inet:ipv4-address {
                  tailf:info
                    "A.B.C.D;;Primary DNS IP address";
                }
              }
              leaf secondary {
                tailf:cli-drop-node-name;
                type inet:ipv4-address {
                  tailf:info
                    "A.B.C.D;;Secondary DNS IP address";
                }
              }
            }
            container request {
              tailf:info
                "Request server addresses from peer";
              tailf:cli-delete-when-empty;
              presence "true";
              leaf accept {
                tailf:info
                  "Accept any non zero DNS address";
                type empty;
              }
            }
          }
        }
      }
      container multilink {
        tailf:info
          "Make interface multilink capable";
        tailf:cli-display-separated;
        presence "true";
        leaf interleave {
          tailf:info
            "Allow interleaving of small packets with fragments";
          type empty;
        }
        container links {
          tailf:info
            "Specify the limits on the number of links in a bundle";
          container minimum {
            tailf:info
              "Minimum number of links desired in the bundle";
            tailf:cli-compact-syntax;
            tailf:cli-sequence-commands {
              tailf:cli-reset-all-siblings;
            }
            leaf minimum-value {
              tailf:cli-drop-node-name;
              type uint8 {
                tailf:info
                  "<1-255>;;Specify minimum desired number of links in a bundle";
              }
            }
            leaf mandatory {
              tailf:info
                "Disable network layer until minimum number of links is reach";
              type empty;
            }
          }
        }
        leaf group {
          tailf:info
            "Put interface in a multilink bundle";
          type uint32 {
            tailf:info
              "<1-2147483647>;;Multilink group number";
            range "1..2147483647";
          }
        }
        container fragment {
          tailf:info
            "Specify fragmentation parameters";
          leaf disable {
            tailf:info
              "Suppress multilink fragmentation when possible";
            tailf:cli-full-command;
            type empty;
          }
          leaf size {
            tailf:info
              "Specify the maximum size of a multilink fragment";
            type uint16 {
              tailf:info
                "<42-65535>;;Maximum fragment size in bytes";
              range "42..65535";
            }
          }
          container delay {
            tailf:info
              "Specify the maximum delay for each fragment";
            tailf:cli-compact-syntax;
            tailf:cli-sequence-commands {
              tailf:cli-reset-siblings;
            }
            leaf delay-value {
              tailf:cli-drop-node-name;
              type uint16 {
                tailf:info
                  "<0-1000>;;Delay in milliseconds";
                range "0..1000";
              }
            }
            leaf additional-delay-value {
              tailf:cli-drop-node-name;
              type uint16 {
                tailf:info
                  "<1-999>;;Additional delay in microseconds";
                range "1..999";
              }
            }
          }
        }
        leaf fragmentation {
          tailf:info
            "Enable/Disable multilink fragmentation";
          tailf:cli-full-command;
          tailf:cli-boolean-no;
          type boolean;
          default "true";
        }
        container queue {
          tailf:info
            "Specify link queuing parameters";
          container depth {
            tailf:info
              "Specify maximum depth for link transmit queues";
            leaf fifo {
              tailf:info
                "Set max depth for link queues when bundle has FIFO queuing";
              type uint8 {
                tailf:info
                  "<2-255>;;Max queue depth for link";
                range "2..255";
              }
            }
            leaf qos {
              tailf:info
                "Set max depth for link queues when bundle has non-FIFO queuing";
              type uint8 {
                tailf:info
                  "<2-255>;;Max queue depth for link";
                range "2..255";
              }
            }
          }
        }
        container min-links {
          tailf:cli-compact-syntax;
          tailf:cli-sequence-commands {
            tailf:cli-reset-siblings;
          }
          leaf links {
            tailf:cli-drop-node-name;
            type uint8;
          }
          leaf mandatory {
            type empty;
          }
        }
      }
    }
    leaf multilink-group {
      tailf:info
        "Put interface in a multilink bundle";
      type uint32 {
        tailf:info
          "<1-2147483647>;;Multilink group number";
        range "1..2147483647";
      }
    }
    leaf physical-layer {
      tailf:info
        "Configure sync or async physical layer on serial interface";
      type enumeration {
        enum "async" {
          tailf:info
            "Configure asynchronous physical layer on serial interface";
        }
        enum "sync" {
          tailf:info
            "Configure synchronous physical layer on serial interface";
        }
      }
    }
    container async {
      tailf:info
        "Async interface parameters";
      container mode {
        tailf:info
          "Specify line mode (interactive or dedicated interface use)";
        leaf dedicated {
          tailf:info
            "Line is dedicated as an async interface";
          type empty;
        }
        leaf interactive {
          tailf:info
            "Line may be switched between interactive use and async interface";
          type empty;
        }
      }
    }
    container pulse-time {
      tailf:info
        "Force DTR low during resets";
      choice pulse-time-choice {
        leaf seconds {
          tailf:cli-drop-node-name;
          type uint8 {
            tailf:info
              "<0-60>;;DTR low time in seconds";
            range "0..60";
          }
        }
        leaf msec {
          tailf:info
            "millisecond (resolution)";
          type uint16 {
            tailf:info
              "<1-59999>;;DTR low time in milliseconds";
            range "1..59999";
          }
        }
      }
    }
    container serial {
      tailf:info
        "serial interface commands";
      container restart-delay {
        tailf:info
          "Configure serial interface restart-delay";
        tailf:cli-compact-syntax;
        tailf:cli-sequence-commands {
          tailf:cli-reset-siblings;
        }
        leaf seconds {
          tailf:cli-drop-node-name;
          type uint16 {
            tailf:info
              "<0-900>;;Restart delay (seconds)";
            range "0..900";
          }
        }
        leaf milliseconds {
          tailf:cli-drop-node-name;
          type uint16 {
            tailf:info
              "<0-999>;;Restart delay (milliseconds)";
            range "0..999";
          }
        }
      }
    }
  }

  grouping interface-switch-grouping0 {
    container switchport {
      tailf:info
        "Set switching mode characteristics";
      tailf:cli-display-separated;
      tailf:cli-recursive-delete;
      tailf:cli-show-no;
      presence "true";
      tailf:callpoint interface-switchport-hook {
        tailf:set-hook node;
      }
      tailf:cli-diff-dependency "../ip/address" {
        tailf:xpath-root 3;
        tailf:cli-trigger-on-set;
      }
      tailf:cli-diff-dependency "../ip/no-address/address" {
        tailf:xpath-root 3;
        tailf:cli-trigger-on-set;
      }
      tailf:cli-diff-dependency "../ip/redirects" {
        tailf:xpath-root 3;
        tailf:cli-trigger-on-set;
      }
      tailf:cli-diff-dependency "../ip/ospf" {
        tailf:xpath-root 3;
        tailf:cli-trigger-on-set;
      }
      tailf:cli-diff-dependency "../standby" {
        tailf:xpath-root 3;
        tailf:cli-trigger-on-set;
      }
      tailf:cli-diff-dependency "../service-policy/output" {
        tailf:xpath-root 3;
        tailf:cli-trigger-on-set;
      }
      tailf:cli-diff-dependency "../service-policy/input" {
        tailf:xpath-root 3;
        tailf:cli-trigger-on-set;
      }
      tailf:cli-diff-dependency "../udld" {
        tailf:xpath-root 3;
        tailf:cli-trigger-on-set;
      }
      tailf:meta-data "inject-interface-config-sp-input" {
        tailf:meta-value "service-policy/input :: service-policy input :: after :: any";
      }
      tailf:meta-data "inject-interface-config-sp-output" {
        tailf:meta-value "service-policy/output :: service-policy output :: after :: any";
      }
      tailf:meta-data "inject-interface-config-lacp-rate" {
        tailf:meta-value "lacp/rate :: lacp rate :: after :: any";
      }
      tailf:ned-data "../service-policy" {
        tailf:xpath-root 3;
        tailf:transaction to;
      }
      tailf:ned-data "../lacp/rate" {
        tailf:xpath-root 3;
        tailf:transaction to;
      }
      container mode {
        tailf:info
          "Set trunking mode of the interface";
        choice mode-choice {
          container access {
            tailf:info
              "Set trunking mode to ACCESS unconditionally";
            presence "true";
          }
          container dot1q-tunnel {
            tailf:info
              "set trunking mode to TUNNEL unconditionally";
            presence "true";
          }
          leaf dynamic {
            tailf:info
              "Set trunking mode to dynamically negotiate access or trunk mode";
            tailf:cli-diff-dependency "../../nonegotiate" {
              tailf:xpath-root 3;
              tailf:cli-trigger-on-set;
            }
            tailf:cli-diff-dependency "../../port-security" {
              tailf:xpath-root 3;
              tailf:cli-trigger-on-set;
            }
            type enumeration {
              enum "auto" {
                tailf:info
                  "Set trunking mode dynamic negotiation parameter to AUTO";
              }
              enum "desirable" {
                tailf:info
                  "Set trunking mode dynamic negotiation parameter to DESIRABLE";
              }
            }
          }
          container trunk {
            tailf:info
              "Set trunking mode to TRUNK unconditionally";
            tailf:cli-diff-dependency "../../trunk/encapsulation" {
              tailf:xpath-root 3;
              tailf:cli-trigger-on-set;
            }
            presence "true";
          }
          container private-vlan {
            tailf:info
              "Set private-vlan mode";
            choice private-vlan-choice {
              leaf host {
                tailf:info
                  "Set the mode to private-vlan host";
                type empty;
              }
              leaf promiscuous {
                tailf:info
                  "Set the mode to private-vlan promiscuous";
                type empty;
              }
              container trunk {
                tailf:info
                  "Set the mode to private-vlan trunk";
                presence "true";
              }
            }
          }
        }
      }
      container trunk {
        tailf:info
          "Set trunking characteristics of the interface";
        leaf encapsulation {
          tailf:info
            "Set encapsulation format on trunk port";
          tailf:cli-diff-dependency "../../mode/dynamic" {
            tailf:xpath-root 3;
            tailf:cli-trigger-on-set;
          }
          type enumeration {
            enum "dot1q" {
              tailf:info
                "Interface uses only 802.1q trunking encapsulation when trunking";
            }
            enum "isl" {
              tailf:info
                "Interface uses only ISL trunking encapsulation when trunking";
            }
            enum "negotiate" {
              tailf:info
                "Device will negotiate trunking encapsulation with peer on interface";
            }
          }
          default "negotiate";
        }
        container native {
          tailf:info
            "Set trunking native characteristics when interface is in trunking mode";
          leaf vlan {
            tailf:info
              "Set native VLAN when interface is in trunking mode";
            type union {
              type enumeration {
                enum "tag" {
                  tailf:info
                    "Set native VLAN tagging state";
                }
              }
              type uint16 {
                tailf:info
                  "<1-4094>;;VLAN ID of the native VLAN when this port is in trunking mode";
                range "1..4094";
              }
            }
          }
        }
        container allowed {
          tailf:info
            "Set allowed VLAN characteristics when interface is in trunking mode";
          container vlan {
            tailf:info
              "Set allowed VLANs when interface is in trunking mode";
            tailf:cli-delete-when-empty;
            tailf:cli-display-separated;
            tailf:cli-incomplete-command;
            presence "true";
            choice vlan-choice {
              leaf-list vlans {
                tailf:cli-drop-node-name;
                tailf:cli-range-list-syntax;
                tailf:cli-diff-dependency "../../../../mode" {
                  tailf:xpath-root 3;
                }
                tailf:cli-diff-dependency "../../vlan" {
                  tailf:xpath-root 3;
                }
                type uint16 {
                  tailf:info
                    "WORD;;VLAN IDs of the allowed VLANs when this port is in trunking mode";
                  range "1..4094";
                }
              }
              leaf none {
                tailf:info
                  "no VLANs";
                type empty;
              }
            }
          }
        }
        container pruning {
          tailf:info
            "Set pruning VLAN characteristics when interface is in trunking mode";
          container vlan {
            tailf:info
              "Set VLANs enabled for pruning when interface is in trunking mode";
            choice vlan-choice {
              leaf-list vlans {
                tailf:cli-drop-node-name;
                tailf:cli-range-list-syntax;
                tailf:cli-replace-all;
                type uint16 {
                  tailf:info
                    "WORD;;VLAN IDs of the allowed VLANs when this port is in trunking mode";
                  range "1..4094";
                }
              }
              leaf none {
                tailf:info
                  "no VLANs";
                type empty;
              }
            }
          }
        }
      }
      container autostate {
        tailf:info
          "Include or exclude this port from vlan link up calculation";
        leaf exclude {
          tailf:info
            "Exclude this port from vlan link up calculation";
          type empty;
        }
      }
      container private-vlan {
        tailf:info
          "Set the private VLAN configuration";
        container trunk {
          tailf:info
            "Set the private vlan trunking configuration";
          container native {
            tailf:info
              "Set the private vlan trunking native configuration";
            leaf vlan {
              tailf:info
                "Set native VLAN configuration";
              type union {
                type enumeration {
                  enum "tag" {
                    tailf:info
                      "Set native VLAN tagging state";
                  }
                }
                type uint16 {
                  tailf:info
                    "<1-4094>;;VLAN ID of the native VLAN when this port is in trunking mode";
                  range "1..4094";
                }
              }
            }
          }
          container allowed {
            tailf:info
              "Set allowed VLAN characteristics when interface is in private-vlan trunking mode";
            container vlan {
              tailf:info
                "Set allowed VLANs when interface is in private-vlan trunking mode";
              choice vlan-choice {
                leaf-list vlans {
                  tailf:cli-replace-all;
                  tailf:cli-range-list-syntax;
                  tailf:cli-drop-node-name;
                  type uint16 {
                    tailf:info
                      "WORD;;VLAN IDs of the allowed VLANs when interface is in private-vlan trunking mode";
                    range "1..4094";
                  }
                }
                leaf none {
                  tailf:info
                    "no VLANs";
                  type empty;
                }
              }
            }
          }
        }
        container association {
          tailf:info
            "Set the private VLAN association";
          list trunk {
            tailf:cli-suppress-mode;
            tailf:cli-delete-when-empty;
            tailf:cli-incomplete-command;
            key "primary-vlan-id";
            leaf primary-vlan-id {
              type uint16 {
                tailf:info
                  "<2-4094>;;Primary VLAN ID of the private VLAN trunk association";
                range "2..4094";
              }
            }
            leaf secondary-vlan-id {
              tailf:cli-drop-node-name;
              type uint16 {
                tailf:info
                  "<2-4094>;;Secondary VLAN ID of the private VLAN port/trunk association";
                range "2..4094";
              }
            }
          }
        }
      }
      container access {
        tailf:info
          "Set access mode characteristics of the interface";
        leaf vlan {
          tailf:info
            "Set VLAN when interface is in access mode";
          tailf:cli-diff-dependency "../../../service/instance" {
            tailf:xpath-root 3;
            tailf:cli-trigger-on-set;
          }
          type union {
            type uint16 {
              tailf:info
                "<1-4094>;;VLAN ID of the VLAN when this port is in access mode";
              range "1..4094";
            }
            type enumeration {
              enum "dynamic" {
                tailf:info
                  "When in access mode, this interfaces VLAN is controlled by VMPS";
              }
            }
          }
          default "1";
        }
      }
      container backup {
        tailf:info
          "Set backup for the interface";
        list interface {
          tailf:info
            "Specify an interface as backup";
          tailf:cli-suppress-mode;
          tailf:cli-delete-when-empty;
          key "name";
          leaf name {
            type string {
              tailf:info
                "WORD;;Interface Name";
            }
          }
          container preemption {
            tailf:info
              "preemption parameters";
            leaf mode {
              tailf:info
                "set the preemption mode";
              type enumeration {
                enum "bandwidth" {
                  tailf:info
                    "higher bandwidth interface preferred";
                }
                enum "forced" {
                  tailf:info
                    "active interface preferred";
                }
                enum "off" {
                  tailf:info
                    "turn off preemption";
                }
              }
            }
            leaf delay {
              tailf:info
                "preemption parameters";
              type uint16 {
                tailf:info
                  "<1-300>;;preemption delay in seconds";
                range "1..300";
              }
            }
          }
        }
      }
      leaf nonegotiate {
        tailf:info
          "Device will not engage in negotiation protocol on this interface";
        tailf:cli-diff-dependency "../trunk" {
          tailf:xpath-root 3;
        }
        tailf:cli-diff-dependency "../mode/trunk" {
          tailf:xpath-root 3;
        }
        tailf:cli-diff-dependency "../mode/access" {
          tailf:xpath-root 3;
        }
        type empty;
      }
      container block {
        tailf:info
          "Disable forwarding of unknown uni/multi cast addresses";
        leaf multicast {
          tailf:info
            "Block unknown multicast addresses";
          tailf:cli-full-command;
          type empty;
        }
        leaf unicast {
          tailf:cli-full-command;
          tailf:info
            "Block unknown unicast addresses";
          type empty;
        }
      }
      container port-security {
        tailf:info
          "Security related command";
        tailf:cli-display-separated;
        tailf:cli-diff-dependency "../mode/access" {
          tailf:xpath-root 3;
        }
        tailf:cli-diff-dependency "../mode/trunk" {
          tailf:xpath-root 3;
        }
        presence "true";
        container aging {
          tailf:info
            "Port-security aging commands";
          leaf time {
            tailf:info
              "Port-security aging time";
            type uint16 {
              tailf:info
                "<1-1440>;;Aging time in minutes. Enter a value between 1 and 1440";
              range "1..1440";
            }
          }
          leaf type {
            tailf:info
              "Port-security aging type";
            type enumeration {
              enum "absolute" {
                tailf:info
                  "Absolute aging (default)";
              }
              enum "inactivity" {
                tailf:info
                  "Aging based on inactivity time period";
              }
            }
          }
        }
        container mac-address {
          tailf:info
            "Secure mac address";
          tailf:cli-compact-syntax;
          tailf:cli-sequence-commands {
            tailf:cli-reset-siblings;
          }
          leaf sticky {
            tailf:info
              "Configure dynamic secure addresses as sticky";
            tailf:cli-optional-in-sequence;
            type empty;
          }
          leaf hw-address {
            tailf:cli-drop-node-name;
            type yang:mac-address {
              tailf:info
                "H.H.H;;48 bit mac address";
            }
          }
          leaf vlan {
            tailf:info
              "set VLAN ID of the VLAN on which this address can be learned";
            type uint16 {
              tailf:info
                "<1-4094>;;VLAN ID on which this address can be learned";
              range "1..4094";
            }
          }
        }
        leaf maximum {
          tailf:info
            "Max secure addresses";
          tailf:cli-no-value-on-delete;
          tailf:cli-full-command;
          type uint16 {
            tailf:info
              "<1-8192>;;Maximum addresses";
            range "1..8192";
          }
        }
        container maximum-vlan {
          tailf:cli-drop-node-name;
          tailf:cli-compact-syntax;
          tailf:cli-sequence-commands {
            tailf:cli-reset-siblings;
          }
          leaf maximum {
            tailf:cli-no-value-on-delete;
            tailf:cli-incomplete-command;
            type uint16 {
              tailf:info
                "<1-8192>;;Maximum addresses";
              range "1..8192";
            }
          }
          leaf vlan {
            tailf:info
              "Max secure addresses per vlan";
            type empty;
          }
        }
        container maximum-vlan-list {
          tailf:cli-drop-node-name;
          list maximum {
            tailf:cli-suppress-mode;
            tailf:cli-delete-when-empty;
            tailf:cli-compact-syntax;
            tailf:cli-sequence-commands {
              tailf:cli-reset-siblings;
            }
            key "max-addresses vlan";
            leaf max-addresses {
              type uint16 {
                tailf:info
                  "<1-8192>;;Maximum addresses";
                range "1..8192";
              }
            }
            leaf vlan {
              tailf:info
                "Max secure addresses per vlan";
              tailf:cli-expose-key-name;
              type string {
                tailf:info
                  "WORD;;VLAN IDs to which this maximum applies";
              }
            }
          }
        }
        leaf violation {
          tailf:info
            "Security violation mode";
          type enumeration {
            enum "protect" {
              tailf:info
                "Security violation protect mode";
            }
            enum "restrict" {
              tailf:info
                "Security violation restrict mode";
            }
            enum "shutdown" {
              tailf:info
                "Security violation shutdown mode";
            }
          }
        }
      }
      container priority {
        tailf:info
          "Set appliance 802.1p priority";
        tailf:cli-incomplete-command;
        container extend {
          tailf:info
            "Set appliance 802.1p priority";
          tailf:cli-incomplete-command;
          choice trust-choice {
            leaf trust {
              tailf:cli-full-command;
              tailf:info
                "Trust 802.1p priorities of devices on appliance";
              type empty;
            }
            leaf cos {
              tailf:info
                "Override 802.1p priority of devices on appliance";
              tailf:cli-full-command;
              type uint8 {
                tailf:info
                  "<0-7>;;Priority for devices on appliance";
                range "0..7";
              }
            }
          }
        }
      }
      leaf protected {
        tailf:info
          "Configure an interface to be a protected port";
        type empty;
      }
      container voice {
        tailf:info
          "Voice appliance attributes";
        leaf vlan {
          tailf:info
            "Vlan for voice traffic";
          type union {
            type enumeration {
              enum "dot1p" {
                tailf:info
                  "Priority tagged on PVID";
              }
              enum "none" {
                tailf:info
                  "Don't tell telephone about voice vlan";
              }
              enum "untagged" {
                tailf:info
                  "Untagged on PVID";
              }
            }
            type uint16 {
              tailf:info
                "<1-4094>;;Vlan for voice traffic";
              range "1..4094";
            }
          }
        }
        container detect {
          tailf:info
            "detection enhancement keyword";
          tailf:cli-incomplete-command;
          container cisco-phone {
            tailf:info
              "Cisco IP phone";
            presence "true";
            leaf full-duplex {
              tailf:info
                "full duplex keyword";
              type empty;
            }
          }
        }
      }
      leaf host {
        tailf:info
          "Set port host";
        type empty;
      }
    }
    container l2protocol-tunnel {
      tailf:info
        "Tunnel Layer2 protocols";
      tailf:cli-delete-when-empty;
      tailf:cli-diff-dependency "../switchport" {
        tailf:xpath-root 3;
      }
      presence "true";
      leaf cdp {
        tailf:info
          "Cisco Discovery Protocol";
        type empty;
      }
      container drop-threshold {
        tailf:info
          "Set drop threshold for protocol packets";
        leaf packet-rate {
          tailf:cli-drop-node-name;
          type uint16 {
            tailf:info
              "<1-4096>;;Packets/sec rate beyond which protocol packets will be dropped";
            range "1..4096";
          }
        }
        leaf cdp {
          tailf:info
            "Cisco Discovery Protocol";
          type uint16 {
            tailf:info
              "<1-4096>;;Packets/sec rate beyond which protocol packets will be dropped";
            range "1..4096";
          }
        }
        leaf stp {
          tailf:info
            "Spanning Tree Protocol";
          type uint16 {
            tailf:info
              "<1-4096>;;Packets/sec rate beyond which protocol packets will be dropped";
            range "1..4096";
          }
        }
        leaf vtp {
          tailf:info
            "Vlan Trunking Protocol";
          type uint16 {
            tailf:info
              "<1-4096>;;Packets/sec rate beyond which protocol packets will be dropped";
            range "1..4096";
          }
        }
      }
      container shutdown-threshold {
        tailf:info
          "Set shutdown threshold for protocol packets";
        leaf packet-rate {
          tailf:cli-drop-node-name;
          type uint16 {
            tailf:info
              "<1-4096>;;Packets/sec rate beyond which interface is put to err-disable";
            range "1..4096";
          }
        }
        leaf cdp {
          tailf:info
            "Cisco Discovery Protocol";
          type uint16 {
            tailf:info
              "<1-4096>;;Packets/sec rate beyond which interface is put to err-disable";
            range "1..4096";
          }
        }
        leaf stp {
          tailf:info
            "Spanning Tree Protocol";
          type uint16 {
            tailf:info
              "<1-4096>;;Packets/sec rate beyond which interface is put to err-disable";
            range "1..4096";
          }
        }
        leaf vtp {
          tailf:info
            "Vlan Trunking Protocol";
          type uint16 {
            tailf:info
              "<1-4096>;;Packets/sec rate beyond which interface is put to err-disable";
            range "1..4096";
          }
        }
        leaf lldp {
          tailf:info
            "Link Layer Discovery Protocol";
          type uint16 {
            tailf:info
              "<1-4096>;;Packets/sec rate beyond which interface is put to err-disable";
            range "1..4096";
          }
        }
      }
      leaf stp {
        tailf:info
          "Spanning Tree Protocol";
        type empty;
      }
      leaf vtp {
        tailf:info
          "Vlan Trunking Protocol";
        type empty;
      }
      leaf lldp {
        tailf:info
          "Link Layer Discovery Protocol";
        type empty;
      }
      container point-to-point {
        tailf:info
          "point-to-point L2 Protocol";
        leaf lacp {
          tailf:info
            "Link Aggregation Control Protocol";
          type empty;
        }
        leaf pagp {
          tailf:info
            "Port Aggregation Protocol";
          type empty;
        }
        leaf udld {
          tailf:info
            "Unidirectional Link Detection";
          type empty;
        }
      }
    }
  }

  grouping interface-switch-grouping {
    uses interface-switch-grouping0 {
      refine "switchport" {
        tailf:cli-diff-dependency "../../../vlan/vlan-list" {
          tailf:xpath-root 3;
        }
      }
    }
  }

  grouping sub-interface-switch-grouping {
    uses interface-switch-grouping0 {
      refine "switchport" {
        tailf:cli-diff-dependency "../../../../vlan/vlan-list" {
          tailf:xpath-root 3;
        }
      }
    }
  }

  grouping crypto-pki-token-grouping {
    container removal {
      tailf:info
        "actions to take after token removal";
      leaf timeout {
        tailf:info
          "seconds after token removal at which keys from the token are cleared";
        type uint16 {
          tailf:info
            "<0-480>;;Token key timeout in seconds";
          range "0..480";
        }
      }
    }
  }

  grouping router-bgp-max-path-grouping {
    container paths {
      tailf:cli-drop-node-name;
      tailf:cli-compact-syntax;
      tailf:cli-sequence-commands {
        tailf:cli-reset-siblings;
      }
      leaf number-of-paths {
        tailf:cli-drop-node-name;
        type uint16 {
          tailf:info
            "<1-16>;;Number of paths";
          range "1..16";
        }
        default "1";
      }
      leaf import {
        tailf:info
          "Maximum import paths";
        type uint16 {
          tailf:info
            "<1-16>;;Number of import paths";
          range "1..16";
        }
      }
    }
  }

  grouping router-bgp-redistribute-isis-grouping {
    choice osi-ip-choice {
      leaf ip {
        tailf:info
          "Redistribution of IP dynamic routes";
        tailf:cli-no-name-on-delete;
        tailf:cli-no-value-on-delete;
        tailf:cli-remove-before-change;
        type empty;
      }
      leaf clns {
        tailf:info
          "Redistribution of OSI dynamic routes";
        tailf:cli-no-name-on-delete;
        tailf:cli-no-value-on-delete;
        tailf:cli-remove-before-change;
        type empty;
      }
    }
    leaf level {
      tailf:cli-drop-node-name;
      tailf:cli-no-name-on-delete;
      tailf:cli-no-value-on-delete;
      type enumeration {
        enum "level-1" {
          tailf:info
            "IS-IS level-1 routes only";
        }
        enum "level-2" {
          tailf:info
            "IS-IS level-2 routes only";
        }
        enum "level-1-2" {
          tailf:info
            "IS-IS level-1 and level-2 routes";
        }
      }
    }
  }

  grouping router-bgp-redistribute-grouping {
    leaf metric {
      tailf:info
        "Metric for redistributed routes";
      tailf:cli-no-name-on-delete;
      tailf:cli-no-value-on-delete;
      tailf:cli-remove-before-change;
      type uint32 {
        tailf:info
          "<0-4294967295>;;Default metric";
        range "0..4294967295";
      }
    }
    leaf subnets {
      tailf:info
        "Consider subnets for redistribution into BGP";
      tailf:cli-no-name-on-delete;
      tailf:cli-no-value-on-delete;
      type empty;
    }
    leaf route-map {
      tailf:info
        "Route map reference";
      tailf:cli-no-name-on-delete;
      tailf:cli-no-value-on-delete;
      type string {
        tailf:info
          "WORD;;Pointer to route-map entries";
      }
    }
    leaf include-connected {
      tailf:info
        "Include connected";
      tailf:cli-no-name-on-delete;
      tailf:cli-no-value-on-delete;
      type empty;
    }
  }

  grouping router-bgp-redistribute-ospf-grouping {
    leaf metric {
      tailf:info
        "Metric for redistributed routes";
      tailf:cli-no-name-on-delete;
      tailf:cli-no-value-on-delete;
      tailf:cli-remove-before-change;
      type uint32 {
        tailf:info
          "<0-4294967295>;;Default metric";
        range "0..4294967295";
      }
    }
    leaf subnets {
      tailf:info
        "Consider subnets for redistribution into BGP";
      tailf:cli-no-name-on-delete;
      tailf:cli-no-value-on-delete;
      type empty;
    }
    leaf route-map {
      tailf:info
        "Route map reference";
      tailf:cli-no-name-on-delete;
      tailf:cli-no-value-on-delete;
      type string {
        tailf:info
          "WORD;;Pointer to route-map entries";
      }
    }
    leaf include-connected {
      tailf:info
        "Include connected";
      tailf:cli-no-name-on-delete;
      tailf:cli-no-value-on-delete;
      type empty;
    }
    leaf match {
      tailf:info
        "Redistribution of OSPF routes";
      tailf:cli-no-name-on-delete;
      tailf:cli-no-value-on-delete;
      tailf:cli-incomplete-command;
      type empty;
    }
    leaf internal {
      when "../match" {
        tailf:xpath-root 3;
        tailf:dependency "../match";
      }
      tailf:info
        "Redistribute OSPF internal routes";
      tailf:cli-no-name-on-delete;
      tailf:cli-no-value-on-delete;
      type empty;
    }
    container external-1 {
      when "../match" {
        tailf:xpath-root 3;
        tailf:dependency "../match";
      }
      tailf:cli-drop-node-name;
      tailf:cli-flatten-container;
      tailf:cli-compact-syntax;
      leaf external {
        tailf:info
          "Redistribute OSPF external routes";
        tailf:cli-no-name-on-delete;
        tailf:cli-no-value-on-delete;
        type enumeration {
          enum "1" {
            tailf:info
              "Redistribute external type 1 routes";
          }
        }
      }
    }
    container external-2 {
      when "../match" {
        tailf:xpath-root 3;
        tailf:dependency "../match";
      }
      tailf:cli-drop-node-name;
      tailf:cli-flatten-container;
      tailf:cli-compact-syntax;
      leaf external {
        tailf:info
          "Redistribute OSPF external routes";
        tailf:cli-no-name-on-delete;
        tailf:cli-no-value-on-delete;
        type enumeration {
          enum "2" {
            tailf:info
              "Redistribute external type 2 routes";
          }
        }
      }
    }
    container nssa-external-1 {
      when "../match" {
        tailf:xpath-root 3;
        tailf:dependency "../match";
      }
      tailf:cli-drop-node-name;
      tailf:cli-flatten-container;
      tailf:cli-compact-syntax;
      leaf nssa-external {
        tailf:info
          "Redistribute OSPF NSSA external routes";
        tailf:cli-no-name-on-delete;
        tailf:cli-no-value-on-delete;
        type enumeration {
          enum "1" {
            tailf:info
              "Redistribute NSSA external type 1 routes";
          }
        }
      }
    }
    container nssa-external-2 {
      when "../match" {
        tailf:xpath-root 3;
        tailf:dependency "../match";
      }
      tailf:cli-drop-node-name;
      tailf:cli-flatten-container;
      tailf:cli-compact-syntax;
      leaf nssa-external {
        tailf:info
          "Redistribute OSPF NSSA external routes";
        tailf:cli-no-name-on-delete;
        tailf:cli-no-value-on-delete;
        type enumeration {
          enum "2" {
            tailf:info
              "Redistribute NSSA external type 2 routes";
          }
        }
      }
    }
  }

  grouping route-map-metric-grouping {
    leaf route-map {
      tailf:info
        "Route map reference";
      type string {
        tailf:info
          "WORD;;Pointer to route-map entries";
      }
    }
    leaf metric {
      tailf:info
        "Metric for redistributed routes";
      type uint32 {
        tailf:info
          "<0-4294967295>;;Default metric";
        range "0..4294967295";
      }
    }
  }

  grouping router-bgp-neighbor-distribute-list-grouping {
    list distribute-list {
      tailf:info
        "Filter networks in routing updates";
      tailf:cli-suppress-mode;
      tailf:cli-delete-when-empty;
      tailf:cli-compact-syntax;
      tailf:cli-sequence-commands;
      tailf:cli-remove-before-change;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      key "direction";
      leaf direction {
        type enumeration {
          enum "in" {
            tailf:info
              "Filter incoming routing updates";
          }
          enum "out" {
            tailf:info
              "Filter outgoing routing updates";
          }
        }
      }
      uses distribute-list-content-grouping;
    }
    container distribute-list-interface {
      tailf:cli-drop-node-name;
      list distribute-list {
        tailf:info
          "Filter networks in routing updates";
        tailf:cli-suppress-mode;
        tailf:cli-delete-when-empty;
        tailf:cli-compact-syntax;
        tailf:cli-sequence-commands;
        tailf:cli-remove-before-change;
        tailf:cli-diff-dependency "../../inherit/peer-session" {
          tailf:xpath-root 3;
        }
        tailf:cli-diff-dependency "../../peer-group" {
          tailf:xpath-root 3;
        }
        tailf:cli-diff-dependency "../../remote-as" {
          tailf:xpath-root 3;
        }
        tailf:cli-diff-dependency "../../activate" {
          tailf:xpath-root 3;
        }
        key "direction interface";
        leaf direction {
          type enumeration {
            enum "in" {
              tailf:info
                "Filter incoming routing updates";
            }
            enum "out" {
              tailf:info
                "Filter outgoing routing updates";
            }
          }
        }
        leaf interface {
          tailf:cli-diff-dependency "/ios:interface" {
            tailf:xpath-root 3;
          }
          type string {
            tailf:info
              "WORD;;Interface name";
          }
        }
        uses distribute-list-content-grouping;
      }
    }
  }

  grouping router-bgp-peer-policy-grouping {
    leaf advertisement-interval {
      tailf:info
        "Minimum interval between sending BGP routing updates";
      tailf:cli-full-command;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      type uint16 {
        tailf:info
          "<0-600>;;time in seconds";
        range "0..600";
      }
    }
    leaf next-hop-self {
      tailf:info
        "Disable the next hop calculation for this neighbor";
      tailf:cli-full-command;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      type empty;
    }
    container aigp {
      tailf:cli-delete-when-empty;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      presence "true";
    }
    container send-community {
      tailf:info
        "Send Community attribute to this neighbor";
      tailf:cli-delete-when-empty;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      presence "true";
      leaf send-community-where {
        tailf:cli-drop-node-name;
        type enumeration {
          enum "both" {
            tailf:info
              "Send Standard and Extended Community attributes";
          }
          enum "extended" {
            tailf:info
              "Send Extended Community attribute";
          }
          enum "standard" {
            tailf:code-name "send_standard";
            tailf:info
              "Send Standard Community attribute";
          }
        }
      }
    }
    container send-label {
      tailf:info
        "Send NLRI + MPLS Label to this peer";
      tailf:cli-delete-when-empty;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      presence "true";
      leaf explicit-null {
        tailf:info
          "Advertise Explicit Null label in place of Implicit Null";
        type empty;
      }
    }
    container maximum-prefix {
      tailf:info
        "Maximum number of prefixes accepted from this peer";
      tailf:cli-compact-syntax;
      tailf:cli-sequence-commands {
        tailf:cli-reset-all-siblings;
      }
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      leaf max-prefix-no {
        tailf:cli-drop-node-name;
        type uint32 {
          tailf:info
            "<1-2147483647>;;maximum no. of prefix limit";
          range "1..2147483647";
        }
      }
      leaf threshold {
        tailf:cli-drop-node-name;
        tailf:cli-break-sequence-commands;
        type uint8 {
          tailf:info
            "<1-100>;;Threshold value (%) at which to generate a warning msg";
          range "1..100";
        }
      }
      leaf restart {
        tailf:cli-full-command;
        tailf:info
          "Restart bgp connection after limit is exceeded";
        type uint16 {
          tailf:info
            "<1-65535>;;Restart interval in minutes";
          range "1..65535";
        }
      }
      leaf warning-only {
        tailf:cli-full-command;
        tailf:info
          "Only give warning message when limit is exceeded";
        type empty;
      }
    }
    container allowas-in {
      tailf:info
        "Accept as-path with my AS present in it";
      tailf:cli-delete-when-empty;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      presence "true";
      leaf as-no {
        tailf:cli-drop-node-name;
        type uint8 {
          tailf:info
            "<1-10>;;Number of occurances of AS number";
          range "1..10";
        }
      }
    }
    container as-override {
      tailf:info
        "Override matching AS-number while sending update";
      tailf:cli-delete-when-empty;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      presence "true";
      leaf disable {
        type empty;
      }
    }
    list route-map {
      tailf:info
        "Apply route map to neighbor";
      tailf:cli-suppress-mode;
      tailf:cli-delete-when-empty;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      key "direction";
      leaf direction {
        type enumeration {
          enum "in" {
            tailf:info
              "Apply map to incoming routes";
          }
          enum "out" {
            tailf:info
              "Apply map to outbound routes";
          }
        }
      }
      leaf route-map-name {
        tailf:cli-drop-node-name;
        tailf:cli-prefix-key;
        type string {
          tailf:info
            "WORD;;Name of route map";
        }
      }
    }
    list advertise-map {
      tailf:info
        "Apply advertise map to neighbor";
      tailf:cli-suppress-mode;
      tailf:cli-delete-when-empty;
      tailf:cli-incomplete-command;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      key "name";
      leaf name {
        type string {
          tailf:info
            "WORD;;Name of route map";
        }
      }
      list exist-map {
        tailf:info
          "advertise prefix only if prefix is in the condition exists";
        tailf:cli-suppress-mode;
        tailf:cli-delete-when-empty;
        key "name";
        leaf name {
          type string {
            tailf:info
              "WORD;;condition route-map name";
          }
        }
      }
    }
    container default-originate {
      tailf:info
        "Originate default route to this neighbour";
      tailf:cli-delete-when-empty;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      presence "true";
      leaf route-map {
        tailf:info
          "Route-map to specify criteria to originate default";
        type string {
          tailf:info
            "WORD;;route-map name";
        }
      }
    }
    list prefix-list {
      tailf:info
        "Filter updates to/from this neighbor";
      tailf:cli-suppress-mode;
      tailf:cli-delete-when-empty;
      tailf:cli-compact-syntax;
      tailf:cli-sequence-commands;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      key "direction";
      leaf direction {
        type enumeration {
          enum "in" {
            tailf:info
              "Filter incoming updates";
          }
          enum "out" {
            tailf:info
              "Filter outgoing updates";
          }
        }
      }
      leaf prefix-list-name {
        tailf:cli-drop-node-name;
        tailf:cli-prefix-key;
        tailf:non-strict-leafref {
          path "/ncs:devices/ncs:device/ncs:config/ios:ip/prefix-list/prefixes/name" {
            tailf:xpath-root 3;
          }
        }
        type string {
          tailf:info
            "WORD;;Name of a prefix list";
        }
      }
    }
    leaf route-reflector-client {
      tailf:info
        "Configure a neighbor as Route Reflector client";
      tailf:cli-full-command;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      type empty;
    }
    leaf soft-reconfiguration {
      tailf:info
        "Per neighbor soft reconfiguration";
      tailf:cli-full-command;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      type enumeration {
        enum "inbound" {
          tailf:info
            "Allow inbound soft reconfiguration for this neighbor";
        }
      }
    }
    container remove-private-as {
      tailf:info
        "Remove private AS number from outbound updates";
      tailf:cli-compact-syntax;
      tailf:cli-sequence-commands {
        tailf:cli-reset-siblings;
      }
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      presence "true";
      leaf all {
        tailf:info
          "Remove all private AS numbers";
        type empty;
      }
      leaf replace-as {
        tailf:info
          "Replace all private AS numbers with local AS";
        type empty;
      }
    }
  }

  grouping router-bgp-peer-session-grouping {
    container local-as {
      tailf:info
        "Specify a local-as number";
      tailf:cli-compact-syntax;
      tailf:cli-sequence-commands {
        tailf:cli-reset-siblings;
      }
      tailf:cli-delete-when-empty;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      presence "true";
      leaf as-no {
        tailf:cli-drop-node-name;
        type bgp-as-no-type;
      }
      leaf no-prepend {
        tailf:info
          "Do not prepend local-as to updates from ebgp peers";
        type empty;
      }
      leaf replace-as {
        tailf:info
          "Replace real AS with local AS in the EBGP updates";
        type empty;
      }
      leaf dual-as {
        tailf:info
          "Accept either real AS or local AS from the ebgp peer";
        type empty;
      }
    }
    container password {
      tailf:info
        "Set a password";
      tailf:cli-compact-syntax;
      tailf:cli-sequence-commands {
        tailf:cli-reset-siblings;
      }
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      leaf enctype {
        tailf:cli-drop-node-name;
        tailf:cli-optional-in-sequence;
        tailf:cli-incomplete-command;
        type uint8 {
          tailf:info
            "<0-7>;;Encryption type (0 to disable encryption, 7 for proprietary)";
          range "0..7";
        }
        default "0";
      }
      leaf text {
        tailf:cli-drop-node-name;
        tailf:cli-multi-value;
        tailf:cli-full-command;
        tailf:cli-disallow-value "0|1|2|3|4|5|6|7";
        type string {
          tailf:info
            "LINE;;The password";
        }
      }
    }
    container ttl-security {
      tailf:info
        "BGP ttl security check";
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      leaf hops {
        tailf:info
          "IP hops";
        type uint8 {
          tailf:info
            "<1-254>;;maximum number of hops";
          range "1..254";
        }
      }
    }
    container timers {
      tailf:info
        "BGP per neighbor timers";
      tailf:cli-compact-syntax;
      tailf:cli-sequence-commands {
        tailf:cli-reset-siblings;
      }
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      leaf keepalive-interval {
        tailf:cli-drop-node-name;
        tailf:cli-incomplete-command;
        type uint16 {
          range "0..65535";
          tailf:info
            "<0-65535>;;Keepalive interval";
        }
      }
      leaf holdtime {
        tailf:cli-drop-node-name;
        type uint16 {
          tailf:info
            "<0-65535>;;Holdtime";
          range "0..65535";
        }
      }
      leaf minimum-neighbor-hold {
        tailf:cli-drop-node-name;
        type uint16 {
          tailf:info
            "<0-65535>;;Minimum hold time from neighbor";
          range "0..65535";
        }
      }
    }
    container fall-over {
      tailf:info
        "session fall on peer route lost";
      tailf:cli-delete-when-empty;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      presence "true";
      leaf route-map {
        tailf:info
          "Route map for peer route";
        type string {
          tailf:info
            "WORD;;Name of the route map";
        }
      }
    }
    container fall-over-bfd {
      tailf:cli-drop-node-name;
      container fall-over {
        tailf:info
          "session fall on peer route lost";
        tailf:cli-incomplete-command;
        tailf:cli-incomplete-no;
        tailf:cli-diff-dependency "../../inherit/peer-session" {
          tailf:xpath-root 3;
        }
        tailf:cli-diff-dependency "../../peer-group" {
          tailf:xpath-root 3;
        }
        tailf:cli-diff-dependency "../../remote-as" {
          tailf:xpath-root 3;
        }
        tailf:cli-diff-dependency "../../activate" {
          tailf:xpath-root 3;
        }
        tailf:cli-diff-dependency "../../fall-over" {
          tailf:xpath-root 3;
        }
        leaf bfd {
          tailf:info
            "Use BFD to detect failure";
          type empty;
        }
      }
    }
    container ebgp-multihop {
      tailf:info
        "Allow EBGP neighbors not on directly connected networks";
      tailf:cli-delete-when-empty;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      presence "true";
      leaf max-hop {
        tailf:cli-drop-node-name;
        type uint8 {
          tailf:info
            "<1-255>;;maximum hop count";
          range "1..255";
        }
      }
    }
    container update-source {
      tailf:info
        "Source of routing updates";
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      uses interface-name-grouping;
    }
    container path-attribute {
      tailf:info
        "BGP optional attribute filtering";
      list discard {
        tailf:info
          "Discard matching path-attribute for this neighbor";
        tailf:cli-suppress-mode;
        tailf:cli-delete-when-empty;
        tailf:cli-incomplete-command;
        key "id";
        leaf id {
          type uint8 {
            tailf:info
              "<1-255>;;path attribute type";
            range "1..255";
          }
        }
        leaf in {
          tailf:info
            "Perform inbound path-attribute filtering";
          type empty;
        }
      }
    }
    leaf version {
      tailf:info
        "Set the BGP version to match a neighbor";
      tailf:cli-full-command;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      type uint8 {
        tailf:info
          "<4-4>;;Neighbor's BGP version";
        range "4";
      }
    }
    container transport {
      tailf:info
        "Transport options";
      leaf connection-mode {
        tailf:info
          "Specify passive or active connection";
        type enumeration {
          enum "active" {
            tailf:info
              "Actively establish the TCP session";
          }
          enum "passive" {
            tailf:info
              "Passively establish the TCP session";
          }
        }
      }
      container path-mtu-discovery {
        tailf:info
          "Use transport path MTU discovery";
        tailf:cli-delete-when-empty;
        presence "true";
        leaf disable {
          tailf:info
            "disable";
          type empty;
        }
      }
    }
    leaf disable-connected-check {
      tailf:info
        "One-hop away EBGP peer using loopback address";
      tailf:cli-full-command;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      type empty;
    }
  }

  grouping router-bgp-neighbor-grouping {
    leaf remote-as {
      tailf:info
        "Specify a BGP neighbor";
      tailf:cli-delete-container-on-delete;
      tailf:cli-full-command;
      tailf:cli-diff-dependency "../inherit/peer-session" {
        tailf:xpath-root 3;
      }
      tailf:cli-diff-dependency "../peer-group" {
        tailf:xpath-root 3;
      }
      type string {
        tailf:info
          "AS of remote neighbor";
      }
    }
    leaf activate {
      tailf:info
        "Enable the Address Family for this Neighbor";
      tailf:cli-delete-container-on-delete;
      tailf:cli-full-command;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      type empty;
    }
    uses router-bgp-peer-session-grouping;
    uses router-bgp-peer-policy-grouping;
    leaf soo {
      tailf:info
        "Site-of-Origin extended community";
      tailf:cli-full-command;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      type string {
        tailf:info
          "ASN:nn or IP-address:nn;;VPN extended community";
      }
    }
    container capability {
      tailf:info
        "Advertise capability to the peer";
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      container orf {
        tailf:info
          "Advertise ORF capability to the peer";
        leaf-list prefix-list {
          tailf:info
            "Advertise prefixlist ORF capability to this neighbor";
          tailf:cli-flat-list-syntax;
          max-elements 1;
          type enumeration {
            enum "both" {
              tailf:info
                "Capability to SEND and RECEIVE the ORF to/from this neighbor";
            }
            enum "receive" {
              tailf:info
                "Capability to RECEIVE the ORF from this neighbor";
            }
            enum "send" {
              tailf:info
                "Capability to SEND the ORF to this neighbor";
            }
          }
        }
      }
    }
    leaf description {
      tailf:info
        "Neighbor specific description";
      tailf:cli-multi-value;
      tailf:cli-preformatted;
      tailf:cli-full-command;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      type string {
        tailf:info
          "LINE;;Up to 80 characters describing this neighbor";
      }
    }
    uses router-bgp-neighbor-distribute-list-grouping;
    leaf dmzlink-bw {
      tailf:info
        "Propagate the DMZ link bandwidth";
      tailf:cli-full-command;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      type empty;
    }
    list filter-list {
      tailf:info
        "Establish BGP filters";
      tailf:cli-suppress-mode;
      tailf:cli-delete-when-empty;
      tailf:cli-compact-syntax;
      tailf:cli-sequence-commands;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      key "direction";
      leaf direction {
        type enumeration {
          enum "in" {
            tailf:info
              "Filter incoming routes";
          }
          enum "out" {
            tailf:info
              "Filter outgoing routes";
          }
        }
      }
      leaf as-path-list {
        tailf:cli-drop-node-name;
        tailf:cli-prefix-key;
        type string {
          tailf:info
            "WORD;;Access-list number or name";
        }
      }
    }
    container inherit {
      tailf:info
        "Inherit a template";
      tailf:cli-diff-dependency "../peer-group" {
        tailf:xpath-root 3;
      }
      tailf:cli-diff-dependency "../remote-as" {
        tailf:xpath-root 3;
      }
      leaf peer-policy {
        tailf:info
          "Inherit a peer-policy template";
        tailf:cli-full-command;
        tailf:cli-diff-dependency "/ios:router/bgp/template/peer-policy" {
          tailf:xpath-root 3;
        }
        tailf:cli-diff-dependency "../../activate" {
          tailf:xpath-root 3;
        }
        type string {
          tailf:info
            "WORD;;Template name";
        }
      }
      leaf peer-session {
        tailf:info
          "Inherit a peer-session template";
        tailf:cli-full-command;
        tailf:cli-diff-dependency "/ios:router/bgp/template/peer-session" {
          tailf:xpath-root 3;
        }
        tailf:cli-diff-dependency "/ios:router/bgp/template/peer-session/remote-as" {
          tailf:xpath-root 3;
        }
        type string {
          tailf:info
            "WORD;;Template name";
        }
      }
    }
    container next-hop-self-arg {
      tailf:cli-drop-node-name;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      leaf next-hop-self {
        type string;
      }
    }
    leaf next-hop-unchanged {
      tailf:info
        "Propagate the iBGP paths's next hop unchanged for this neighbor";
      tailf:cli-full-command;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      type empty;
    }
    leaf shutdown {
      tailf:info
        "Administratively shut down this neighbor";
      tailf:cli-full-command;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      type empty;
    }
    container translate-update {
      tailf:info
        "Translate Update to MBGP format";
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      container ipv4 {
        tailf:info
          "Address Family";
        container multicast {
          tailf:info
            "Address Family modifier";
          tailf:cli-delete-when-empty;
          presence "Address Family modifier";
          leaf unicast {
            tailf:info
              "Address Family modifier";
            type empty;
          }
        }
      }
    }
    leaf unsuppress-map {
      tailf:info
        "Route-map to selectively unsuppress suppressed routes";
      tailf:cli-full-command;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      type string {
        tailf:info
          "WORD;;Name of route map";
      }
    }
    leaf weight {
      tailf:info
        "Set default weight for routes from this neighbor";
      tailf:cli-full-command;
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      type uint16 {
        tailf:info
          "<0-65535>;;default weight";
        range "0..65535";
      }
    }
    container ha-mode {
      tailf:info
        "high availability mode";
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      container graceful-restart {
        tailf:info
          "graceful-restart for this peer";
        presence "true";
        leaf disable {
          tailf:info
            "disable graceful-restart";
          type empty;
        }
      }
      container sso {
        tailf:info
          "stateful-switchover support for this peer";
        presence "true";
        leaf disable {
          tailf:info
            "disable stateful-switchover";
          type empty;
        }
      }
    }
    container suppress-signaling-protocol {
      tailf:info
        "suppress VPLS signaling protocol";
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      leaf ldp {
        tailf:info
          "suppress ldp signaling, enable bgp signaling";
        tailf:cli-full-command;
        type empty;
      }
    }
    leaf prefix-length-size {
      tailf:info
        "Packet Level storage size for Prefixes";
      tailf:cli-diff-dependency "../inherit/peer-session" {
        tailf:xpath-root 3;
      }
      tailf:cli-diff-dependency "../peer-group" {
        tailf:xpath-root 3;
      }
      tailf:cli-diff-dependency "../remote-as" {
        tailf:xpath-root 3;
      }
      tailf:cli-diff-dependency "../activate" {
        tailf:xpath-root 3;
      }
      type uint8 {
        tailf:info
          "<1-2>;;Storage size in bytes";
        range "1..2";
      }
    }
  }

  grouping router-bgp-af-grouping {
    leaf synchronization {
      tailf:info
        "Perform IGP synchronization";
      tailf:cli-full-command;
      type empty;
    }
    leaf table-map {
      tailf:info
        "Map external entry attributes into routing table";
      tailf:cli-full-command;
      type string {
        tailf:info
          "WORD;;route-map name";
      }
    }
    container bgp-af {
      tailf:cli-drop-node-name;
      container bgp {
        tailf:info
          "BGP specific commands";
        leaf redistribute-internal {
          tailf:info
            "Allow redistribution of iBGP into IGPs (dangerous)";
          tailf:cli-full-command;
          type empty;
        }
        container dampening {
          tailf:info
            "Enable route-flap dampening";
          presence "true";
          choice dampening-choice {
            leaf route-map {
              tailf:info
                "Route-map to specify criteria for dampening";
              type string {
                tailf:info
                  "WORD;;route-map name";
              }
            }
            container dampen {
              tailf:cli-drop-node-name;
              tailf:cli-compact-syntax;
              tailf:cli-sequence-commands;
              leaf half-life-time {
                tailf:cli-drop-node-name;
                type uint8 {
                  tailf:info
                    "<1-45>;;Half-life time for the penalty";
                  range "1..45";
                }
              }
              leaf reuse-time {
                tailf:cli-drop-node-name;
                tailf:cli-incomplete-command;
                type uint16 {
                  tailf:info
                    "<1-20000>;;Value to start reusing a route";
                  range "1..20000";
                }
              }
              leaf suppress-time {
                tailf:cli-drop-node-name;
                tailf:cli-incomplete-command;
                type uint16 {
                  tailf:info
                    "<1-20000>;;Value to start suppressing a route";
                  range "1..20000";
                }
              }
              leaf max-suppress-time {
                tailf:cli-drop-node-name;
                type uint8 {
                  tailf:info
                    "<1-255>;;Maximum duration to suppress a stable route";
                  range "1..255";
                }
              }
            }
          }
        }
        container additional-paths {
          tailf:info
            "Additional paths in the BGP table";
          choice send-receive-choice {
            leaf receive {
              tailf:info
                "Receive additional paths from neighbors";
              tailf:cli-full-command;
              type empty;
            }
            container send {
              tailf:info
                "Send additional paths to neighbors";
              tailf:cli-delete-when-empty;
              presence "true";
              leaf receive {
                tailf:info
                  "Receive additional paths from neighbors";
                type empty;
              }
            }
          }
          leaf install {
            tailf:info
              "Additional paths to install into RIB";
            tailf:cli-full-command;
            type empty;
          }
        }
        container bestpath {
          tailf:info
            "Change the default bestpath selection";
          container igp-metric {
            tailf:info
              "igp metric";
            leaf ignore {
              tailf:info
                "Ignore igp metric in bestpath selection";
              type empty;
            }
          }
        }
        leaf suppress-inactive {
          tailf:info
            "Suppress routes that are not in the routing table";
          tailf:cli-full-command;
          type empty;
        }
        leaf dmzlink-bw {
          tailf:info
            "Use DMZ Link Bandwidth as weight for BGP multipaths";
          tailf:cli-full-command;
          type empty;
        }
        leaf soft-reconfig-backup {
          tailf:info
            "Use soft-reconfiguration inbound only when route-refresh is not negotiated";
          tailf:cli-full-command;
          type empty;
        }
        container nexthop {
          tailf:info
            "Nexthop tracking commands";
          leaf route-map {
            tailf:info
              "Route map for valid nexthops";
            tailf:cli-full-command;
            type string {
              tailf:info
                "WORD;;route-map name";
            }
          }
          container trigger {
            tailf:info
              "Nexthop triggering";
            leaf delay {
              tailf:cli-full-command;
              tailf:info
                "Set the delay to tigger nexthop tracking";
              type uint8 {
                tailf:info
                  "<0-100>;;Delay value (seconds)";
                range "0..100";
              }
            }
            leaf enable {
              tailf:info
                "Enable nexthop tracking";
              tailf:cli-full-command;
              tailf:cli-boolean-no;
              type boolean;
              default "true";
            }
          }
        }
        leaf scan-time {
          tailf:cli-full-command;
          tailf:info
            "Configure background scanner interval";
          type uint8 {
            tailf:info
              "<5-60>;;Scanner interval (seconds)";
            range "5..60";
          }
        }
        list inject-map {
          tailf:info
            "Routemap which specifies prefixes to inject";
          tailf:cli-suppress-mode;
          tailf:cli-delete-when-empty;
          tailf:cli-compact-syntax;
          tailf:cli-sequence-commands;
          tailf:cli-incomplete-command;
          key "name";
          leaf name {
            type string {
              tailf:info
                "WORD;;route-map name";
            }
          }
          leaf exist-map {
            tailf:info
              "Routemap which specifies exist condition";
            type string {
              tailf:info
                "WORD;;route-map name";
            }
          }
          leaf copy-attributes {
            tailf:info
              "Copy attributes from aggregate";
            type empty;
          }
        }
        container recursion {
          tailf:info
            "recursion rule for the nexthops";
          leaf host {
            tailf:info
              "recursion via host for the nexthops";
            type empty;
          }
        }
      }
    }
    list network {
      tailf:info
        "Specify a network to announce via BGP";
      tailf:cli-suppress-mode;
      tailf:cli-delete-when-empty;
      tailf:cli-compact-syntax;
      tailf:cli-reset-container;
      key "number";
      leaf number {
        type union {
          type inet:ipv4-address {
            tailf:info
              "A.B.C.D;;Network number";
          }
          type ios:ipv6-prefix {
            tailf:info
              "X:X:X:X::X/<0-128>;;IPv6 prefix";
          }
        }
      }
      leaf backdoor {
        tailf:info
          "Specify a BGP backdoor route";
        tailf:cli-full-command;
        type empty;
      }
      leaf mask {
        tailf:info
          "Network mask";
        type inet:ipv4-address {
          tailf:info
            "A.B.C.D;;Network mask";
        }
      }
      leaf route-map {
        tailf:info
          "Route-map to modify the attributes";
        type string {
          tailf:info
            "WORD;;Name of the route map";
        }
      }
    }
    list aggregate-address {
      tailf:info
        "Configure BGP aggregate entries";
      tailf:cli-suppress-mode;
      tailf:cli-delete-when-empty;
      tailf:cli-compact-syntax;
      tailf:cli-sequence-commands {
        tailf:cli-reset-all-siblings;
      }
      key "address mask";
      leaf address {
        type inet:ipv4-address {
          tailf:info
            "A.B.C.D;;Aggregate address";
        }
      }
      leaf mask {
        type inet:ipv4-address {
          tailf:info
            "A.B.C.D;;Aggregate mask";
        }
      }
      uses router-bgp-aggregate-address-content-grouping;
    }
    container aggregate-addres-ipv6 {
      tailf:cli-drop-node-name;
      list aggregate-address {
        tailf:info
          "Configure BGP aggregate entries";
        tailf:cli-suppress-mode;
        tailf:cli-delete-when-empty;
        tailf:cli-compact-syntax;
        tailf:cli-sequence-commands {
          tailf:cli-reset-all-siblings;
        }
        key "address";
        leaf address {
          type ipv6-prefix {
            tailf:info
              "X:X:X:X::X/<0-128>;;IPv6 Network number";
          }
        }
        uses router-bgp-aggregate-address-content-grouping;
      }
    }
    container redistribute {
      tailf:info
        "Redistribute information from another routing protocol";
      container bgp {
        tailf:info
          "Border Gateway Protocol (BGP)";
        tailf:cli-compact-syntax;
        tailf:cli-sequence-commands;
        tailf:cli-delete-when-empty;
        leaf as-no {
          tailf:cli-drop-node-name;
          tailf:cli-remove-before-change;
          type bgp-as-no-type;
        }
        uses router-bgp-redistribute-grouping {
          refine "metric" {
            tailf:cli-break-sequence-commands;
          }
        }
      }
      container connected {
        tailf:info
          "Connected";
        tailf:cli-compact-syntax;
        tailf:cli-delete-when-empty;
        presence "true";
        uses router-bgp-redistribute-grouping;
      }
      container static {
        tailf:info
          "Static routes";
        tailf:cli-compact-syntax;
        tailf:cli-delete-when-empty;
        presence "true";
        uses router-bgp-redistribute-grouping;
      }
      container dvmrp {
        tailf:info
          "Redistribution of DVMRP into BGP IPv4 Multicast";
        tailf:cli-compact-syntax;
        tailf:cli-sequence-commands;
        tailf:cli-delete-when-empty;
        presence "true";
        uses route-map-metric-grouping;
      }
      list eigrp {
        tailf:info
          "Enhanced Interior Gateway Routing Protocol (EIGRP)";
        tailf:cli-suppress-mode;
        tailf:cli-delete-when-empty;
        tailf:cli-compact-syntax;
        tailf:cli-remove-before-change;
        key "as-no";
        leaf as-no {
          type eigrp-as-no-type;
        }
        uses router-bgp-redistribute-grouping;
      }
      container isis {
        tailf:info
          "ISO IS-IS";
        tailf:cli-compact-syntax;
        tailf:cli-delete-when-empty;
        presence "true";
        uses router-bgp-redistribute-isis-grouping;
        uses router-bgp-redistribute-grouping;
        list isis-list {
          tailf:cli-drop-node-name;
          tailf:cli-suppress-mode;
          tailf:cli-delete-when-empty;
          tailf:cli-compact-syntax;
          tailf:cli-remove-before-change;
          key "name";
          leaf name {
            tailf:cli-disallow-value "level-1|level-2|level-1-2|metric|clns|ip|route-map|subnets|include-connected";
            type string {
              tailf:info
                "WORD;;ISO routing area tag";
            }
          }
          uses router-bgp-redistribute-isis-grouping;
          uses router-bgp-redistribute-grouping;
        }
      }
      container iso-igrp {
        tailf:info
          "IGRP for OSI networks";
        tailf:cli-compact-syntax;
        tailf:cli-delete-when-empty;
        uses route-map-metric-grouping;
        list iso-igrp-area {
          tailf:cli-drop-node-name;
          tailf:cli-suppress-mode;
          tailf:cli-delete-when-empty;
          tailf:cli-compact-syntax;
          tailf:cli-remove-before-change;
          key "name";
          leaf name {
            type string {
              tailf:info
                "WORD;;Pointer to route-map entries";
              pattern '^([^r].*)|(r^[o].*)|(ro[^u].*)|(rou[^t].*)|(rout[^e].*)|(route[^\-].*)|(route-[^m].*)|(route-m[^a].*)|(route-ma[^p])|(route-map..*)';
            }
          }
          uses route-map-metric-grouping;
        }
      }
      container mobile {
        tailf:info
          "Mobile routes";
        tailf:cli-compact-syntax;
        tailf:cli-delete-when-empty;
        presence "true";
        uses router-bgp-redistribute-grouping;
      }
      container odr {
        tailf:info
          "On Demand stub Routes";
        tailf:cli-compact-syntax;
        tailf:cli-delete-when-empty;
        presence "true";
        uses router-bgp-redistribute-grouping;
      }
      list ospf {
        tailf:info
          "Open Shortest Path First (OSPF)";
        tailf:cli-suppress-mode;
        tailf:cli-flatten-container;
        tailf:cli-compact-syntax;
        tailf:cli-delete-when-empty;
        tailf:cli-remove-before-change;
        key "id";
        leaf id {
          type uint16 {
            tailf:info
              "<1-65535>;;Process ID";
            range "1..65535";
          }
        }
        leaf vrf {
          tailf:info
            "VPN Routing/Forwarding Instance";
          tailf:cli-diff-dependency "/ios:ip/vrf" {
            tailf:xpath-root 3;
          }
          tailf:cli-diff-dependency "/ios:vrf/definition" {
            tailf:xpath-root 3;
          }
          type string {
            tailf:info
              "WORD;;VPN Routing/Forwarding Instance (VRF) name";
          }
        }
        uses router-bgp-redistribute-ospf-grouping;
      }
      container rip {
        tailf:info
          "Routing Information Protocol (RIP)";
        tailf:cli-compact-syntax;
        tailf:cli-delete-when-empty;
        presence "true";
        uses router-bgp-redistribute-grouping;
      }
      container lisp {
        tailf:info
          "Locator ID Separation Protocol (LISP)";
        tailf:cli-compact-syntax;
        tailf:cli-delete-when-empty;
        presence "true";
        uses router-bgp-redistribute-grouping;
      }
    }
    container neighbor-tag {
      tailf:cli-drop-node-name;
      list neighbor {
        tailf:info
          "Specify a neighbor router";
        tailf:cli-suppress-mode;
        tailf:cli-delete-when-empty;
        tailf:cli-incomplete-command;
        tailf:cli-show-long-obu-diffs;
        ordered-by user;
        key "id";
        leaf id {
          type string {
            tailf:info
              "WORD;;Neighbor tag";
          }
        }
        leaf peer-group {
          tailf:info
            "Configure peer-group";
          tailf:cli-delete-container-on-delete;
          tailf:cli-full-command;
          type empty;
        }
        uses router-bgp-neighbor-grouping;
      }
    }
    list neighbor {
      tailf:info
        "Specify a neighbor router";
      tailf:cli-suppress-mode;
      tailf:cli-delete-when-empty;
      tailf:cli-incomplete-command;
      tailf:cli-diff-dependency "../neighbor-tag/neighbor" {
        tailf:xpath-root 3;
      }
      key "id";
      leaf id {
        type union {
          type inet:ipv4-address {
            tailf:info
              "A.B.C.D;;Neighbor address";
          }
          type inet:ipv6-address {
            tailf:info
              "X:X:X:X::X;;Neighbor IPv6 address";
          }
        }
      }
      leaf peer-group {
        tailf:info
          "Member of the peer-group";
        tailf:cli-delete-container-on-delete;
        tailf:cli-full-command;
        type string {
          tailf:info
            "WORD;;peer-group name";
        }
      }
      uses router-bgp-neighbor-grouping;
    }
    container maximum-paths {
      tailf:info
        "Forward packets over multiple paths";
      uses router-bgp-max-path-grouping;
      container eibgp {
        tailf:info
          "Both eBGP and iBGP paths as multipath";
        uses router-bgp-max-path-grouping;
      }
      container ibgp {
        tailf:info
          "iBGP-multipath";
        choice ibgp-choice {
          default "b";
          case a {
            container unequal-cost {
              tailf:info
                "Perform Un-Equal cost multipath selection";
              uses router-bgp-max-path-grouping;
            }
          }
          case b {
            uses router-bgp-max-path-grouping;
          }
        }
      }
      leaf import {
        tailf:info
          "Maximum import paths";
        type uint16 {
          tailf:info
            "<1-16>;;Number of import paths";
          range "1..16";
        }
      }
    }
    container import {
      tailf:info
        "Configure path import";
      container path {
        tailf:info
          "Path selection and path limit";
        container selection {
          tailf:info
            "Path selection policy";
          choice selection-choice {
            leaf all {
              tailf:info
                "Import all available paths";
              type empty;
            }
            container bestpath {
              tailf:info
                "Import the best available path.";
              tailf:cli-delete-when-empty;
              presence "true";
              leaf strict {
                tailf:info
                  "Do not fallback to best available path";
                type empty;
              }
            }
            container multipaths {
              tailf:info
                "Import all multipaths.";
              tailf:cli-delete-when-empty;
              presence "true";
              leaf strict {
                tailf:info
                  "Do not fallback to best available path";
                type empty;
              }
            }
          }
        }
        leaf limit {
          tailf:info
            "Per net imported path limit";
          type uint8 {
            tailf:info
              "<2-255>;;Maximum number of paths that can be imported into a net";
            range "2..255";
          }
        }
      }
    }
    container default-information {
      tailf:info
        "Control distribution of default information";
      leaf originate {
        tailf:info
          "Distribute a default route";
        type empty;
      }
    }
    leaf default-metric {
      tailf:info
        "Set metric of redistributed routes";
      tailf:cli-full-command;
      type uint32 {
        tailf:info
          "<1-4294967295>;;Default metric";
        range "1..4294967295";
      }
    }
    uses router-distribute-list-grouping;
    container distance {
      tailf:info
        "Define an administrative distance";
      container bgp {
        tailf:info
          "BGP distance";
        tailf:cli-compact-syntax;
        tailf:cli-sequence-commands;
        leaf extern-as {
          tailf:cli-drop-node-name;
          tailf:cli-incomplete-command;
          type uint16 {
            tailf:info
              "<1-255>;;Distance for routes external to the AS";
            range "1..255";
          }
        }
        leaf internal-as {
          tailf:cli-drop-node-name;
          tailf:cli-incomplete-command;
          type uint16 {
            tailf:info
              "<1-255>;;Distance for routes internal to the AS";
            range "1..255";
          }
        }
        leaf local {
          tailf:cli-drop-node-name;
          type uint16 {
            tailf:info
              "<1-255>;;Distance for local routes";
            range "1..255";
          }
        }
      }
      list adm-distance {
        tailf:cli-drop-node-name;
        tailf:cli-suppress-mode;
        tailf:cli-delete-when-empty;
        key "srcip wildbits";
        leaf distance {
          tailf:cli-drop-node-name;
          tailf:cli-prefix-key;
          type uint16 {
            tailf:info
              "<1-255>;;Administrative distance";
            range "1..255";
          }
        }
        leaf srcip {
          type inet:ipv4-address {
            tailf:info
              "A.B.C.D;;IP Source address";
          }
        }
        leaf wildbits {
          type inet:ipv4-address {
            tailf:info
              "A.B.C.D;;Wildcard bits";
          }
        }
        leaf access-list {
          tailf:cli-drop-node-name;
          type std-ip-acl-type;
        }
      }
    }
    leaf auto-summary {
      tailf:info
        "Enable automatic network number summarization";
      tailf:cli-boolean-no;
      tailf:cli-full-command;
      type boolean;
    }
  }

  grouping router-bgp-bgp-grouping {
    container bgp {
      leaf router-id {
        tailf:info
          "Override configured router identifier (peers will reset)";
        tailf:cli-full-command;
        type inet:ipv4-address {
          tailf:info
            "A.B.C.D;;Manually configured router identifier";
        }
      }
      leaf fast-external-fallover {
        tailf:info
          "Immediately reset session if a link to a directly connected external peer goes down";
        tailf:cli-boolean-no;
        tailf:cli-full-command;
        type boolean;
        default "true";
      }
      leaf always-compare-med {
        tailf:info
          "Allow comparing MED from different neighbors";
        tailf:cli-full-command;
        type empty;
      }
      leaf cluster-id {
        tailf:cli-full-command;
        type union {
          type uint32 {
            tailf:info
              "<1-4294967295>;;Route-Reflector Cluster-id as 32 bit quantity";
            range "1..4294967295";
          }
          type inet:ipv4-address {
            tailf:info
              "A.B.C.D;;Route-Reflector Cluster-id in IP address format";
          }
        }
      }
      container transport {
        tailf:info
          "global enable/disable transport session parameters";
        leaf path-mtu-discovery {
          tailf:info
            "transport path MTU discovery";
          tailf:cli-boolean-no;
          tailf:cli-full-command;
          type boolean;
          default "true";
        }
      }
      leaf enforce-first-as {
        tailf:info
          "Enforce the first AS for EBGP routes(default)";
        tailf:cli-boolean-no;
        tailf:cli-full-command;
        type boolean;
        default "true";
      }
      container client-to-client {
        tailf:info
          "Configure client to client route reflection";
        leaf reflection {
          tailf:info
            "reflection of routes allowed";
          tailf:cli-boolean-no;
          tailf:cli-full-command;
          type boolean;
          default "true";
        }
      }
      leaf log-neighbor-changes {
        tailf:info
          "Log neighbor up/down and reset reason";
        tailf:cli-boolean-no;
        tailf:cli-full-command;
        type boolean;
      }
      container confederation {
        tailf:info
          "AS confederation parameters";
        leaf identifier {
          tailf:info
            "as number";
          tailf:cli-full-command;
          type uint16 {
            tailf:info
              "<1-65535>;;Set routing domain confederation AS";
            range "1..65535";
          }
        }
        container peers {
          tailf:info
            "Peer ASs in BGP confederation";
          leaf-list as-no {
            tailf:cli-drop-node-name;
            tailf:cli-flat-list-syntax;
            type bgp-as-no-type;
          }
        }
      }
      leaf deterministic-med {
        tailf:cli-full-command;
        tailf:info
          "Pick the best-MED path among paths advertised from the neighboring AS";
        type empty;
      }
      container listen {
        tailf:info
          "Neighbor subnet range listener";
        list range {
          tailf:info
            "Subnet network range";
          tailf:cli-suppress-mode;
          tailf:cli-delete-when-empty;
          tailf:cli-incomplete-command;
          key "network-length";
          leaf network-length {
            type ios:ipv4-prefix {
              tailf:info
                "A.B.C.D/nn;;Subnet range <network>/<length>, e.g., 10.0.0.0/24";
            }
          }
          leaf peer-group {
            tailf:info
              "Member of the peer-group";
            type string {
              tailf:info
                "WORD;;peer-group name";
            }
          }
        }
        leaf limit {
          tailf:info
            "Set the max limit for the dynamic subnet range neighbors";
          type uint32 {
            tailf:info
              "<1-5000>;;max number";
            range "1..5000";
          }
        }
      }
      leaf update-delay {
        tailf:info
          "Set the max initial delay for sending update";
        tailf:cli-full-command;
        type uint16 {
          tailf:info
            "<1-3600>;;Delay value (seconds)";
          range "1..3600";
        }
      }
      container graceful-restart-conf {
        tailf:cli-drop-node-name;
        container graceful-restart {
          tailf:info
            "Graceful restart capability parameters";
          tailf:cli-incomplete-no;
          tailf:cli-incomplete-command;
          leaf restart-time {
            tailf:info
              "Set the max time needed to restart and come back up";
            tailf:cli-full-command;
            type uint16 {
              tailf:info
                "<1-3600>;;Delay value (seconds)";
              range "1..3600";
            }
            default "120";
          }
          leaf stalepath-time {
            tailf:info
              "Set the max time to hold onto restarting peer's stale paths";
            type uint16 {
              tailf:info
                "<1-3600>;;Delay value (seconds)";
              range "1..3600";
            }
            default "360";
          }
        }
      }
      leaf graceful-restart {
        tailf:info
          "Graceful restart capability parameters";
        tailf:cli-full-command;
        type empty;
      }
      container regexp {
        tailf:info
          "Select regular expression engine";
        leaf deterministic {
          tailf:info
            "Enable bounded-execution-time regular expression engine";
          tailf:cli-boolean-no;
          type boolean;
          default "true";
        }
      }
      container bestpath {
        tailf:info
          "Change the default bestpath selection";
        leaf compare-routerid {
          tailf:info
            "Compare router-id for identical EBGP paths";
          tailf:cli-full-command;
          type empty;
        }
        container cost-community {
          tailf:info
            "cost community";
          leaf ignore {
            tailf:info
              "Ignore cost communities in bestpath selection";
            type empty;
          }
        }
        container med {
          tailf:info
            "MED attribute";
          choice med-choice {
            container confed {
              tailf:info
                "Compare MED among confederation paths";
              presence "Compare MED among confederation paths";
              leaf missing-at-worst {
                tailf:info
                  "Treat missing MED as the least preferred one";
                type empty;
              }
            }
            leaf missing-at-worst {
              tailf:info
                "Treat missing MED as the least preferred one";
              type empty;
            }
          }
        }
        container as-path {
          leaf multipath-relax {
            type empty;
          }
        }
      }
      leaf maxas-limit {
        tailf:info
          "Allow AS-PATH attribute from any neighbor imposing a limit on number of ASes";
        tailf:cli-full-command;
        type uint16 {
          tailf:info
            "<1-2000>;;Number of ASes in the AS-PATH attribute";
          range "1..2000";
        }
      }
      container default {
        tailf:info
          "Configure BGP defaults";
        leaf ipv4-unicast {
          tailf:info
            "Activate ipv4-unicast for a peer by default";
          tailf:cli-boolean-no;
          type boolean;
          default "true";
        }
        leaf ipv4-activate {
          tailf:cli-boolean-no;
          type boolean;
          default "true";
        }
        leaf local-preference {
          tailf:info
            "local preference (higher=more preferred)";
          type uint32 {
            tailf:info
              "<0-4294967295>;;Configure default local preference value";
            range "1..4294967295";
          }
        }
        container route-target {
          tailf:info
            "Control behavior based on Route-Target attributes";
          leaf filter {
            tailf:info
              "Control automatic VPN Route-Target filtering";
            tailf:cli-boolean-no;
            type boolean;
            default "true";
          }
        }
      }
    }
    container timers {
      tailf:info
        "Adjust routing timers";
      container bgp {
        tailf:info
          "BGP timers";
        tailf:cli-compact-syntax;
        tailf:cli-sequence-commands {
          tailf:cli-reset-siblings;
        }
        leaf keepalive {
          tailf:cli-drop-node-name;
          tailf:cli-incomplete-command;
          type uint16 {
            tailf:info
              "<0-65535>;;Keepalive interval";
            range "0..65535";
          }
        }
        leaf holdtime {
          tailf:cli-drop-node-name;
          type uint16 {
            tailf:info
              "<0-65535>;;Holdtime";
            range "0..65535";
          }
        }
        leaf min-holdtime {
          tailf:cli-drop-node-name;
          type uint16 {
            tailf:info
              "<0-65535>;;Minimum hold time from neighbor";
            range "0..65535";
          }
        }
      }
    }
  }

  grouping router-ospf-af-grouping;

  grouping router-ospfv3-af-grouping {
    container capability {
      tailf:info
        "Enable a specific feature";
      leaf vrf-lite {
        tailf:info
          "Do not perform PE specific checks";
        type empty;
      }
    }
    container discard-route {
      tailf:info
        "Enable or disable discard-route installation";
      leaf external {
        tailf:info
          "Discard route for summarised redistributed routes";
        tailf:cli-boolean-no;
        tailf:cli-full-command;
        type boolean;
        default "true";
      }
      leaf internal {
        tailf:info
          "Discard route for summarised inter-area routes";
        tailf:cli-boolean-no;
        tailf:cli-full-command;
        type boolean;
        default "true";
      }
    }
  }

  grouping router-ospf-common-af-grouping {
    container default-information {
      tailf:info
        "Control distribution of default information";
      container originate {
        tailf:info
          "Distribute a default route";
        tailf:cli-compact-syntax;
        tailf:meta-data "trim-delete-when-empty" {
          tailf:meta-value "( originate)";
        }
        tailf:ned-data "." {
          tailf:xpath-root 3;
          tailf:transaction to;
        }
        presence "true";
        leaf always {
          tailf:info
            "Always advertise default route";
          type empty;
        }
        leaf metric {
          tailf:info
            "OSPF default metric";
          type uint32 {
            tailf:info
              "<0-16777214>;;OSPF metric";
            range "0..16777214";
          }
        }
        leaf metric-type {
          tailf:info
            "OSPF metric type for default routes";
          type ospf-metric-type;
          default "2";
        }
        leaf route-map {
          tailf:info
            "Route map reference";
          type string {
            tailf:info
              "WORD;;Route map name";
          }
        }
      }
    }
    leaf default-metric {
      tailf:info
        "Set metric of redistributed routes";
      tailf:cli-full-command;
      type uint32 {
        tailf:info
          "<1-16777214>;;OSPF default metric";
        range "1..16777214";
      }
    }
    container distance {
      tailf:info
        "Define an administrative distance";
      leaf weight {
        tailf:cli-drop-node-name;
        type uint8 {
          tailf:info
            "<1-255>;;Administrative distance";
          range "1..255";
        }
      }
      list distance-list {
        tailf:cli-drop-node-name;
        tailf:cli-suppress-mode;
        tailf:cli-delete-when-empty;
        tailf:cli-compact-syntax;
        tailf:cli-sequence-commands {
          tailf:cli-reset-siblings;
        }
        key "ip-address wildcard-mask";
        leaf ip-address {
          type inet:ipv4-address {
            tailf:info
              "A.B.C.D;;IP source address";
          }
        }
        leaf wildcard-mask {
          type inet:ipv4-address {
            tailf:info
              "A.B.C.D;;Wildcard bits";
          }
        }
        leaf weight {
          tailf:cli-drop-node-name;
          tailf:cli-prefix-key;
          type uint8 {
            tailf:info
              "<1-255>;;Administrative distance";
            range "1..255";
          }
        }
        leaf access-list {
          tailf:cli-drop-node-name;
          type std-ip-acl-type;
        }
      }
      container ospf {
        tailf:info
          "OSPF routes Administrative distance";
        tailf:cli-compact-syntax;
        leaf intra-area {
          tailf:info
            "Intra-area routes";
          type uint32 {
            tailf:info
              "<1-255>;;Distance for intra-area routes";
            range "1..255";
          }
        }
        leaf inter-area {
          tailf:info
            "Inter-area routes";
          type uint32 {
            tailf:info
              "<1-255>;;Distance for inter-area routes";
            range "1..255";
          }
        }
        leaf external {
          tailf:info
            "External routes";
          type uint32 {
            tailf:info
              "<1-255>;;Distance for external routes";
            range "1..255";
          }
        }
      }
    }
    leaf maximum-paths {
      tailf:info
        "Forward packets over multiple paths";
      tailf:cli-full-command;
      type uint32 {
        range "1..32";
        tailf:info
          "<1-32>;;Number of paths";
      }
    }
    leaf nsr {
      tailf:info
        "Enable non-stop routing";
      type empty;
    }
    container redistribute {
      tailf:info
        "Redistribute information from another routing protocol";
      container connected {
        tailf:info
          "Connected";
        tailf:cli-compact-syntax;
        tailf:cli-delete-when-empty;
        presence "true";
        uses router-ospf-redistribute-grouping;
        uses router-ospf-route-map-grouping;
      }
      container static {
        tailf:info
          "Static routes";
        tailf:cli-compact-syntax;
        tailf:cli-delete-when-empty;
        presence "true";
        uses router-ospf-redistribute-grouping;
        uses router-ospf-route-map-grouping;
      }
      container odr {
        tailf:info
          "On Demand stub Routes";
        tailf:cli-compact-syntax;
        presence "true";
        uses router-ospf-redistribute-grouping;
        uses router-ospf-route-map-grouping;
      }
      container bgp {
        tailf:info
          "Border Gateway Protocol (BGP)";
        tailf:cli-compact-syntax;
        tailf:cli-sequence-commands;
        leaf as-no {
          tailf:cli-drop-node-name;
          tailf:cli-remove-before-change;
          tailf:cli-delete-container-on-delete;
          tailf:cli-diff-dependency "/ios:router/bgp" {
            tailf:xpath-root 3;
          }
          type bgp-as-no-type;
        }
        uses router-ospf-redistribute-grouping {
          refine "metric" {
            tailf:cli-break-sequence-commands;
          }
        }
        uses router-ospf-route-map-grouping;
      }
      list ospf {
        tailf:info
          "Open Shortest Path First (OSPF)";
        tailf:cli-suppress-mode;
        tailf:cli-delete-when-empty;
        tailf:cli-compact-syntax;
        key "id";
        leaf id {
          tailf:cli-suppress-range;
          type uint16 {
            tailf:info
              "<1-65535>;;Process ID";
            range "1..65535";
          }
        }
        uses router-ospf-redistribute-grouping;
        uses redistribute-ospf-match-grouping;
        uses router-ospf-route-map-grouping;
      }
      container isis {
        tailf:info
          "ISO IS-IS";
        tailf:cli-compact-syntax;
        presence "true";
        uses router-isis-level-grouping;
        uses router-ospf-redistribute-grouping;
        uses router-ospf-route-map-grouping;
        list isis-area {
          tailf:cli-drop-node-name;
          tailf:cli-suppress-mode;
          tailf:cli-delete-when-empty;
          tailf:cli-compact-syntax;
          key "name";
          leaf name {
            tailf:cli-disallow-value "level-1|level-2|level-1-2|metric|metric-type|route-map|nssa-only|subnets|tag";
            type string {
              tailf:info
                "WORD;;ISO routing area tag";
            }
          }
          uses router-isis-level-grouping;
          uses router-ospf-redistribute-grouping;
          uses router-ospf-route-map-grouping;
        }
      }
      list eigrp {
        tailf:info
          "Enhanced Interior Gateway Routing Protocol (EIGRP)";
        tailf:cli-suppress-mode;
        tailf:cli-delete-when-empty;
        tailf:cli-compact-syntax;
        key "as-no";
        leaf as-no {
          type eigrp-as-no-type;
        }
        uses router-ospf-redistribute-grouping;
        uses router-ospf-route-map-grouping;
      }
      container iso-igrp {
        tailf:info
          "IGRP for OSI networks";
        tailf:cli-compact-syntax;
        tailf:cli-sequence-commands;
        presence "true";
        leaf area-tag {
          tailf:cli-drop-node-name;
          tailf:cli-disallow-value "route-map";
          tailf:cli-optional-in-sequence;
          type string {
            tailf:info
              "WORD;;ISO routing area tag";
          }
        }
        uses router-ospf-route-map-grouping;
        uses router-ospf-redistribute-grouping;
      }
      container maximum-prefix {
        tailf:info
          "Maximum number of prefixes redistributed to protocol";
        tailf:cli-compact-syntax;
        tailf:cli-sequence-commands;
        leaf number {
          tailf:cli-drop-node-name;
          type uint32 {
            tailf:info
              "<1-4294967295>;;Maximum number of IP prefixes redistributed";
            range "1..4294967295";
          }
        }
        container threshold-warning-only-container {
          tailf:cli-drop-node-name;
          tailf:cli-flatten-container;
          tailf:cli-compact-syntax;
          leaf threshold {
            tailf:cli-drop-node-name;
            type uint32 {
              tailf:info
                "<1-100>;;Threshold value (%) at which to generate a warning message";
              range "1..100";
            }
          }
          leaf warning-only {
            tailf:info
              "Only give warning message when limit is exceeded";
            tailf:cli-full-command;
            type empty;
          }
        }
      }
      container mobile {
        tailf:info
          "Mobile routes";
        tailf:cli-compact-syntax;
        presence "true";
        uses router-ospf-redistribute-grouping;
        uses router-ospf-route-map-grouping;
      }
      container rip {
        tailf:info
          "Routing Information Protocol (RIP)";
        tailf:cli-compact-syntax;
        presence "true";
        uses router-ospf-redistribute-grouping;
        uses router-ospf-route-map-grouping;
        list redistribute-list-rip {
          tailf:cli-drop-node-name;
          tailf:cli-suppress-mode;
          tailf:cli-delete-when-empty;
          tailf:cli-compact-syntax;
          key "name";
          leaf name {
            type string {
              tailf:info
                "WORD;;User selected string identifying this process";
            }
          }
          uses router-ospf-redistribute-grouping;
          uses router-ospf-route-map-grouping;
        }
      }
      container lisp {
        tailf:info
          "Locator ID Separation Protocol (LISP)";
        container subnets {
          tailf:info
            "Consider subnets for redistribution into OSPF";
          tailf:cli-compact-syntax;
          tailf:cli-delete-when-empty;
          presence "true";
        }
      }
    }
  }

  grouping router-ospf-common-grouping {
    list area {
      tailf:info
        "OSPF area parameters";
      tailf:cli-suppress-mode;
      tailf:cli-delete-when-empty;
      tailf:cli-incomplete-command;
      key "id";
      leaf id {
        tailf:cli-suppress-range;
        type ospf-area-type;
      }
      container authentication {
        tailf:info
          "Enable authentication";
        presence "true";
        leaf message-digest {
          tailf:info
            "Use message-digest authentication";
          type empty;
        }
        choice authentication-choice {
          leaf null {
            tailf:info
              "Use no authentication";
            tailf:cli-full-command;
            type empty;
          }
          leaf key-chain {
            tailf:info
              "Use a key-chain for cryptographic authentication keys";
            tailf:cli-full-command;
            type string {
              tailf:info
                "LINE;;name of key-chain";
            }
          }
        }
      }
      container nssa {
        tailf:info
          "Specify a NSSA area";
        tailf:cli-compact-syntax;
        tailf:meta-data "trim-delete-when-empty" {
          tailf:meta-value "( nssa)";
        }
        tailf:ned-data "." {
          tailf:xpath-root 3;
          tailf:transaction to;
        }
        tailf:cli-diff-dependency "../stub" {
          tailf:xpath-root 3;
          tailf:cli-trigger-on-set;
        }
        presence "true";
        leaf no-redistribution {
          tailf:info
            "No redistribution into this NSSA area";
          type empty;
        }
        leaf default-information-originate {
          tailf:info
            "Originate Type 7 default into NSSA area";
          type empty;
        }
        leaf metric {
          tailf:info
            "OSPF default metric";
          when "../default-information-originate" {
            tailf:xpath-root 3;
            tailf:dependency "../default-information-originate";
          }
          type uint32 {
            tailf:info
              "<0-16777214>;;OSPF metric";
            range "0..16777214";
          }
        }
        leaf metric-type {
          tailf:info
            "OSPF metric type for default routes";
          type ospf-metric-type;
          default "2";
        }
        leaf nssa-only {
          tailf:info
            "Limit default advertisement to this NSSA area";
          type empty;
        }
        leaf no-ext-capability {
          tailf:info
            "Do not send domain specific capabilities into NSSA";
          type empty;
        }
        leaf no-summary {
          tailf:info
            "Do not send summary LSA into NSSA";
          type empty;
        }
        container translate {
          tailf:info
            "Translate LSA";
          container type7 {
            tailf:info
              "From Type 7 to Type 5";
            tailf:cli-compact-syntax;
            leaf always {
              tailf:info
                "Always translate LSAs on this ABR";
              type empty;
            }
            leaf suppress-fa {
              tailf:info
                "Suppress forwarding address in translated LSAs";
              type empty;
            }
          }
        }
      }
      leaf default-cost {
        tailf:info
          "Set the summary default-cost of a NSSA/stub area";
        tailf:cli-full-command;
        type uint32 {
          tailf:info
            "<0-16777215;;Stub's advertised external route metric";
          range "0..16777215";
        }
      }
      list filter-list {
        tailf:info
          "Filter networks between OSPF areas";
        tailf:cli-suppress-mode;
        tailf:cli-delete-when-empty;
        tailf:cli-compact-syntax;
        tailf:cli-sequence-commands;
        key "direction";
        leaf direction {
          type enumeration {
            enum "in" {
              tailf:info
                "Filter networks sent to this area";
            }
            enum "out" {
              tailf:info
                "Filter networks sent from this area";
            }
          }
        }
        leaf prefix {
          tailf:cli-prefix-key;
          tailf:info
            "Filter prefixes between OSPF areas";
          type string {
            tailf:info
              "WORD;;Name of an IP prefix-list";
          }
        }
      }
      list range {
        tailf:info
          "Summarize routes matching address/mask (border routers only)";
        tailf:cli-compact-syntax;
        tailf:cli-suppress-mode;
        tailf:cli-delete-when-empty;
        key "ip mask";
        leaf ip {
          type inet:ipv4-address {
            tailf:info
              "A.B.C.D;;IP address to match";
          }
        }
        leaf mask {
          type inet:ipv4-address {
            tailf:info
              "A.B.C.D;;IP mask for address";
          }
        }
        leaf advertise {
          tailf:cli-drop-node-name;
          type enumeration {
            enum "advertise" {
              tailf:info
                "Advertise this range (default)";
            }
            enum "not-advertise" {
              tailf:info
                "DoNotAdvertise this range";
            }
          }
          default "advertise";
        }
        leaf cost {
          tailf:info
            "User specified metric for this range";
          type uint32 {
            tailf:info
              "<0-16777215>;;Advertised metric for this range";
            range "0..16777215";
          }
        }
      }
      container range-ipv6 {
        tailf:cli-drop-node-name;
        list range {
          tailf:info
            "Summarize routes matching address/mask(border routers only)";
          tailf:cli-compact-syntax;
          tailf:cli-suppress-mode;
          tailf:cli-delete-when-empty;
          key "prefix";
          leaf prefix {
            type ipv6-prefix {
              tailf:info
                "X:X:X:X::X/<0-128>;;IPv6 prefix to match";
            }
          }
          leaf advertise {
            tailf:cli-drop-node-name;
            type enumeration {
              enum "advertise" {
                tailf:info
                  "Advertise this range (default)";
              }
              enum "not-advertise" {
                tailf:info
                  "DoNotAdvertise this range";
              }
            }
            default "advertise";
          }
          leaf cost {
            tailf:info
              "User specified metric for this range";
            type uint32 {
              tailf:info
                "<0-16777215>;;Advertised metric for this range";
              range "0..16777215";
            }
          }
        }
      }
      list sham-link {
        tailf:info
          "Define a sham link and its parameters";
        tailf:cli-suppress-mode;
        tailf:cli-delete-when-empty;
        key "source dest";
        leaf source {
          type inet:ipv4-address {
            tailf:info
              "A.B.C.D;;IP addr associated with sham-link source";
          }
        }
        leaf dest {
          type inet:ipv4-address {
            tailf:info
              "A.B.C.D;;IP addr associated with sham-link destination";
          }
        }
        leaf cost {
          tailf:info
            "Associate a cost with the sham-link";
          type uint16 {
            tailf:info
              "<1-65535>;;Cost of the sham-link";
            range "0..65535";
          }
        }
      }
      container stub {
        tailf:info
          "Specify a stub area";
        tailf:cli-compact-syntax;
        tailf:meta-data "trim-delete-when-empty" {
          tailf:meta-value "( stub)";
        }
        tailf:ned-data "." {
          tailf:xpath-root 3;
          tailf:transaction to;
        }
        tailf:cli-diff-dependency "../nssa" {
          tailf:xpath-root 3;
          tailf:cli-trigger-on-set;
        }
        presence "true";
        leaf no-summary {
          tailf:info
            "Do not send summary LSA into stub area";
          type empty;
        }
        leaf no-ext-capability {
          tailf:info
            "Do not send domain specific capabilities into stub area";
          type empty;
        }
      }
      list virtual-link {
        tailf:info
          "Define a virtual link and its parameters";
        tailf:cli-suppress-mode;
        tailf:cli-delete-when-empty;
        tailf:cli-compact-syntax;
        key "id";
        leaf id {
          type inet:ipv4-address {
            tailf:info
              "A.B.C.D;;ID (IP addr) associated with virtual link neighbor";
          }
        }
        leaf retransmit-interval {
          tailf:info
            "LSA retransmit interval";
          type uint16 {
            tailf:info
              "<1-8192>;;Seconds";
            range "1..8192";
          }
        }
        leaf transmit-delay {
          tailf:info
            "LSA transmission delay";
          type uint16 {
            tailf:info
              "<1-8192>;;Seconds";
            range "1..8192";
          }
          default "1";
        }
        leaf hello-interval {
          tailf:info
            "Hello packet interval";
          type int32 {
            tailf:info
              "<1-8192;;Seconds>";
            range "1..8192";
          }
        }
        leaf dead-interval {
          tailf:info
            "Dead router detection time";
          type uint16 {
            tailf:info
              "<1-8192;;Seconds>";
            range "1..8192";
          }
        }
        leaf authentication {
          tailf:info
            "Set authentication type";
          type empty;
        }
        container authentication-key {
          tailf:info
            "Set authentication key";
          tailf:cli-flatten-container;
          tailf:cli-compact-syntax;
          tailf:cli-sequence-commands {
            tailf:cli-reset-siblings;
          }
          uses password-grouping;
        }
        list message-digest-key {
          tailf:info
            "Set message digest key";
          tailf:cli-suppress-mode;
          tailf:cli-delete-when-empty;
          tailf:cli-compact-syntax;
          tailf:cli-incomplete-command;
          key "id";
          leaf id {
            tailf:cli-suppress-range;
            type uint8 {
              tailf:info
                "<1-255>;;Key ID";
              range "1..255";
            }
          }
          container md5 {
            tailf:info
              "Use MD5 algorithm";
            tailf:cli-compact-syntax;
            tailf:cli-sequence-commands {
              tailf:cli-reset-siblings;
            }
            leaf auth-type {
              tailf:cli-drop-node-name;
              tailf:cli-optional-in-sequence;
              tailf:cli-incomplete-command;
              type uint8 {
                tailf:info
                  "<0-7>;;Encryption type (0 for not yet encrypted, 7 for proprietary)";
                range "0..7";
              }
              default "0";
            }
            leaf auth-key {
              tailf:cli-drop-node-name;
              tailf:cli-full-command;
              type string {
                tailf:info
                  "WORD;;Authentication key (16 chars)";
                length "1..16";
              }
            }
          }
        }
      }
    }
    container auto-cost {
      tailf:info
        "Calculate OSPF interface cost according to bandwidth";
      presence "Calculate OSPF interface cost according to bandwidth";
      leaf reference-bandwidth {
        tailf:info
          "Use reference bandwidth method to assign OSPF cost";
        type uint32 {
          tailf:info
            "<1-4294967>;;The reference bandwidth in terms of Mbits per second";
          range "1..4294967";
        }
      }
    }
    container bfd {
      tailf:info
        "BFD configuration commands";
      leaf all-interfaces {
        tailf:info
          "Enable BFD on all interfaces";
        type empty;
      }
    }
    container interface-id {
      tailf:info
        "Source of the interface ID";
      leaf snmp-if-index {
        tailf:info
          "SNMP MIB ifIndex";
        type empty;
      }
    }
    container log-adjacency-changes {
      tailf:info
        "Log changes in adjacency state";
      tailf:cli-show-no;
      presence "true";
      leaf detail {
        tailf:info
          "Log all state changes";
        type empty;
      }
    }
    container max-lsa {
      tailf:info
        "maximum number of LSAs OSPF process will receive";
      tailf:cli-compact-syntax;
      tailf:cli-sequence-commands {
        tailf:cli-reset-all-siblings;
      }
      leaf maximum-number {
        tailf:cli-drop-node-name;
        type uint32 {
          tailf:info
            "<1-4294967294>;;Maximum number of non self-generated LSAs this process can receive";
          range "1..4294967294";
        }
      }
      leaf threshold-percentage {
        tailf:cli-break-sequence-commands;
        tailf:cli-drop-node-name;
        type uint8 {
          tailf:info
            "<1-100>;;Threshold value (%) at which to generate a warning msg";
          range "1..100";
        }
      }
      leaf warning-only {
        tailf:info
          "Only give warning message when limit is exceeded";
        tailf:cli-full-command;
        type empty;
      }
      leaf ignore-time {
        tailf:info
          "time during which all adjacencies are suppressed";
        type uint32 {
          tailf:info
            "<1-17895>;;number of minutes during which all adjacencies are suppressed";
          range "1..17895";
        }
      }
      leaf reset-time {
        tailf:info
          "time after which ignore-count is reset to zero";
        type uint32 {
          tailf:info
            "<2-35791>;;number of minutes after which ignore-count is reset to zero";
          range "2..35791";
        }
        default "60";
      }
      leaf ignore-count {
        tailf:info
          "maximum number of times adjacencies can be suppressed";
        type uint32 {
          range "1..65534";
          tailf:info
            "<1-65534>;;count on how many times adjacencies can be suppressed";
        }
      }
    }
    uses passive-interface-grouping;
    container queue-depth {
      tailf:info
        "OSPF Hello/Router process queue depth";
      leaf hello {
        tailf:info
          "OSPF Hello process queue depth";
        type union {
          type uint32 {
            tailf:info
              "<1-2147483647>;;maximum numer of packets in the queue";
            range "1..2147483647";
          }
          type enumeration {
            enum "unlimited" {
              tailf:info
                "Unlimited queue depth";
            }
          }
        }
        default "unlimited";
      }
      leaf update {
        tailf:info
          "OSPF Router process queue depth";
        type union {
          type uint32 {
            tailf:info
              "<1-2147483647>;;maximum numer of packets in the queue";
            range "1..2147483647";
          }
          type enumeration {
            enum "unlimited" {
              tailf:info
                "Unlimited queue depth";
            }
          }
        }
      }
    }
    container timers {
      tailf:info
        "Adjust routing timers";
      container lsa {
        tailf:info
          "OSPF LSA timers";
        leaf arrival {
          tailf:info
            "OSPF LSA arrival timer";
          type uint32 {
            range "0..600000";
            tailf:info
              "<0-600000>;;The minimum interval in milliseconds between accepting the same LSA";
          }
        }
      }
      container pacing {
        tailf:info
          "OSPF pacing timers";
        leaf flood {
          tailf:info
            "OSPF flood pacing timer";
          tailf:cli-full-command;
          type uint32 {
            tailf:info
              "<5-100>;;The minimum interval in msec to pace limit flooding on interface";
            range "5..100";
          }
        }
        leaf lsa-group {
          tailf:info
            "OSPF LSA group pacing timer";
          tailf:cli-full-command;
          type uint32 {
            tailf:info
              "<10-1800>;;Interval in sec between group of LSA being refreshed or maxaged";
            range "10..1800";
          }
        }
        leaf retransmission {
          tailf:info
            "OSPF retransmission pacing timer";
          tailf:cli-full-command;
          type uint32 {
            tailf:info
              "<5-200>;;The minimum interval in msec between neighbor retransmissions";
            range "5..200";
          }
        }
      }
      container throttle {
        tailf:info
          "OSPF throttle timers";
        container lsa {
          tailf:info
            "OSPF LSA throttle timers";
          tailf:cli-compact-syntax;
          tailf:cli-sequence-commands;
          leaf all {
            tailf:info
              "For all type of OSPF LSAs";
            tailf:cli-optional-in-sequence;
            tailf:cli-incomplete-command;
            type empty;
          }
          leaf start-interval {
            tailf:cli-drop-node-name;
            tailf:cli-incomplete-command;
            type uint32 {
              tailf:info
                "<0-600000>;;Delay to generate first occurrence of LSA in milliseconds";
              range "0..600000";
            }
          }
          leaf hold-interval {
            tailf:cli-drop-node-name;
            tailf:cli-incomplete-command;
            type uint32 {
              tailf:info
                "<0-600000>;;Minimum delay between originating the same LSA in milliseconds";
              range "0..600000";
            }
          }
          leaf max-interval {
            tailf:cli-drop-node-name;
            type uint32 {
              tailf:info
                "<0-600000>;;Maximum delay between originating the same LSA in milliseconds";
              range "0..600000";
            }
          }
        }
        container spf {
          tailf:info
            "OSPF SPF throttle timers";
          tailf:cli-sequence-commands;
          tailf:cli-compact-syntax;
          leaf spf-start {
            tailf:cli-drop-node-name;
            tailf:cli-incomplete-command;
            type uint32 {
              tailf:info
                "<0-600000>;;Delay between receiving a change to SPF calculation in milliseconds";
              range "0..600000";
            }
          }
          leaf spf-hold {
            tailf:cli-drop-node-name;
            tailf:cli-incomplete-command;
            type uint32 {
              tailf:info
                "<0-600000>;;Delay between first and second SPF calculation in milliseconds";
              range "0..600000";
            }
          }
          leaf spf-max-wait {
            tailf:cli-drop-node-name;
            type uint32 {
              tailf:info
                "<0-600000>;;Maximum wait time in milliseconds for SPF calculations";
              range "0..600000";
            }
          }
        }
      }
    }
    leaf router-id {
      tailf:cli-full-command;
      tailf:info
        "Override configured router identifier (peers will reset)";
      type inet:ipv4-address {
        tailf:info
          "A.B.C.D;;Manually configured router identifier";
      }
    }
  }

  grouping router-ospf-grouping {
    container capability {
      tailf:info
        "Enable specific OSPF feature";
      leaf vrf-lite {
        tailf:info
          "Do not perform PE specific checks";
        type empty;
      }
      leaf opaque {
        tailf:info
          "Opaque LSA";
        tailf:cli-boolean-no;
        tailf:cli-full-command;
        type boolean;
        default "true";
      }
      leaf lls {
        tailf:info
          "Link-local Signaling (LLS) support";
        tailf:cli-boolean-no;
        tailf:cli-full-command;
        type boolean;
        default "true";
      }
      leaf transit {
        tailf:info
          "Transit Area";
        tailf:cli-boolean-no;
        tailf:cli-full-command;
        type boolean;
        default "true";
      }
    }
    container compatible {
      tailf:info
        "OSPF compatibility list";
      leaf rfc1583 {
        tailf:info
          "compatible with RFC 1583";
        tailf:cli-boolean-no;
        type boolean;
        default "true";
      }
    }
    uses router-distribute-list-grouping;
    container domain-id {
      tailf:info
        "OSPF domain-id";
      choice domain-id-choice {
        case a {
          leaf ip-format {
            tailf:cli-drop-node-name;
            type inet:ipv4-address {
              tailf:info
                "A.B.C.D;;OSPF domain ID in IP address format";
            }
          }
          container ip-format-secondary {
            tailf:cli-drop-node-name;
            tailf:cli-compact-syntax;
            tailf:cli-sequence-commands;
            leaf ip {
              tailf:cli-drop-node-name;
              type inet:ipv4-address {
                tailf:info
                  "A.B.C.D;;OSPF domain ID in IP address format";
              }
            }
            leaf secondary {
              tailf:info
                "Secondary Domain-ID";
              type empty;
            }
          }
        }
        leaf Null {
          tailf:info
            "Null Domain-ID";
          tailf:cli-full-command;
          type empty;
        }
        container type {
          tailf:info
            "OSPF domain ID type in Hex format";
          tailf:cli-sequence-commands;
          tailf:cli-compact-syntax;
          leaf type-leaf {
            tailf:cli-drop-node-name;
            tailf:cli-incomplete-command;
            type enumeration {
              enum "0005" {
                tailf:info
                  "Type 0x0005";
              }
              enum "0105" {
                tailf:info
                  "Type 0x0105";
              }
              enum "0205" {
                tailf:info
                  "Type 0x0205";
              }
              enum "8005" {
                tailf:info
                  "Type 0x8005";
              }
            }
          }
          leaf value {
            tailf:info
              "OSPF domain ID value in Hex format";
            type string {
              tailf:info
                "Hex-data;;OSPF domain ID ext. community value in Hex";
              pattern '[0-9a-fA-F]{12}';
            }
          }
        }
      }
    }
    leaf domain-tag {
      tailf:info
        "OSPF domain-tag";
      tailf:cli-full-command;
      type uint32 {
        tailf:info
          "<1-4294967295>;;OSPF domain tag - 32-bit value";
        range "1..4294967295";
      }
    }
    container ignore {
      tailf:info
        "Do not complain about specific event";
      container lsa {
        tailf:info
          "Do not complain upon receiving LSA of the specified type";
        leaf mospf {
          tailf:info
            "MOSPF Type 6 LSA";
          type empty;
        }
      }
    }
    leaf ispf {
      tailf:info
        "Enable incremental SPF computation";
      tailf:cli-full-command;
      type empty;
    }
    container limit {
      tailf:info
        "Limit a specific OSPF feature";
      container retransmissions {
        tailf:info
          "LS update, DBD, and LS request retransmissions";
        tailf:cli-compact-syntax;
        leaf dc {
          tailf:info
            "Demand circuit retransmissions";
          type limit-dc-non-dc-type;
        }
        leaf non-dc {
          tailf:info
            "Non-demand-circuit retransmissions";
          type limit-dc-non-dc-type;
        }
      }
    }
    container local-rib-criteria {
      tailf:info
        "Enable or disable usage of local RIB as route criteria";
      tailf:cli-compact-syntax;
      leaf forwarding-address {
        tailf:info
          "Local RIB used to validate external/NSSA forwarding addresses";
        type empty;
      }
      leaf inter-area-summary {
        tailf:info
          "Local RIB used as criteria for inter-area summaries";
        type empty;
      }
      leaf nssa-translation {
        tailf:info
          "Local RIB used as criteria for NSSA translation";
        type empty;
      }
    }
    container max-metric {
      tailf:info
        "Set maximum metric";
      container router-lsa {
        tailf:info
          "Maximum metric in self-originated router-LSAs";
        tailf:cli-compact-syntax;
        presence "true";
        leaf include-stub {
          tailf:info
            "Set maximum metric for stub links in router-LSAs";
          type empty;
        }
        leaf summary-lsa {
          tailf:info
            "Override summary-lsa metric with max-metric value";
          type empty;
        }
        leaf summary-lsa-max-metric-value {
          when "../summary-lsa" {
            tailf:xpath-root 3;
            tailf:dependency "../summary-lsa";
          }
          tailf:cli-drop-node-name;
          type uint32 {
            tailf:info
              "<1-16777215>;;Overriding metric in summary-LSAs (default 16711680)";
            range "1..16777215";
          }
        }
        leaf external-lsa {
          tailf:info
            "Override external-lsa metric with max-metric value";
          type empty;
        }
        leaf external-lsa-max-metric-value {
          when "../external-lsa" {
            tailf:xpath-root 3;
            tailf:dependency "../external-lsa";
          }
          tailf:cli-drop-node-name;
          type uint32 {
            tailf:info
              "<1-16777215>;;Overriding metric in external-LSAs (default 16711680)";
            range "1..16777215";
          }
        }
        container on-startup {
          tailf:info
            "Set maximum metric temporarily after reboot";
          tailf:cli-flatten-container;
          tailf:cli-compact-syntax;
          choice time-wait-for-bgp-choice {
            leaf seconds {
              tailf:cli-drop-node-name;
              type uint32 {
                tailf:info
                  "<5-86400>;;Time, in seconds, router-LSAs are originated with max-metric";
                range "5..86400";
              }
            }
            leaf wait-for-bgp {
              tailf:info
                "Let BGP decide when to originate router-LSA with normal metric";
              type empty;
            }
          }
        }
      }
    }
    container mpls {
      tailf:info
        "Configure MPLS routing protocol parameters";
      container ldp {
        tailf:info
          "routing protocol commands for MPLS LDP";
        container autoconfig {
          tailf:info
            "Configure LDP automatic configuration";
          presence "Configure LDP automatic configuration";
          leaf area {
            tailf:info
              "Configure an OSPF area to run MPLS LDP";
            type ospf-area-type;
          }
        }
        container sync {
          tailf:info
            "Configure LDP-IGP Synchronization";
          presence "Configure LDP-IGP Synchronization";
        }
      }
      container traffic-eng {
        tailf:info
          "routing protocol commands for MPLS Traffic Engineering";
        container router-id {
          tailf:info
            "Traffic Engineering stable IP address for system";
          uses interface-name-grouping;
        }
        leaf area {
          tailf:info
            "configure an ospf area to run MPLS Traffic Engineering";
          tailf:cli-full-command;
          type ospf-area-type;
        }
        leaf multicast-intact {
          tailf:info
            "MPLS TE and PIM interaction";
          tailf:cli-full-command;
          type empty;
        }
        container interface {
          tailf:info
            "MPLS TE interface configuration for this OSPF process";
          tailf:cli-compact-syntax;
          tailf:cli-sequence-commands {
            tailf:cli-reset-siblings;
          }
          container name {
            tailf:cli-drop-node-name;
            tailf:cli-flatten-container;
            tailf:cli-compact-syntax;
            uses interface-name-grouping;
          }
          leaf area {
            tailf:info
              "advertise MPLS TE information for this interface into area";
            type uint32 {
              tailf:info
                "<0-0>;;OSPF area ID as a decimal value";
            }
          }
        }
        list mesh-group {
          tailf:info
            "Traffic Engineering Mesh-Group advertisement";
          tailf:cli-suppress-mode;
          tailf:cli-delete-when-empty;
          tailf:cli-compact-syntax;
          tailf:cli-sequence-commands {
            tailf:cli-reset-siblings;
          }
          key "id area";
          leaf id {
            type uint32 {
              tailf:info
                "<0-4294967295>;;Mesh Group Id";
            }
          }
          leaf area {
            tailf:cli-expose-key-name;
            tailf:info
              "configure flooding scope as area";
            type ospf-area-type;
          }
          leaf interface {
            tailf:cli-drop-node-name;
            tailf:cli-prefix-key {
              tailf:cli-before-key 2;
            }
            type string {
              tailf:info
                "WORD;;Interface Name";
            }
          }
        }
      }
    }
    list neighbor {
      tailf:info
        "Specify a neighbor router";
      tailf:cli-suppress-mode;
      tailf:cli-delete-when-empty;
      key "ip";
      leaf ip {
        type inet:ipv4-address {
          tailf:info
            "A.B.C.D;;Neighbor address";
        }
      }
      container cost-database-filter-container {
        tailf:cli-drop-node-name;
        tailf:cli-compact-syntax;
        leaf cost {
          tailf:info
            "OSPF cost for point-to-multipoint neighbor";
          type uint32 {
            tailf:info
              "<1-65535>;;metric";
            range "1..65535";
          }
        }
        container database-filter {
          tailf:info
            "Filter OSPF LSA during synchronization and flooding for point-to-multipoint neighbor";
          tailf:cli-flatten-container;
          tailf:cli-compact-syntax;
          container all {
            tailf:info
              "Filter all LSA";
            tailf:cli-flatten-container;
            tailf:cli-compact-syntax;
            leaf out {
              tailf:info
                "Outgoing LSA";
              type empty;
            }
          }
        }
      }
      container poll-interval-priority-container {
        tailf:cli-drop-node-name;
        tailf:cli-compact-syntax;
        leaf poll-interval {
          tailf:info
            "OSPF dead-router polling interval";
          type uint32 {
            tailf:info
              "<0-65535>;;Seconds";
            range "0..65535";
          }
        }
        leaf priority {
          tailf:info
            "OSPF priority of non-broadcast neighbor";
          type uint32 {
            tailf:info
              "<0-255>;;Priority";
            range "0..255";
          }
        }
      }
    }
    list network {
      tailf:info
        "Enable routing on an IP network";
      tailf:cli-suppress-mode;
      tailf:cli-delete-when-empty;
      tailf:cli-incomplete-command;
      key "ip mask";
      leaf ip {
        type inet:ipv4-address {
          tailf:info
            "A.B.C.D;;Network number";
        }
      }
      leaf mask {
        type inet:ipv4-address {
          tailf:info
            "A.B.C.D;;OSPF wild card bits";
        }
      }
      leaf area {
        tailf:info
          "Set the OSPF area ID";
        type ospf-area-type;
      }
    }
    container nsf {
      tailf:info
        "Non-stop forwarding";
      presence "true";
      container cisco {
        tailf:info
          "Cisco Non-stop forwarding";
        tailf:cli-delete-when-empty;
        presence "true";
        container helper {
          tailf:info
            "helper support";
          presence "true";
          leaf disable {
            tailf:info
              "disable helper support";
            tailf:cli-reset-container;
            type empty;
          }
        }
      }
      container ietf {
        tailf:info
          "IETF graceful restart";
        container helper {
          tailf:info
            "helper support";
          presence "helper support";
          leaf disable {
            tailf:info
              "disable helper support";
            tailf:cli-reset-container;
            tailf:cli-delete-container-on-delete;
            type empty;
          }
          leaf strict-lsa-checking {
            tailf:info
              "enable helper strict LSA checking";
            type empty;
          }
        }
      }
    }
    container prefix-priority {
      tailf:info
        "OSPF prefix priority";
      container high {
        tailf:info
          "High prefix priority";
        leaf route-map {
          tailf:info
            "Prefix priority selection by route-map";
          type string {
            tailf:info
              "WORD;;Route map name";
          }
        }
      }
    }
    leaf prefix-suppression {
      tailf:info
        "OSPF prefix suppression";
      tailf:cli-full-command;
      type empty;
    }
    container process-min-time {
      tailf:info
        "Percentage of quantum to be used before releasing CPU";
      leaf percent {
        tailf:info
          "percent";
        type uint32 {
          range "1..100";
          tailf:info
            "<1-100>;;Minimum CPU quantum";
        }
      }
    }
    container traffic-share {
      tailf:info
        "How to compute traffic share over alternate paths";
      container min {
        tailf:info
          "All traffic shared among min metric paths";
        leaf across-interfaces {
          tailf:info
            "Use different interfaces for equal-cost paths";
          type empty;
        }
      }
    }
    leaf shutdown {
      tailf:info
        "Shutdown the OSPF protocol under the current instance";
      tailf:cli-boolean-no;
      type boolean;
    }
    list summary-address {
      tailf:info
        "Configure IP address summaries";
      tailf:cli-suppress-mode;
      tailf:cli-delete-when-empty;
      key "ip wildcard";
      leaf ip {
        type inet:ipv4-address {
          tailf:info
            "A.B.C.D;;IP summary address";
        }
      }
      leaf wildcard {
        type inet:ipv4-address {
          tailf:info
            "A.B.C.D;;Summary mask";
        }
      }
      choice tag-no-advertise-choice {
        leaf tag {
          tailf:info
            "Set tag";
          tailf:cli-full-command;
          type uint32 {
            range "0..4294967295";
            tailf:info
              "<0-4294967295>;;32-bit tag value";
          }
        }
        leaf not-advertise {
          tailf:info
            "Do not advertise when translating OSPF type-7 LSA";
          type empty;
          tailf:cli-full-command;
        }
      }
    }
    container discard-route {
      tailf:info
        "Enable or disable discard-route installation";
      tailf:cli-compact-syntax;
      presence "true";
      leaf external {
        tailf:info
          "Discard route for redistributed summarised routes";
        type uint32 {
          tailf:info
            "<1-255>;;Administrative distance for redistributed summarised routes";
          range "1..255";
        }
      }
      leaf internal {
        tailf:info
          "Discard route for summarised internal routes";
        type uint32 {
          tailf:info
            "<1-255>;;Administrative distance for summarised internal routes";
          range "1..255";
        }
      }
    }
    container fast-reroute {
      tailf:info
        "Configure Fast-Reroute";
      leaf keep-all-paths {
        tailf:info
          "Keep LFA FRR audit trail";
        tailf:cli-full-command;
        type empty;
      }
      container per-prefix {
        tailf:info
          "Per-prefix LFA FRR parameters";
        container enable {
          tailf:info
            "Enable LFA Fast Reroute";
          list area {
            tailf:info
              "Area to enable LFA FRR in";
            tailf:cli-suppress-mode;
            tailf:cli-delete-when-empty;
            tailf:cli-compact-syntax;
            tailf:cli-sequence-commands {
              tailf:cli-reset-siblings;
            }
            key "area";
            leaf area {
              type ospf-area-type;
            }
            leaf prefix-priority {
              tailf:info
                "Priority of prefixes to be protected";
              type enumeration {
                enum "high" {
                  tailf:info
                    "High priority prefixes";
                }
                enum "low" {
                  tailf:info
                    "Low priority prefixes";
                }
              }
            }
          }
          leaf prefix-priority {
            tailf:info
              "Priority of prefixes to be protected";
            type enumeration {
              enum "high" {
                tailf:info
                  "High priority prefixes";
              }
              enum "low" {
                tailf:info
                  "Low priority prefixes";
              }
            }
          }
        }
        container remote-lfa {
          tailf:info
            "Remote LFA FastReroute parameters";
          leaf area {
            tailf:info
              "Area for remote LFA command";
            tailf:cli-full-command;
            type ospf-area-type;
          }
          leaf maximum-cost {
            tailf:info
              "Maximum distance to tunnel endpoint";
            tailf:cli-full-command;
            type uint32 {
              tailf:info
                "<1-16777214>;;Value of the maximum distance to tunnel endpoint";
            }
          }
          leaf tunnel {
            tailf:info
              "Remote LFA tunnel type";
            tailf:cli-full-command;
            type enumeration {
              enum "mpls-ldp" {
                tailf:info
                  "Enable remote LFA tunneling via MPLS";
              }
            }
          }
        }
      }
    }
  }

  grouping router-ospfv3-grouping {
    list summary-prefix {
      tailf:info
        "Configure IP summary prefix";
      tailf:cli-suppress-mode;
      tailf:cli-delete-when-empty;
      tailf:cli-compact-syntax;
      key "prefix";
      leaf prefix {
        type union {
          type ios:ipv4-prefix;
          type ios:ipv6-prefix;
        }
      }
    }
  }

  grouping ospf-redistribute-match-grouping {
    leaf metric {
      tailf:info
        "Metric for redistributed routes";
      type uint32 {
        tailf:info
          "<0-16777214>;;OSPF default metric";
      }
    }
    leaf subnets {
      tailf:info
        "Consider subnets for redistribution into OSPF";
      type empty;
    }
    leaf route-map {
      tailf:info
        "Route map reference";
      type string {
        tailf:info
          "WORD;;Pointer to route-map entries";
      }
    }
    leaf tag {
      tailf:info
        "Set tag for routes redistributed into OSPF";
      type uint32 {
        tailf:info
          "<0-4294967295>;;32-bit tag value";
        range "0..4294967295";
      }
    }
  }

  grouping router-isis-level-grouping {
    leaf level {
      tailf:cli-drop-node-name;
      type enumeration {
        enum "level-1" {
          tailf:info
            "IS-IS level-1 routes only";
        }
        enum "level-1-2" {
          tailf:info
            "IS-IS level-1 and level-2 routes";
        }
        enum "level-2" {
          tailf:info
            "IS-IS level-2 routes only";
        }
      }
    }
  }

  grouping router-ospf-route-map-grouping {
    leaf route-map {
      tailf:info
        "Route map reference";
      tailf:cli-no-name-on-delete;
      tailf:cli-no-value-on-delete;
      type string {
        tailf:info
          "WORD;;Pointer to route-map entries";
      }
    }
  }

  grouping router-ospf-redistribute-grouping {
    leaf metric {
      tailf:info
        "Metric for redistributed routes";
      tailf:cli-no-name-on-delete;
      tailf:cli-no-value-on-delete;
      type uint32 {
        tailf:info
          "<0-16777214>;;OSPF default metric";
      }
    }
    leaf metric-type {
      tailf:info
        "OSPF/IS-IS exterior metric type for redistributed routes";
      tailf:cli-no-name-on-delete;
      tailf:cli-no-value-on-delete;
      type enumeration {
        enum "1" {
          tailf:info
            "Set OSPF External Type 1 metrics";
        }
        enum "2" {
          tailf:info
            "Set OSPF External Type 2 metrics";
        }
      }
      default "2";
    }
    leaf subnets {
      tailf:info
        "Consider subnets for redistribution into OSPF";
      tailf:cli-no-name-on-delete;
      tailf:cli-no-value-on-delete;
      type empty;
    }
    leaf nssa-only {
      tailf:info
        "Limit redistributed routes to NSSA areas";
      tailf:cli-no-name-on-delete;
      tailf:cli-no-value-on-delete;
      type empty;
    }
    leaf tag {
      tailf:info
        "Set tag for routes redistributed into OSPF";
      tailf:cli-no-name-on-delete;
      tailf:cli-no-value-on-delete;
      type uint32 {
        tailf:info
          "<0-4294967295>;;32-bit tag value";
      }
    }
  }

  grouping router-rip-af-grouping {
    leaf auto-summary {
      tailf:info
        "Enable automatic network number summarization";
      tailf:cli-boolean-no;
      tailf:cli-full-command;
      type boolean;
      default "true";
    }
    leaf maximum-paths {
      tailf:info
        "Forward packets over multiple paths";
      tailf:cli-full-command;
      type uint8 {
        tailf:info
          "1-32;;Number of paths";
        range "1..32";
      }
    }
    list neighbor {
      tailf:info
        "Specify a neighbor router";
      tailf:cli-suppress-mode;
      tailf:cli-delete-when-empty;
      key "ip";
      leaf ip {
        type inet:ipv4-address {
          tailf:info
            "A.B.C.D;;Neighbor address";
        }
      }
    }
    list network {
      tailf:info
        "Enable routing on an IP network";
      tailf:cli-suppress-mode;
      tailf:cli-delete-when-empty;
      key "ip";
      leaf ip {
        type inet:ipv4-address {
          tailf:info
            "A.B.C.D;;Network number";
        }
      }
    }
    leaf validate-update-source {
      tailf:info
        "Perform sanity checks against source address of routing updates";
      tailf:cli-boolean-no;
      tailf:cli-full-command;
      type boolean;
      default "true";
    }
    container default-information {
      tailf:info
        "Control distribution of default information";
      container originate {
        tailf:info
          "Distribute a default route";
        presence "true";
        leaf route-map {
          tailf:info
            "Route-map reference";
          type string {
            tailf:info
              "WORD;;Route map name";
          }
        }
      }
    }
    leaf default-metric {
      tailf:info
        "Set metric of redistributed routes";
      tailf:cli-full-command;
      type uint32 {
        tailf:info
          "<1-4294967295>;;Default metric";
        range "1..4294967295";
      }
    }
    container distance {
      tailf:info
        "Define an administrative distance";
      tailf:cli-compact-syntax;
      leaf distance-leaf {
        tailf:cli-drop-node-name;
        tailf:cli-full-command;
        type uint8 {
          tailf:info
            "1-255;;Administrative distance";
          range "1..255";
        }
      }
      list distance-list {
        tailf:cli-drop-node-name;
        tailf:cli-suppress-mode;
        tailf:cli-delete-when-empty;
        tailf:cli-compact-syntax;
        tailf:cli-sequence-commands {
          tailf:cli-reset-siblings;
        }
        key "ip mask";
        leaf number {
          tailf:cli-prefix-key;
          tailf:cli-drop-node-name;
          type uint8 {
            tailf:info
              "1-255;;Administrative distance";
            range "1..255";
          }
        }
        leaf ip {
          type inet:ipv4-address {
            tailf:info
              "A.B.C.D;;IP source address";
          }
        }
        leaf mask {
          type inet:ipv4-address {
            tailf:info
              "A.B.C.D;;Wildcard bits";
          }
        }
        leaf access-list {
          tailf:cli-drop-node-name;
          type std-ip-acl-type;
        }
      }
    }
    uses router-distribute-list-grouping;
    uses router-offset-list-grouping;
    container redistribute {
      tailf:info
        "Redistribute information from another routing protocol";
      container connected {
        tailf:info
          "Connected";
        tailf:cli-compact-syntax;
        presence "true";
        uses router-rip-redistribute-grouping;
      }
      container bgp {
        tailf:info
          "Border Gateway Protocol (BGP)";
        tailf:cli-compact-syntax;
        leaf as-no {
          tailf:cli-drop-node-name;
          type bgp-as-no-type;
        }
        uses router-rip-redistribute-grouping;
      }
      list eigrp {
        tailf:info
          "Enhanced Interior Gateway Routing Protocol (EIGRP)";
        tailf:cli-suppress-mode;
        tailf:cli-delete-when-empty;
        tailf:cli-compact-syntax;
        key "as-no";
        leaf as-no {
          type eigrp-as-no-type;
        }
        uses router-rip-redistribute-grouping;
      }
      container isis {
        tailf:info
          "ISO IS-IS";
        tailf:cli-compact-syntax;
        tailf:cli-delete-when-empty;
        presence "true";
        list isis-list {
          tailf:cli-drop-node-name;
          tailf:cli-suppress-mode;
          tailf:cli-delete-when-empty;
          tailf:cli-compact-syntax;
          key "name";
          leaf name {
            tailf:cli-disallow-value "level-1|level-2|level-1-2|metric|route-map";
            type string {
              tailf:info
                "WORD;;ISO routing area tag";
            }
          }
          leaf level {
            tailf:cli-drop-node-name;
            type isis-level-type;
          }
          uses router-rip-redistribute-grouping;
        }
        leaf level {
          tailf:cli-drop-node-name;
          type isis-level-type;
        }
        uses router-rip-redistribute-grouping;
      }
      container iso-igrp {
        tailf:info
          "IGRP for OSI networks";
        presence "true";
        list iso-igrp-list {
          tailf:info
            "Border Gateway Protocol (BGP)";
          tailf:cli-suppress-mode;
          tailf:cli-delete-when-empty;
          tailf:cli-drop-node-name;
          key "name";
          leaf name {
            tailf:cli-disallow-value "metric|route-map";
            type string {
              tailf:info
                "WORD;;ISO routing area tag";
            }
          }
          uses router-rip-redistribute-grouping;
        }
        uses router-rip-redistribute-grouping;
      }
      container mobile {
        tailf:info
          "Mobile routes";
        tailf:cli-compact-syntax;
        presence "Mobile routes";
        uses router-rip-redistribute-grouping;
      }
      container odr {
        tailf:info
          "On Demand stub Routes";
        tailf:cli-compact-syntax;
        presence "On Demand stub Routes";
        uses router-rip-redistribute-grouping;
      }
      list ospf {
        tailf:info
          "Open Shortest Path First (OSPF)";
        tailf:cli-suppress-mode;
        tailf:cli-delete-when-empty;
        tailf:cli-compact-syntax;
        key "id";
        leaf id {
          tailf:cli-suppress-range;
          type uint16 {
            tailf:info
              "<1-65535>;;Process ID";
            range "1..65535";
          }
        }
        uses router-rip-redistribute-grouping;
        uses redistribute-ospf-match-grouping;
      }
      container static {
        tailf:info
          "Static routes";
        tailf:cli-compact-syntax;
        tailf:cli-delete-when-empty;
        presence "Static routes";
        uses router-rip-redistribute-grouping;
      }
      container rip {
        tailf:info
          "Routing Information Protocol (RIP)";
        tailf:cli-compact-syntax;
        presence "true";
        uses router-rip-redistribute-grouping;
      }
    }
    container timers {
      tailf:info
        "Adjust routing timers";
      tailf:cli-incomplete-no;
      tailf:cli-compact-syntax;
      container basic {
        tailf:info
          "Basic routing protocol update timers";
        tailf:cli-compact-syntax;
        tailf:cli-sequence-commands;
        tailf:cli-full-no;
        leaf updates {
          tailf:cli-drop-node-name;
          tailf:cli-incomplete-command;
          tailf:cli-no-value-on-delete;
          type uint32 {
            tailf:info
              "1-4294967295;;Interval between updates for RIP";
            range "1..4294967295";
          }
        }
        leaf invalid {
          tailf:cli-drop-node-name;
          tailf:cli-incomplete-command;
          tailf:cli-no-value-on-delete;
          type uint32 {
            tailf:info
              "1-4294967295;;Invalid";
            range "1..4294967295";
          }
        }
        leaf holddown {
          tailf:cli-drop-node-name;
          tailf:cli-incomplete-command;
          tailf:cli-no-value-on-delete;
          type uint32 {
            tailf:info
              "1-4294967295;;Holddown";
            range "1..4294967295";
          }
        }
        leaf flush {
          tailf:cli-drop-node-name;
          tailf:cli-incomplete-command;
          tailf:cli-no-value-on-delete;
          type uint32 {
            tailf:info
              "1-4294967295;;Flush";
            range "1..4294967295";
          }
        }
        leaf sleep {
          tailf:cli-drop-node-name;
          tailf:cli-no-value-on-delete;
          type uint32 {
            tailf:info
              "1-4294967295;;Sleep time, in milliseconds";
            range "1..4294967295";
          }
        }
      }
    }
    leaf version {
      tailf:info
        "Set routing protocol version";
      type uint8 {
        tailf:info
          "1-2;;rip version 1 or 2";
        range "1..2";
      }
    }
    container traffic-share {
      tailf:info
        "How to compute traffic share over alternate paths";
      container min {
        tailf:info
          "All traffic shared among min metric paths";
        leaf across-interfaces {
          tailf:info
            "Use different interfaces for equal-cost paths";
          type empty;
        }
      }
    }
  }

  grouping router-rip-grouping {
    uses router-rip-af-grouping;
    uses passive-interface-grouping;
    leaf output-delay {
      tailf:info
        "Interpacket delay for RIP updates";
      tailf:cli-full-command;
      type uint8 {
        tailf:info
          "8-50;;Delay in milliseconds";
        range "8..50";
      }
    }
    leaf input-queue {
      tailf:info
        "Specify input queue depth";
      tailf:cli-full-command;
      type uint16 {
        tailf:info
          "0-1024;;queue depth";
        range "0..1024";
      }
    }
    leaf flash-update-threshold {
      tailf:info
        "Specify flash update threshold in second";
      tailf:cli-full-command;
      type uint8 {
        tailf:info
          "<0-30>;;threshold in seconds";
        range "0..30";
      }
    }
  }

  grouping router-rip-redistribute-grouping {
    leaf metric {
      tailf:info
        "Metric for redistributed routes";
      type union {
        type uint8 {
          tailf:info
            "<0-16>;;Default metric";
          range "0..16";
        }
        type enumeration {
          enum "transparent" {
            tailf:info
              "Transparently redistribute metric";
          }
        }
      }
    }
    leaf route-map {
      tailf:info
        "Route map reference";
      type string {
        tailf:info
          "WORD;;Pointer to route-map entries";
      }
    }
  }

  grouping router-eigrp-redistribute-grouping {
    container metric {
      tailf:info
        "Metric for redistributed routes";
      tailf:cli-break-sequence-commands;
      tailf:cli-flatten-container;
      tailf:cli-compact-syntax;
      tailf:cli-sequence-commands {
        tailf:cli-reset-siblings;
      }
      leaf bandwidth-metric {
        tailf:cli-drop-node-name;
        tailf:cli-incomplete-command;
        type uint32 {
          tailf:info
            "<1-4294967295>;;Bandwidth metric in Kbits per second";
        }
      }
      leaf delay-metric {
        tailf:cli-drop-node-name;
        tailf:cli-incomplete-command;
        type uint32 {
          tailf:info
            "<0-4294967295>;;EIGRP delay metric, in 10 microsecond units";
        }
      }
      leaf reliability-metric {
        tailf:cli-drop-node-name;
        tailf:cli-incomplete-command;
        type uint8 {
          tailf:info
            "<0-255>;;EIGRP reliability metric where 255 is 100% reliable";
        }
      }
      leaf effective-bandwidth-metric {
        tailf:cli-drop-node-name;
        tailf:cli-incomplete-command;
        type uint8 {
          tailf:info
            "<1-255>;;EIGRP Effective bandwidth metric (Loading) where 255 is 100% loaded";
          range "1..255";
        }
      }
      leaf mtu-bytes {
        tailf:cli-drop-node-name;
        type uint16 {
          tailf:info
            "<1-65535>;;EIGRP MTU of the path";
          range "1..65535";
        }
      }
    }
    leaf route-map {
      tailf:info
        "Route map reference";
      type string {
        tailf:info
          "WORD;;Pointer to route-map entries";
      }
    }
  }

  grouping router-eigrp-grouping {
    container metric {
      tailf:info
        "Modify metrics and parameters for advertisement";
      leaf maximum-hops {
        tailf:info
          "Advertise greater than <hops> as unreachable";
        type uint8 {
          tailf:info
            "<1-255>;;Hop count";
          range "1..255";
        }
      }
      container weights {
        tailf:info
          "Modify metric coefficients";
        tailf:cli-compact-syntax;
        tailf:cli-sequence-commands {
          tailf:cli-reset-siblings;
        }
        leaf tos {
          tailf:cli-drop-node-name;
          tailf:cli-incomplete-command;
          type uint8 {
            tailf:info
              "<0-8>;;Type (Only TOS 0 supported)";
            range "0..8";
          }
        }
        leaf k1 {
          tailf:cli-drop-node-name;
          tailf:cli-incomplete-command;
          type uint8 {
            tailf:info
              "<0-255>;;K1";
          }
        }
        leaf k2 {
          tailf:cli-drop-node-name;
          tailf:cli-incomplete-command;
          type uint8 {
            tailf:info
              "<0-255>;;K2";
          }
        }
        leaf k3 {
          tailf:cli-drop-node-name;
          tailf:cli-incomplete-command;
          type uint8 {
            tailf:info
              "<0-255>;;K3";
          }
        }
        leaf k4 {
          tailf:cli-drop-node-name;
          tailf:cli-incomplete-command;
          type uint8 {
            tailf:info
              "<0-255>;;K4";
          }
        }
        leaf k5 {
          tailf:cli-drop-node-name;
          type uint8 {
            tailf:info
              "<0-255>;;K5";
          }
        }
      }
    }
    container network-ip {
      tailf:cli-drop-node-name;
      list network {
        tailf:info
          "Enable routing on an IP network";
        tailf:cli-suppress-mode;
        tailf:cli-delete-when-empty;
        key "ip";
        leaf ip {
          type inet:ipv4-address {
            tailf:info
              "A.B.C.D;;Network number";
          }
        }
      }
    }
    list network {
      tailf:info
        "Enable routing on an IP network";
      tailf:cli-suppress-mode;
      tailf:cli-delete-when-empty;
      key "ip mask";
      leaf ip {
        type inet:ipv4-address {
          tailf:info
            "A.B.C.D;;Network number";
        }
      }
      leaf mask {
        type inet:ipv4-address {
          tailf:info
            "A.B.C.D;;EIGRP wild card bits";
        }
      }
    }
    container neighbor {
      tailf:info
        "Specify a neighbor router";
      list neighbor-list {
        tailf:cli-drop-node-name;
        tailf:cli-suppress-mode;
        tailf:cli-delete-when-empty;
        key "address interface";
        leaf address {
          type inet:ipv4-address {
            tailf:info
              "A.B.C.D;;Neighbor address";
          }
        }
        leaf interface {
          tailf:cli-diff-dependency "/ios:interface" {
            tailf:xpath-root 3;
          }
          type string {
            tailf:info
              "WORD;;Interface name";
          }
        }
      }
    }
    container eigrp {
      tailf:info
        "EIGRP specific commands";
      leaf router-id {
        tailf:info
          "router id for this EIGRP process";
        type inet:ipv4-address {
          tailf:info
            "A.B.C.D;;EIGRP Router-ID in IP address format";
        }
      }
      container stub {
        tailf:info
          "Set address-family in stubbed mode";
        tailf:cli-compact-syntax;
        tailf:cli-reset-container;
        leaf connected {
          tailf:info
            "Do advertise connected routes";
          type empty;
        }
        leaf static {
          tailf:info
            "Do advertise static routes";
          type empty;
        }
        leaf summary {
          tailf:info
            "Do advertise summary routes";
          type empty;
        }
        leaf redistributed {
          tailf:info
            "Do advertise redistributed routes";
          type empty;
        }
      }
      leaf stub-site {
        tailf:info
          "Set address-family in stub-site mode";
        tailf:cli-full-command;
        type string {
          tailf:info
            "ASN:nn or 4BASN:nn Stub-Site ID in aa:nn format";
          pattern '[0-9]+:[0-9]+';
        }
      }
    }
  }

  grouping router-eigrp-base-grouping {
    uses router-distribute-list-grouping;
    container default-metric {
      tailf:info
        "Set metric of redistributed routes";
      tailf:cli-compact-syntax;
      tailf:cli-sequence-commands;
      leaf bandwidth {
        tailf:cli-drop-node-name;
        tailf:cli-incomplete-command;
        type uint32 {
          tailf:info
            "<1-4294967295>;;Bandwidth in Kbits per second";
          range "1..4294967295";
        }
      }
      leaf delay {
        tailf:cli-drop-node-name;
        tailf:cli-incomplete-command;
        type uint32 {
          tailf:info
            "<0-4294967295>;;delay metric in 10 microsecond units";
          range "0..4294967295";
        }
      }
      leaf reliability {
        tailf:cli-drop-node-name;
        tailf:cli-incomplete-command;
        type uint8 {
          tailf:info
            "<0-255>;;Reliability metric where 255 is 100% reliable";
          range "0..255";
        }
      }
      leaf loading {
        tailf:cli-drop-node-name;
        tailf:cli-incomplete-command;
        type uint8 {
          tailf:info
            "<1-255>;;Effective bandwidth metric (Loading) where 255 is 100% loaded";
          range "1..255";
        }
      }
      leaf mtu {
        tailf:cli-drop-node-name;
        type uint16 {
          tailf:info
            "<1-65535>;;Maximum Transmission Unit metric of the path";
          range "1..65535";
        }
      }
    }
    list summary-metric {
      tailf:info
        "Specify summary to apply metric/filtering";
      tailf:cli-suppress-mode;
      tailf:cli-delete-when-empty;
      tailf:cli-compact-syntax;
      tailf:cli-sequence-commands {
        tailf:cli-reset-siblings;
      }
      key "prefix";
      leaf prefix {
        type ios:ipv4-prefix {
          tailf:info
            "A.B.C.D/nn;;Summary <network>/<length>, e.g., 192.168.0.0/16";
        }
      }
      leaf bandwidth {
        tailf:cli-optional-in-sequence;
        tailf:cli-drop-node-name;
        tailf:cli-incomplete-command;
        type uint32 {
          tailf:info
            "<1-4294967295>;;Bandwidth metric in Kbits per second";
        }
      }
      leaf delay {
        when "../bandwidth" {
          tailf:xpath-root 3;
          tailf:dependency "../bandwidth";
        }
        tailf:cli-drop-node-name;
        tailf:cli-incomplete-command;
        type uint32 {
          tailf:info
            "<1-4294967295>;;delay metric in 10 microsecond units";
        }
      }
      leaf reliability {
        when "../delay" {
          tailf:xpath-root 3;
          tailf:dependency "../delay";
        }
        tailf:cli-drop-node-name;
        tailf:cli-incomplete-command;
        type uint8 {
          tailf:info
            "<0-255>;;reliability metric where 255 is 100% reliable";
        }
      }
      leaf load {
        when "../reliability" {
          tailf:xpath-root 3;
          tailf:dependency "../reliability";
        }
        tailf:cli-drop-node-name;
        tailf:cli-incomplete-command;
        type uint8 {
          tailf:info
            "<0-255>;;Effective bandwidth metric (Loading) where 255 is 100% loaded";
        }
      }
      leaf mtu {
        when "../load" {
          tailf:xpath-root 3;
          tailf:dependency "../load";
        }
        tailf:cli-drop-node-name;
        type uint16 {
          tailf:info
            "<1-65535>;;MTU of the path";
          range "1..65535";
        }
      }
      leaf distance {
        tailf:info
          "Set administrative distance for summary route";
        type uint8 {
          tailf:info
            "<1-255>;;Administrative distance";
          range "1..255";
        }
      }
    }
    uses router-offset-list-grouping;
    container redistribute {
      tailf:info
        "Redistribute IPv4 routes from another routing protocol";
      container connected {
        tailf:info
          "Connected";
        tailf:cli-compact-syntax;
        tailf:cli-delete-when-empty;
        presence "true";
        uses router-eigrp-redistribute-grouping;
      }
      container bgp {
        tailf:info
          "Border Gateway Protocol (BGP)";
        tailf:cli-compact-syntax;
        tailf:cli-sequence-commands {
          tailf:cli-reset-all-siblings;
        }
        leaf as-no {
          tailf:cli-drop-node-name;
          type bgp-as-no-type;
        }
        uses router-eigrp-redistribute-grouping;
      }
      list eigrp {
        tailf:info
          "Enhanced Interior Gateway Routing Protocol (EIGRP)";
        tailf:cli-suppress-mode;
        tailf:cli-delete-when-empty;
        tailf:cli-compact-syntax;
        key "as-no";
        leaf as-no {
          type eigrp-as-no-type;
        }
        uses router-eigrp-redistribute-grouping;
      }
      container isis {
        tailf:info
          "ISO IS-IS";
        tailf:cli-compact-syntax;
        presence "true";
        list isis-list {
          tailf:cli-drop-node-name;
          tailf:cli-suppress-mode;
          tailf:cli-delete-when-empty;
          tailf:cli-compact-syntax;
          key "name";
          leaf name {
            tailf:cli-disallow-value "level-1|level-2|level-1-2|metric|route-map";
            type string {
              tailf:info
                "WORD;;ISO routing area tag";
            }
          }
          leaf level {
            tailf:cli-drop-node-name;
            type isis-level-type;
          }
          uses router-eigrp-redistribute-grouping;
        }
        leaf level {
          tailf:cli-drop-node-name;
          type isis-level-type;
        }
        uses router-eigrp-redistribute-grouping;
      }
      container iso-igrp {
        tailf:info
          "IGRP for OSI networks";
        presence "true";
        list iso-igrp-list {
          tailf:info
            "Border Gateway Protocol (BGP)";
          tailf:cli-suppress-mode;
          tailf:cli-delete-when-empty;
          tailf:cli-drop-node-name;
          key "name";
          leaf name {
            tailf:cli-disallow-value "metric|route-map";
            type string {
              tailf:info
                "WORD;;ISO routing area tag";
            }
          }
          uses router-eigrp-redistribute-grouping;
        }
        uses router-eigrp-redistribute-grouping;
      }
      container mobile {
        tailf:info
          "Mobile routes";
        tailf:cli-compact-syntax;
        presence "true";
        uses router-eigrp-redistribute-grouping;
      }
      container odr {
        tailf:info
          "On Demand stub Routes";
        tailf:cli-compact-syntax;
        presence "true";
        uses router-eigrp-redistribute-grouping;
      }
      list ospf {
        tailf:info
          "Open Shortest Path First (OSPF)";
        tailf:cli-suppress-mode;
        tailf:cli-delete-when-empty;
        tailf:cli-compact-syntax;
        key "id";
        leaf id {
          tailf:cli-suppress-range;
          type uint16 {
            tailf:info
              "<1-65535>;;Process ID";
            range "1..65535";
          }
        }
        uses redistribute-ospf-match-grouping;
        uses router-eigrp-redistribute-grouping;
      }
      container static {
        tailf:info
          "Static routes";
        tailf:cli-compact-syntax;
        tailf:cli-delete-when-empty;
        presence "Static routes";
        uses router-eigrp-redistribute-grouping;
      }
      container rip {
        tailf:info
          "Routing Information Protocol (RIP)";
        tailf:cli-compact-syntax;
        presence "true";
        uses router-eigrp-redistribute-grouping;
      }
    }
    container distance {
      tailf:info
        "Define an administrative distance";
      container eigrp {
        tailf:info
          "Set distance for internal and external routes";
        tailf:cli-compact-syntax;
        tailf:cli-sequence-commands;
        leaf internal-distance {
          tailf:cli-drop-node-name;
          tailf:cli-incomplete-command;
          type uint8 {
            tailf:info
              "<1-255>;;Distance for internal routes";
            range "1..255";
          }
        }
        leaf external-distance {
          tailf:cli-drop-node-name;
          type uint8 {
            tailf:info
              "<1-255>;;Distance for external routes";
            range "1..255";
          }
        }
      }
      list distance-list {
        tailf:cli-drop-node-name;
        tailf:cli-suppress-mode;
        tailf:cli-delete-when-empty;
        tailf:cli-compact-syntax;
        tailf:cli-sequence-commands {
          tailf:cli-reset-siblings;
        }
        key "ip-address wildcard-mask";
        leaf ip-address {
          type inet:ipv4-address {
            tailf:info
              "A.B.C.D;;IP source address";
          }
        }
        leaf wildcard-mask {
          type inet:ipv4-address {
            tailf:info
              "A.B.C.D;;Wildcard bits";
          }
        }
        leaf weight {
          tailf:cli-drop-node-name;
          tailf:cli-prefix-key;
          type uint8 {
            tailf:info
              "<1-255>;;Administrative distance";
            range "1..255";
          }
        }
        leaf access-list {
          tailf:cli-drop-node-name;
          type std-ip-acl-type;
        }
      }
    }
    leaf auto-summary {
      tailf:info
        "Enable automatic network number summarization";
      tailf:cli-full-command;
      type empty;
    }
    uses passive-interface-grouping;
  }

  grouping router-eigrp-af-virtual-instance-grouping {
    list af-interface {
      tailf:cli-break-sequence-commands;
      tailf:info
        "Enter Address Family interface configuration";
      tailf:cli-mode-name "config-router-af-interface";
      tailf:cli-exit-command "exit-af-interface" {
        tailf:info
          "Exit from Address Family Interface configuration";
      }
      tailf:cli-show-long-obu-diffs;
      ordered-by user;
      key "name";
      leaf name {
        type string {
          tailf:info
            "WORD;;Interface name";
        }
      }
      list summary-address {
        tailf:info
          "Perform address summarization";
        tailf:cli-suppress-mode;
        tailf:cli-delete-when-empty;
        tailf:cli-compact-syntax;
        key "ip mask";
        leaf ip {
          type inet:ipv4-address {
            tailf:info
              "A.B.C.D;;Summary network address";
          }
        }
        leaf mask {
          type inet:ipv4-address {
            tailf:info
              "A.B.C.D;;Summary network mask";
          }
        }
        leaf leak-map {
          tailf:info
            "Allow dynamic prefixes based on the leak-map";
          type string {
            tailf:info
              "WORD;;leak-map name";
          }
        }
      }
      container summary-address-ipv6 {
        tailf:cli-drop-node-name;
        list summary-address {
          tailf:info
            "Perform address summarization";
          tailf:cli-suppress-mode;
          tailf:cli-delete-when-empty;
          tailf:cli-compact-syntax;
          key "ipv6";
          leaf ipv6 {
            type ipv6-prefix {
              tailf:info
                "X:X:X:X::X/<0-128>;;Summary network prefix";
            }
          }
          leaf leak-map {
            tailf:info
              "Allow dynamic prefixes based on the leak-map";
            type string {
              tailf:info
                "WORD;;leak-map name";
            }
          }
        }
      }
      container authentication {
        tailf:info
          "authentication subcommands";
        container mode {
          tailf:info
            "authentication mode";
          leaf md5 {
            tailf:info
              "Keyed message digest";
            type empty;
          }
        }
        leaf key-chain {
          tailf:info
            "key-chain";
          tailf:cli-full-command;
          type string {
            tailf:info
              "WORD;;name of key-chain";
          }
        }
      }
      leaf hello-interval {
        tailf:info
          "Configures hello interval";
        type uint16 {
          tailf:info
            "<1-65535>;;Seconds between hello transmissions";
          range "1..65535";
        }
      }
      leaf hold-time {
        tailf:info
          "Configures hold time";
        type uint16 {
          tailf:info
            "<1-65535>;;Seconds before neighbor is considered down";
          range "1..65535";
        }
      }
      leaf next-hop-self {
        tailf:info
          "Configures EIGRP next-hop-self";
        tailf:cli-boolean-no;
        tailf:cli-full-command;
        type boolean;
        default "true";
      }
      leaf passive-interface {
        tailf:info
          "Suppress address updates on an interface";
        tailf:cli-show-no;
        type empty;
      }
      leaf split-horizon {
        tailf:info
          "Perform split horizon";
        tailf:cli-boolean-no;
        tailf:cli-full-command;
        type boolean;
        default "true";
      }
      container stub-site {
        tailf:info
          "Stub-Site";
        leaf wan-interface {
          tailf:info
            "Wan Interface";
          type empty;
        }
      }
    }
    container topology {
      tailf:info
        "Topology configuration mode";
      container base {
        tailf:info
          "Base Topology";
        tailf:cli-add-mode;
        tailf:cli-mode-name "config-router-af-topology";
        tailf:cli-exit-command "exit-af-topology" {
          tailf:info
            "Exit from Address Family Topology configuration mode";
        }
        presence "true";
        uses router-eigrp-base-grouping;
      }
    }
    uses router-eigrp-grouping;
  }

  grouping narrow-wide-transition-grouping {
    leaf transition {
      tailf:info
        "Accept both styles of TLVs during transition";
      type empty;
    }
    leaf level {
      tailf:cli-drop-node-name;
      tailf:cli-full-command;
      type isis-level-type;
    }
  }

  grouping spf-intervals-grouping {
    leaf interval {
      tailf:cli-drop-node-name;
      type uint8 {
        tailf:info
          "<1-120>;;Interval between consecutive SPFs in seconds";
        range "1..120";
      }
    }
    leaf initial-wait {
      tailf:cli-drop-node-name;
      type uint32 {
        tailf:info
          "<1-120000>;;Initial wait before first SPF in milliseconds";
        range "1..120000";
      }
    }
    leaf minimum-wait {
      tailf:cli-drop-node-name;
      type uint32 {
        tailf:info
          "<1-120000>;;Minimum wait between first and second SPF in milliseconds";
        range "1..120000";
      }
    }
  }

  grouping router-isis-authenticate-snp-grouping {
    leaf authenticate {
      tailf:info
        "Authentication";
      tailf:cli-incomplete-command;
      type empty;
    }
    leaf snp {
      tailf:info
        "SNP PDUs";
      type enumeration {
        enum "send-only" {
          tailf:info
            "Send but do not check PDUs on receiving";
        }
        enum "validate" {
          tailf:info
            "Send and check PDUs on receiving";
        }
      }
    }
  }

  grouping lsp-gen-interval-grouping {
    leaf interval {
      tailf:cli-drop-node-name;
      type uint32 {
        range "1..120";
        tailf:info
          "<1-120>;;Interval in seconds";
      }
    }
    leaf initial-wait {
      tailf:cli-drop-node-name;
      type uint32 {
        range "1..120000";
        tailf:info
          "<1-120000>;;Initial wait in milliseconds";
      }
    }
    leaf wait {
      tailf:cli-drop-node-name;
      type uint32 {
        range "1..120000";
        tailf:info
          "<1-120000>;;Wait between first and second lsp generation in milliseconds";
      }
    }
  }

  grouping set-overload-bit-suppress-grouping {
    leaf external {
      tailf:info
        "If overload-bit set, don't advertise IP prefixes learned from other protocols";
      tailf:cli-break-sequence-commands;
      type empty;
    }
    leaf interlevel {
      tailf:info
        "If overload-bit set, don't advertise IP prefixes learned from another ISIS level";
      type empty;
    }
  }

  grouping authentication-level-grouping {
    leaf level {
      tailf:cli-drop-node-name;
      type authentication-level-type;
    }
  }

  grouping redist-level-grouping {
    leaf level {
      tailf:cli-drop-node-name;
      tailf:cli-break-sequence-commands;
      type isis-level-type;
    }
  }

  grouping router-isis-redistribute-grouping {
    leaf metric {
      tailf:info
        "ISIS default metric";
      type uint32 {
        tailf:info
          "<0-4294967295>;;ISIS default metric";
        range "0..4294967295";
      }
    }
    leaf route-map {
      tailf:info
        "Route map reference";
      type string {
        tailf:info
          "WORD;;Pointer to route-map entries";
      }
    }
    leaf metric-type {
      tailf:info
        "OSPF/IS-IS exterior metric type for redistributed routes";
      type enumeration {
        enum "external" {
          tailf:info
            "Set IS-IS External metric type";
        }
        enum "internal" {
          tailf:info
            "Set IS-IS Internal metric type";
        }
      }
      default "internal";
    }
    uses router-isis-level-grouping;
  }

  grouping router-isis-af-redistribute-grouping {
    leaf metric {
      tailf:info
        "ISIS default metric";
      type uint32 {
        tailf:info
          "<0-4294967295>;;ISIS default metric";
        range "0..4294967295";
      }
    }
    leaf metric-type {
      tailf:info
        "OSPF/IS-IS exterior metric type for redistributed routes";
      type enumeration {
        enum "external" {
          tailf:info
            "Set IS-IS External metric type";
        }
        enum "internal" {
          tailf:info
            "Set IS-IS Internal metric type";
        }
      }
    }
    uses router-isis-level-grouping;
    leaf route-map {
      tailf:info
        "Route map reference";
      type string {
        tailf:info
          "WORD;;Pointer to route-map entries";
      }
    }
    leaf include-connected {
      tailf:info
        "Include connected";
      type empty;
    }
  }

  grouping isis-redist-ospf-match-grouping {
    uses redist-level-grouping;
    leaf metric {
      tailf:info
        "ISIS default metric";
      type uint32 {
        tailf:info
          "<0-4294967295>;;ISIS default metric";
        range "0..4294967295";
      }
    }
    leaf route-map {
      tailf:info
        "Route map reference";
      type string {
        tailf:info
          "WORD;;Pointer to route-map entries";
      }
    }
  }

  grouping router-isis-interface-grouping {
    container authentication {
      tailf:info
        "ISIS authentication for LSPs";
      container mode {
        tailf:info
          "Authentication mode";
        container md5 {
          tailf:info
            "Keyed message digest";
          presence "true";
          uses authentication-level-grouping;
        }
        container text {
          tailf:info
            "Clear text password";
          presence "true";
          uses authentication-level-grouping;
        }
      }
      container key-chain {
        tailf:info
          "Authentication key-chain";
        tailf:cli-compact-syntax;
        tailf:cli-sequence-commands;
        leaf name {
          tailf:cli-drop-node-name;
          type string {
            tailf:info
              "WORD;;Name of key-chain";
          }
        }
        uses authentication-level-grouping;
      }
      container send-only {
        tailf:info
          "Authentication send only, receive ignore";
        presence "true";
        uses authentication-level-grouping;
      }
    }
  }

  grouping router-isis-af-grouping {
    leaf adjacency-check {
      tailf:info
        "Check ISIS neighbor protocol support";
      tailf:cli-boolean-no;
      tailf:cli-full-command;
      type boolean;
      default "true";
    }
    container set-overload-bit {
      tailf:info
        "Signal other routers not to use us in SPF";
      tailf:cli-delete-when-empty;
      tailf:cli-reset-container;
      presence "true";
      choice set-overload-bit-choice {
        container on-startup {
          tailf:info
            "Set overload-bit only temporarily after reboot";
          choice on-startup-choice {
            container time {
              tailf:cli-drop-node-name;
              tailf:cli-compact-syntax;
              tailf:cli-sequence-commands;
              leaf time {
                tailf:cli-drop-node-name;
                type uint32 {
                  tailf:info
                    "<5-86400>;;Time in seconds to advertise ourself as overloaded after reboot";
                  range "5..86400";
                }
              }
              leaf suppress {
                tailf:info
                  "If overload-bit set, suppress the following types of IP prefixes";
                tailf:cli-incomplete-command;
                type empty;
              }
              uses set-overload-bit-suppress-grouping;
            }
            container wait-for-bgp {
              tailf:info
                "Let BGP decide when to unset the overload bit";
              presence "Let BGP decide when to unset the overload bitW";
              container suppress {
                tailf:info
                  "If overload-bit set, suppress the following types of IP prefixes";
                tailf:cli-compact-syntax;
                tailf:cli-sequence-commands;
                uses set-overload-bit-suppress-grouping;
              }
            }
          }
        }
        container suppress {
          tailf:info
            "If overload-bit set, suppress the following types of IP prefixes";
          tailf:cli-compact-syntax;
          tailf:cli-sequence-commands;
          uses set-overload-bit-suppress-grouping;
        }
      }
    }
    container spf-interval {
      tailf:info
        "Minimum interval between SPF calculations";
      tailf:cli-compact-syntax;
      choice spf-interval-choice {
        list level-1-2 {
          tailf:cli-drop-node-name;
          tailf:cli-suppress-mode;
          tailf:cli-delete-when-empty;
          tailf:cli-compact-syntax;
          tailf:cli-sequence-commands;
          tailf:cli-incomplete-command;
          key "level";
          leaf level {
            type enumeration {
              enum "level-1" {
                tailf:info
                  "Set interval for level 1 only";
              }
              enum "level-2" {
                tailf:info
                  "Set interval for level 2 only";
              }
            }
          }
          uses spf-intervals-grouping;
        }
        container intervals {
          tailf:cli-drop-node-name;
          tailf:cli-compact-syntax;
          tailf:cli-sequence-commands;
          uses spf-intervals-grouping;
        }
      }
    }
    container prc-interval {
      tailf:info
        "Minimum interval between partial route calculations";
      tailf:cli-compact-syntax;
      tailf:cli-sequence-commands;
      leaf interval {
        tailf:cli-drop-node-name;
        type uint32 {
          tailf:info
            "<1-120>;;PRC interval in seconds";
          range "1..120";
        }
      }
      leaf initial-wait {
        tailf:cli-drop-node-name;
        type uint32 {
          tailf:info
            "<1-120000>;;Initial wait for PRC in milliseconds";
          range "1..120000";
        }
      }
      leaf minimum-wait {
        tailf:cli-drop-node-name;
        type uint32 {
          tailf:info
            "<1-120000>;;Minimum wait between first and second PRC in milliseconds";
          range "1..120000";
        }
      }
    }
    container metric-style {
      tailf:info
        "Use old-style (ISO 10589) or new-style packet formats";
      choice metric-style-choice {
        container narrow {
          tailf:info
            "Use old style of TLVs with narrow metric";
          presence "true";
          uses narrow-wide-transition-grouping;
        }
        container transition {
          tailf:info
            "Send and accept both styles of TLVs during transition";
          presence "true";
          leaf level {
            tailf:cli-drop-node-name;
            type isis-level-type;
          }
        }
        container wide {
          tailf:info
            "Use new style of TLVs to carry wider metric";
          presence "true";
          uses narrow-wide-transition-grouping;
        }
      }
    }
    choice metric-choice {
      case default-case {
        container metric {
          tailf:info
            "Set ISIS metric for all interfaces";
          tailf:cli-diff-dependency "../metric-style" {
            tailf:xpath-root 3;
          }
          leaf default {
            tailf:cli-drop-node-name;
            type uint32 {
              tailf:info
                "<1-16777214>;;Default metric";
              range "1..16777214";
            }
          }
        }
      }
      case level-case {
        container metric-level {
          tailf:cli-drop-node-name;
          tailf:cli-diff-dependency "../metric-style" {
            tailf:xpath-root 3;
          }
          list metric {
            tailf:cli-suppress-mode;
            tailf:cli-delete-when-empty;
            tailf:cli-compact-syntax;
            tailf:cli-sequence-commands;
            key "level";
            leaf level {
              type enumeration {
                enum "level-1" {
                  tailf:info
                    "Apply metric to level-1 links";
                }
                enum "level-2" {
                  tailf:info
                    "Apply metric to level-2 links";
                }
              }
            }
            leaf default {
              tailf:cli-drop-node-name;
              tailf:cli-prefix-key;
              type uint32 {
                tailf:info
                  "<1-16777214>;;Default metric";
                range "1..16777214";
              }
            }
          }
        }
      }
    }
    leaf maximum-paths {
      tailf:info
        "Forward packets over multiple paths";
      tailf:cli-full-command;
      type uint32 {
        tailf:info
          "<1-32>;;Number of paths";
        range "1..32";
      }
    }
    container default-information {
      tailf:info
        "Control distribution of default information";
      tailf:cli-incomplete-no;
      container originate {
        tailf:info
          "Distribute a default route";
        presence "true";
        leaf route-map {
          tailf:info
            "Route-map reference";
          type string {
            tailf:info
              "WORD;;Route map name";
          }
        }
      }
    }
  }

  grouping router-isis-grouping {
    container protocol {
      tailf:info
        "Set protocol's administrative state";
      leaf shutdown {
        tailf:info
          "Set protocol's administrative state to disable";
        type empty;
      }
    }
    leaf max-area-addresses {
      tailf:info
        "Allow configuration of more manual area addresses";
      tailf:cli-full-command;
      type uint32 {
        tailf:info
          "<3-254>;;Max number of manual area addresses";
        range "3..254";
      }
    }
    list net {
      tailf:info
        "A Network Entity Title for this process (OSI only)";
      tailf:cli-suppress-mode;
      tailf:cli-delete-when-empty;
      key "tag";
      leaf tag {
        type string {
          tailf:info
            "XX.XXXX. ... .XXX.XX;;Network entity title (NET)";
        }
      }
    }
    leaf is-type {
      tailf:info
        "IS Level for this routing process (OSI only)";
      tailf:cli-full-command;
      type enumeration {
        enum "level-1" {
          tailf:info
            "Act as a station router only";
        }
        enum "level-1-2" {
          tailf:info
            "Act as both a station router and an area router";
        }
        enum "level-2-only" {
          tailf:info
            "Act as an area router only";
        }
      }
    }
    container advertise {
      tailf:info
        "Control which IP routes flow in L1 and L2 LSPs";
      leaf passive-only {
        tailf:info
          "only interface address of passive interfaces";
        type empty;
      }
    }
    uses router-isis-interface-grouping;
    container area-password {
      tailf:info
        "Configure the authentication password for an area";
      tailf:cli-compact-syntax;
      tailf:cli-sequence-commands;
      leaf name {
        tailf:cli-drop-node-name;
        type string {
          tailf:info
            "WORD;;Area password";
        }
      }
      uses router-isis-authenticate-snp-grouping;
    }
    container ispf {
      tailf:info
        "Configure execution of incremental SPF";
      tailf:cli-compact-syntax;
      tailf:cli-sequence-commands;
      leaf level {
        tailf:cli-drop-node-name;
        type enumeration {
          enum "level-1" {
            tailf:info
              "Do incremental SPF for level-1";
          }
          enum "level-1-2" {
            tailf:info
              "Do incremental SPF for both levels";
          }
          enum "level-2" {
            tailf:info
              "Do incremental SPF for level-2";
          }
        }
      }
      leaf number {
        tailf:cli-drop-node-name;
        type uint32 {
          range "1..600";
          tailf:info
            "<1-600>;;Number of seconds before activating incremental-spf";
        }
      }
    }
    container fast-flood {
      tailf:info
        "Flood LSPs (that triggered SPF) before running SPF";
      presence "Flood LSPs (that triggered SPF) before running SPF";
      leaf number {
        tailf:cli-drop-node-name;
        type uint32 {
          range "1..15";
          tailf:info
            "<1-15>;;number of LSPs to be flooded before starting SPF";
        }
      }
    }
    container ip {
      tailf:info
        "IP specific commands";
      container route {
        tailf:info
          "ISIS IP routes";
        container priority {
          tailf:info
            "Assign priority to IP prefixes";
          container high {
            tailf:info
              "Assign high priority to important IP prefixes in ISIS IP local RIB";
            leaf tag {
              tailf:info
                "Assign high priority to IP prefixes with a specific route tag";
              type uint32 {
                range "1..4294967295";
                tailf:info
                  "<1-4294967295>;;tag value";
              }
            }
          }
        }
      }
    }
    container set-attached-bit {
      tailf:info
        "Conditionally advertise us as attached to L2";
      leaf route-map {
        tailf:info
          "Route-map reference";
        type string {
          tailf:info
            "WORD;;Route map name";
        }
      }
    }
    leaf max-lsp-lifetime {
      tailf:info
        "Set maximum LSP lifetime";
      tailf:cli-full-command;
      type uint32 {
        range "1..65535";
        tailf:info
          "<1-65535>;;Maximum LSP lifetime in seconds";
      }
    }
    leaf lsp-refresh-interval {
      tailf:info
        "Set LSP refresh interval";
      tailf:cli-full-command;
      type uint32 {
        range "1..65535";
        tailf:info
          "<1-65535>;;LSP refresh time in seconds";
      }
    }
    container lsp-gen-interval {
      tailf:info
        "Minimum interval between regenerating same LSP";
      choice lsp-gen-interval-choice {
        container intervals {
          tailf:cli-drop-node-name;
          tailf:cli-compact-syntax;
          tailf:cli-sequence-commands;
          uses lsp-gen-interval-grouping;
        }
        container intervals-levels {
          tailf:cli-drop-node-name;
          container intervals-level-1 {
            tailf:cli-drop-node-name;
            tailf:cli-compact-syntax;
            tailf:cli-sequence-commands;
            leaf level-1 {
              tailf:info
                "Set interval for level 1 only";
              type empty;
            }
            uses lsp-gen-interval-grouping;
          }
          container intervals-level-2 {
            tailf:cli-drop-node-name;
            tailf:cli-compact-syntax;
            tailf:cli-sequence-commands;
            leaf level-2 {
              tailf:info
                "Set interval for level 2 only";
              type empty;
            }
            uses lsp-gen-interval-grouping;
          }
        }
      }
    }
    container use {
      tailf:info
        "Use different algorithms during SPF";
      leaf external-metrics {
        tailf:info
          "Honour external metrics during SPF";
        type empty;
      }
    }
    leaf ignore-lsp-errors {
      tailf:info
        "Ignore LSPs with bad checksums";
      tailf:cli-boolean-no;
      tailf:cli-full-command;
      type boolean;
      default "true";
    }
    container hostname {
      tailf:info
        "Dynamic hostname for IS-IS";
      leaf dynamic {
        tailf:info
          "Dynamic hostname";
        tailf:cli-boolean-no;
        type boolean;
        default "true";
      }
    }
    container log-adjacency-changes {
      tailf:info
        "Log changes in adjacency state";
      presence "true";
      leaf all {
        tailf:info
          "Include changes generated by non-IIH event";
        type empty;
      }
    }
    container partition {
      tailf:info
        "CLNS area partition";
      leaf avoidance {
        tailf:info
          "Withdraw area prefix if partition detected";
        type empty;
      }
    }
    leaf lsp-mtu {
      tailf:info
        "Set maximum LSP size";
      tailf:cli-full-command;
      type uint32 {
        range "128..4352";
        tailf:info
          "<128-4352>;;Max LSP size in bytes";
      }
    }
    container lsp-full {
      tailf:info
        "If we run out of LSP fragments";
      container suppress {
        tailf:info
          "suppress the following types of IP prefixes";
        choice lsp-full-choince {
          container external-interlevel-container {
            tailf:cli-drop-node-name;
            tailf:cli-compact-syntax;
            leaf external {
              tailf:info
                "don't advertise IP prefixes learned from other protocols";
              type empty;
            }
            leaf interlevel {
              tailf:info
                "don't advertise IP prefixes learned from another ISIS level";
              type empty;
            }
          }
          leaf none {
            tailf:info
              "don't suppress any prefixes";
            type empty;
          }
        }
      }
    }
    leaf update-queue-depth {
      tailf:info
        "Set Update process queue depth";
      type uint32 {
        tailf:info
          "<1-2147483647>;;Max queue depth";
        range "1..2147483647";
      }
    }
    container nsf {
      tailf:info
        "Non-stop forwarding";
      leaf cisco {
        tailf:info
          "Checkpoint method";
        type empty;
      }
      leaf ietf {
        tailf:info
          "IETF method";
        type empty;
      }
    }
    container bfd {
      tailf:info
        "BFD configuration commands";
      leaf all-interfaces {
        tailf:info
          "Enable BFD on all interfaces";
        type empty;
      }
    }
    container distance {
      tailf:info
        "Define an administrative distance";
      container distance-ip {
        tailf:cli-drop-node-name;
        tailf:cli-compact-syntax;
        tailf:cli-sequence-commands;
        leaf distance {
          tailf:cli-drop-node-name;
          tailf:cli-incomplete-command;
          type uint8 {
            tailf:info
              "<1-255>;;Administrative distance";
            range "1..255";
          }
        }
        leaf ip {
          tailf:info
            "Distance applied for IP derived routes";
          type empty;
        }
      }
      list distance-network-list {
        tailf:cli-drop-node-name;
        tailf:cli-suppress-mode;
        tailf:cli-delete-when-empty;
        tailf:cli-compact-syntax;
        tailf:cli-sequence-commands {
          tailf:cli-reset-siblings;
        }
        key "ip-address wildcard-mask";
        leaf ip-address {
          type inet:ipv4-address {
            tailf:info
              "A.B.C.D;;IP Source address";
          }
        }
        leaf wildcard-mask {
          type inet:ipv4-address {
            tailf:info
              "A.B.C.D;;Wildcard bits";
          }
        }
        leaf distance {
          tailf:cli-drop-node-name;
          tailf:cli-prefix-key;
          type uint8 {
            tailf:info
              "<1-255>;;Administrative distance";
            range "1..255";
          }
        }
        leaf access-list {
          tailf:cli-drop-node-name;
          type std-ip-acl-type;
        }
      }
      container distance-clns {
        tailf:cli-drop-node-name;
        tailf:cli-compact-syntax;
        tailf:cli-sequence-commands;
        leaf distance {
          tailf:cli-drop-node-name;
          tailf:cli-incomplete-command;
          type uint8 {
            tailf:info
              "<1-255>;;OSPF Administrative distance";
            range "1..255";
          }
        }
        leaf clns {
          tailf:info
            "Distance applied for CLNS derived routes";
          type empty;
        }
      }
    }
    container domain-password {
      tailf:info
        "Set the authentication password for a routing domain";
      tailf:cli-sequence-commands;
      tailf:cli-compact-syntax;
      leaf name {
        tailf:cli-drop-node-name;
        type string {
          tailf:info
            "WORD;;Routing domain password";
        }
      }
      uses router-isis-authenticate-snp-grouping;
    }
    choice hello-padding-choice {
      container hello {
        tailf:info
          "Pad ISIS hello PDUs to full MTU";
        leaf padding {
          tailf:info
            "Pad hello PDU";
          tailf:cli-boolean-no;
          tailf:cli-full-command;
          type boolean;
          default "true";
        }
      }
      container conf {
        tailf:cli-drop-node-name;
        container hello {
          tailf:info
            "Pad ISIS hello PDUs to full MTU";
          tailf:cli-incomplete-no;
          tailf:cli-incomplete-command;
          leaf padding {
            tailf:info
              "Pad hello PDU";
            type enumeration {
              enum "multi-point" {
                tailf:info
                  "Pad LAN hello PDUs";
              }
              enum "point-to-point" {
                tailf:info
                  "Pad point-to-point hello PDUs";
              }
            }
          }
        }
      }
    }
    container traffic-share {
      tailf:info
        "How to compute traffic share over alternate paths";
      container min {
        tailf:info
          "All traffic shared among min metric paths";
        leaf across-interfaces {
          tailf:info
            "Use different interfaces for equal-cost paths";
          type empty;
        }
      }
    }
    container microloop {
      tailf:info
        "Enable microloop protection configuration commands";
      container avoidance {
        tailf:info
          "Enable local microloop avoidance";
        tailf:cli-delete-when-empty;
        tailf:cli-reset-container;
        presence "true";
        choice avoidance-choice {
          leaf protected {
            tailf:info
              "Microloop avoidance for protected link or prefix only";
            type empty;
          }
          leaf disable {
            tailf:info
              "Disable Microloop avoidance";
            type empty;
          }
        }
      }
    }
    container segment-routing {
      tailf:info
        "Enable Segment Routing Feature";
      leaf mpls {
        tailf:info
          "Enable Segment Routing Feature using MPLS encapsulation";
        type empty;
      }
    }
    container fast-reroute {
      tailf:info
        "Configure Fast-Reroute";
      container per-prefix {
        tailf:info
          "Enable Fast-Reroute Per-Prefix";
        container level-1 {
          tailf:info
            "Apply to level-1";
          choice level-choice {
            leaf route-map {
              tailf:info
                "route-map for selecting primary paths for protection";
              type string {
                tailf:info
                  "WORD;;route-map name";
              }
            }
            leaf all {
              tailf:info
                "Enable Fast-Reroute for primary paths";
              type empty;
            }
          }
        }
        container level-2 {
          tailf:info
            "Apply to level-2";
          choice level-choice {
            leaf route-map {
              tailf:info
                "route-map for selecting primary paths for protection";
              type string {
                tailf:info
                  "WORD;;route-map name";
              }
            }
            leaf all {
              tailf:info
                "Enable Fast-Reroute for primary paths";
              type empty;
            }
          }
        }
      }
      container remote-lfa {
        tailf:info
          "Configuring fast-reroute remote-lfa";
        container level-1 {
          tailf:info
            "Apply to level-1";
          container mpls-ldp {
            tailf:info
              "Use mpls-ldp tunnel type";
            tailf:cli-delete-when-empty;
            presence "true";
            leaf maximum-metric {
              tailf:info
                "maximum metric to reach release node";
              type uint32 {
                tailf:info
                  "<1-4294967295>;;metric value";
              }
            }
          }
        }
        container level-2 {
          tailf:info
            "Apply to level-2";
          container mpls-ldp {
            tailf:info
              "Use mpls-ldp tunnel type";
            tailf:cli-delete-when-empty;
            presence "true";
            leaf maximum-metric {
              tailf:info
                "maximum metric to reach release node";
              type uint32 {
                tailf:info
                  "<1-4294967295>;;metric value";
              }
            }
          }
        }
      }
    }
    container mpls {
      tailf:info
        "Configure MPLS routing protocol parameters";
      container ldp {
        tailf:info
          "routing protocol commands for MPLS LDP";
        leaf sync {
          tailf:info
            "Configure LDP-IGP Synchronization";
          type empty;
        }
      }
      container traffic-eng {
        tailf:info
          "routing protocol commands for MPLS Traffic Engineering";
        leaf level-1 {
          tailf:info
            "Run MPLS TE on IS-IS level 1 only";
          tailf:cli-full-command;
          type empty;
        }
        leaf level-2 {
          tailf:info
            "Run MPLS TE on IS-IS level 2 only";
          tailf:cli-full-command;
          type empty;
        }
        leaf multicast-intact {
          tailf:info
            "MPLS TE and PIM interaction";
          tailf:cli-full-command;
          type empty;
        }
        container router-id {
          tailf:info
            "Traffic Engineering stable IP address for system";
          uses interface-name-grouping;
        }
        container scanner {
          tailf:info
            "Timer parameters for TE database";
          presence "Timer parameters for TE database";
          tailf:cli-compact-syntax;
          leaf interval {
            tailf:info
              "time (secs) between LSPDB walks for TE";
            type uint32 {
              range "1..60";
              tailf:info
                "<1-60>;;interval between LSPDB walks for TE TLVs extraction";
            }
          }
          leaf max-flash {
            tailf:info
              "Number of ISIS LSPs to be processed with no delay";
            type uint32 {
              range "0..200";
              tailf:info
                "<0-200>;;Max. number of LSPs ISIS may send to TE db without delay";
            }
          }
        }
      }
    }
    uses passive-interface-grouping;
    uses router-distribute-list-grouping;
    container redistribute {
      tailf:info
        "Redistribute information from another routing protocol";
      container maximum-prefix {
        tailf:info
          "Maximum number of prefixes redistributed to protocol";
        tailf:cli-compact-syntax;
        tailf:cli-sequence-commands;
        leaf number {
          tailf:cli-drop-node-name;
          type uint32 {
            tailf:info
              "<1-4294967295>;;Maximum number of IP prefixes redistributed";
            range "1..4294967295";
          }
        }
        leaf threshold-value {
          tailf:cli-drop-node-name;
          tailf:cli-break-sequence-commands;
          type uint32 {
            tailf:info
              "<1-100>;;Threshold value (%) at which to generate a warning message";
            range "1..100";
          }
        }
        leaf warning-only {
          tailf:info
            "Only give warning message when limit is exceeded";
          tailf:cli-full-command;
          type empty;
        }
        leaf withdraw {
          tailf:info
            "Withdraw redistibuted prefixes";
          tailf:cli-full-command;
          type empty;
        }
      }
      container connected {
        tailf:info
          "Connected";
        tailf:cli-compact-syntax;
        tailf:cli-delete-when-empty;
        presence "Connected";
        uses router-isis-redistribute-grouping;
      }
      container static {
        tailf:info
          "Static routes";
        tailf:cli-compact-syntax;
        tailf:cli-delete-when-empty;
        presence "Static routes";
        container clns {
          tailf:info
            "Redistribution of BGP NSAP routes";
          tailf:cli-delete-when-empty;
          presence "true";
          leaf route-map {
            tailf:info
              "Route map reference";
            type string {
              tailf:info
                "WORD;;Pointer to route-map entries";
            }
          }
        }
        container ip {
          tailf:info
            "Redistribution of IP static routes";
          tailf:cli-compact-syntax;
          tailf:cli-delete-when-empty;
          presence "true";
          uses router-isis-redistribute-grouping;
        }
      }
      container odr {
        tailf:info
          "On Demand stub Routes";
        tailf:cli-compact-syntax;
        presence "On Demand stub Routes";
        uses router-isis-redistribute-grouping;
      }
      container rip {
        tailf:info
          "Routing Information Protocol (RIP)";
        tailf:cli-compact-syntax;
        presence "Routing Information Protocol (RIP)";
        uses router-isis-redistribute-grouping;
      }
      list bgp {
        tailf:info
          "Border Gateway Protocol (BGP)";
        tailf:cli-suppress-mode;
        tailf:cli-delete-when-empty;
        tailf:cli-compact-syntax;
        tailf:cli-incomplete-command;
        key "as-no";
        leaf as-no {
          tailf:cli-suppress-range;
          type bgp-as-no-type;
        }
        container clns {
          tailf:info
            "Redistribution of BGP NSAP routes";
          tailf:cli-delete-when-empty;
          presence "true";
          leaf route-map {
            tailf:info
              "Route map reference";
            type string {
              tailf:info
                "WORD;;Pointer to route-map entries";
            }
          }
        }
        uses router-isis-redistribute-grouping;
      }
      list ospf {
        tailf:info
          "Open Shortest Path First (OSPF)";
        tailf:cli-suppress-mode;
        tailf:cli-delete-when-empty;
        tailf:cli-compact-syntax;
        key "id";
        leaf id {
          tailf:cli-suppress-range;
          type uint16 {
            tailf:info
              "<1-65535>;;Process ID";
            range "1..65535";
          }
        }
        uses redistribute-ospf-match-grouping;
        uses router-isis-redistribute-grouping;
      }
      container isis {
        tailf:info
          "ISO IS-IS";
        tailf:cli-compact-syntax;
        list isis-area-list {
          tailf:cli-drop-node-name;
          tailf:cli-suppress-mode;
          tailf:cli-delete-when-empty;
          tailf:cli-compact-syntax;
          tailf:cli-incomplete-command;
          key "area-tag";
          leaf area-tag {
            tailf:cli-disallow-value "ip";
            type string {
              tailf:info
                "WORD;;ISO routing area tag";
            }
          }
          leaf ip {
            tailf:info
              "Redistribution of IP routes between levels or processes";
            type empty;
          }
          leaf metric {
            tailf:info
              "ISIS default metric";
            type uint32 {
              tailf:info
                "<0-4294967295>;;ISIS default metric";
              range "0..4294967295";
            }
          }
          leaf route-map {
            tailf:info
              "Route map reference";
            type string {
              tailf:info
                "WORD;;Pointer to route-map entries";
            }
          }
        }
        list ip {
          tailf:info
            "Redistribution of IP routes between levels";
          tailf:cli-suppress-mode;
          tailf:cli-delete-when-empty;
          tailf:cli-compact-syntax;
          tailf:cli-incomplete-command;
          key "from into";
          leaf from {
            type enumeration {
              enum "level-1" {
                tailf:info
                  "Inter-area routes from level-1";
              }
              enum "level-2" {
                tailf:info
                  "Inter-area routes from level-2";
              }
            }
          }
          leaf into {
            tailf:info
              "from level-n into level-m";
            tailf:cli-expose-key-name;
            type enumeration {
              enum "level-1" {
                tailf:info
                  "Inter-area routes from level-1";
              }
              enum "level-2" {
                tailf:info
                  "Inter-area routes from level-2";
              }
            }
          }
          leaf distribute-list {
            tailf:info
              "select routes";
            type uint8 {
              tailf:info
                "<100-199>;;IP extended acces-list number";
              range "100..199";
            }
          }
          leaf route-map {
            tailf:info
              "Route map for route matching";
            type string {
              tailf:info
                "WORD;;Name of the route-map";
            }
          }
        }
      }
      list eigrp {
        tailf:info
          "Enhanced Interior Gateway Routing Protocol (EIGRP)";
        tailf:cli-suppress-mode;
        tailf:cli-delete-when-empty;
        tailf:cli-compact-syntax;
        key "as-no";
        leaf as-no {
          type eigrp-as-no-type;
        }
        uses router-isis-redistribute-grouping;
      }
      container iso-igrp {
        tailf:info
          "IGRP for OSI networks";
        presence "IGRP for OSI networks";
        tailf:cli-compact-syntax;
        tailf:cli-sequence-commands;
        choice iso-igrp-choice {
          container area-tag-route-map-container {
            tailf:cli-drop-node-name;
            tailf:cli-flatten-container;
            tailf:cli-compact-syntax;
            tailf:cli-sequence-commands;
            leaf area-tag {
              tailf:cli-drop-node-name;
              tailf:cli-disallow-value "route-map";
              type string {
                tailf:info
                  "WORD;;ISO routing area tag";
              }
            }
            leaf route-map {
              tailf:info
                "Route map reference";
              type string {
                tailf:info
                  "WORD;;Pointer to route-map entries";
              }
            }
          }
          leaf route-map {
            tailf:info
              "Route map reference";
            type string {
              tailf:info
                "WORD;;Pointer to route-map entries";
            }
          }
        }
        uses redist-level-grouping;
        leaf metric {
          tailf:info
            "ISIS default metric";
          type uint32 {
            tailf:info
              "<0-4294967295>;;ISIS default metric";
            range "0..4294967295";
          }
        }
        leaf metric-type {
          tailf:info
            "OSPF/IS-IS exterior metric type for redistributed routes";
          type enumeration {
            enum "external" {
              tailf:info
                "Set IS-IS External metric type";
            }
            enum "internal" {
              tailf:info
                "Set IS-IS Internal metric type";
            }
          }
        }
      }
      container mobile {
        tailf:info
          "Mobile routes";
        tailf:cli-compact-syntax;
        presence "Mobile routes";
        uses router-isis-redistribute-grouping;
      }
    }
    list summary-address {
      tailf:info
        "Configure IP address summaries";
      tailf:cli-suppress-mode;
      tailf:cli-delete-when-empty;
      tailf:cli-compact-syntax;
      key "ip mask";
      leaf ip {
        type inet:ipv4-address {
          tailf:info
            "A.B.C.D;;IP summary address";
        }
      }
      leaf mask {
        type inet:ipv4-address {
          tailf:info
            "A.B.C.D;;Summary mask";
        }
      }
      leaf level {
        tailf:cli-drop-node-name;
        type enumeration {
          enum "level-1" {
            tailf:info
              "Summarize into level-1 area";
          }
          enum "level-1-2" {
            tailf:info
              "Summarize into both area and sub-domain";
          }
          enum "level-2" {
            tailf:info
              "Summarize into level-2 sub-domain";
          }
        }
      }
      leaf tag {
        tailf:info
          "Set tag";
        type uint32 {
          tailf:info
            "<1-4294967295>;;32-bit tag value";
          range "1..4294967295";
        }
      }
      leaf metric {
        tailf:info
          "Set metric for summay route";
        type uint32 {
          tailf:info
            "<1-4294967295>;;metric";
          range "1..4294967295";
        }
      }
    }
    uses router-isis-af-grouping;
    container address-family {
      tailf:info
        "Enter Address Family command mode";
      container ipv6 {
        tailf:info
          "Address family";
        tailf:cli-add-mode;
        tailf:cli-mode-name "config-router-af";
        tailf:cli-exit-command "exit-address-family" {
          tailf:info
            "Exit from Address Family configuration mode";
        }
        leaf af {
          tailf:cli-drop-node-name;
          tailf:cli-hide-in-submode;
          tailf:cli-full-command;
          type enumeration {
            enum "unicast" {
              tailf:info
                "Address Family Modifier";
            }
          }
          default "unicast";
        }
        uses router-isis-af-grouping;
        list summary-prefix {
          tailf:info
            "Configure IPv6 summary prefix";
          tailf:cli-suppress-mode;
          tailf:cli-delete-when-empty;
          tailf:cli-compact-syntax;
          key "prefix";
          leaf prefix {
            type ipv6-prefix {
              tailf:info
                "X:X:X:X::X/<0-128>;;IPv6 prefix x:x::y/<z>";
            }
          }
          leaf level {
            tailf:cli-drop-node-name;
            type enumeration {
              enum "level-1" {
                tailf:info
                  "Summarize into level-1 area";
              }
              enum "level-1-2" {
                tailf:info
                  "Summarize into both area and sub-domain";
              }
              enum "level-2" {
                tailf:info
                  "Summarize into level-2 sub-domain";
              }
            }
          }
          leaf tag {
            tailf:info
              "Set tag";
            type uint32 {
              tailf:info
                "<1-4294967295>;;32-bit tag value";
            }
          }
        }
        leaf distance {
          tailf:info
            "Administrative distance";
          tailf:cli-full-command;
          type uint32 {
            tailf:info
              "<1-255>;;OSPF Administrative distance";
            range "1..255";
          }
        }
        container multi-topology {
          tailf:info
            "Enable multi-topology mode";
          presence "Enable multi-topology mode";
          leaf transition {
            tailf:info
              "Accept and generate both IS-IS IPv6 and Multi-topology IPv6 TLVs";
            type empty;
          }
        }
        container redistribute {
          tailf:info
            "Redistribute IPv6 prefixes from another routing protocol";
          container connected {
            tailf:info
              "Connected";
            tailf:cli-compact-syntax;
            tailf:cli-delete-when-empty;
            presence "Connected";
            uses router-isis-af-redistribute-grouping;
          }
          container static {
            tailf:info
              "Static routes";
            tailf:cli-compact-syntax;
            tailf:cli-delete-when-empty;
            presence "Static routes";
            uses router-isis-redistribute-grouping;
          }
          container bgp {
            tailf:info
              "Border Gateway Protocol (BGP)";
            tailf:cli-compact-syntax;
            leaf as-no {
              tailf:cli-drop-node-name;
              type bgp-as-no-type;
            }
            uses router-isis-af-redistribute-grouping;
          }
          list ospf {
            tailf:info
              "Open Shortest Path First (OSPF)";
            tailf:cli-suppress-mode;
            tailf:cli-delete-when-empty;
            tailf:cli-compact-syntax;
            key "id";
            leaf id {
              tailf:cli-suppress-range;
              type uint16 {
                tailf:info
                  "<1-65535>;;Process ID";
                range "1..65535";
              }
            }
            uses redistribute-ospf-match-grouping;
            uses router-isis-af-redistribute-grouping;
          }
          list rip {
            tailf:info
              "IPv6 Routing Information Protocol (RIPv6)";
            tailf:cli-suppress-mode;
            tailf:cli-delete-when-empty;
            tailf:cli-compact-syntax;
            key "process";
            leaf process {
              type string {
                tailf:info
                  "WORD;;User selected string identifying this process";
              }
            }
            uses router-isis-af-redistribute-grouping;
          }
          list eigrp {
            tailf:info
              "Enhanced Interior Gateway Routing Protocol (EIGRP)";
            tailf:cli-suppress-mode;
            tailf:cli-delete-when-empty;
            tailf:cli-compact-syntax;
            key "as-no";
            leaf as-no {
              type eigrp-as-no-type;
            }
            uses router-isis-af-redistribute-grouping;
          }
          container isis {
            tailf:info
              "ISO IS-IS";
            tailf:cli-compact-syntax;
            list isis-list {
              tailf:cli-drop-node-name;
              tailf:cli-suppress-mode;
              tailf:cli-delete-when-empty;
              tailf:cli-compact-syntax;
              tailf:cli-incomplete-command;
              key "from into";
              leaf from {
                type enumeration {
                  enum "level-1" {
                    tailf:info
                      "Inter-area routes from level-1";
                  }
                  enum "level-2" {
                    tailf:info
                      "Inter-area routes from level-2";
                  }
                }
              }
              leaf into {
                tailf:info
                  "from level-n into level-m";
                tailf:cli-expose-key-name;
                type enumeration {
                  enum "level-1" {
                    tailf:info
                      "Inter-area routes from level-1";
                  }
                  enum "level-2" {
                    tailf:info
                      "Inter-area routes from level-2";
                  }
                }
              }
              leaf distribute-list {
                tailf:info
                  "select routes";
                type string {
                  tailf:info
                    "WORD;;IPv6 prefix-list name";
                }
              }
              leaf route-map {
                tailf:info
                  "Route map for route matching";
                type string {
                  tailf:info
                    "WORD;;Name of the route-map";
                }
              }
            }
          }
          container nemo {
            tailf:info
              "Network Mobility (NEMO)";
            tailf:cli-compact-syntax;
            tailf:cli-delete-when-empty;
            uses router-isis-af-redistribute-grouping;
          }
        }
      }
    }
  }

  grouping router-lisp-database-mapping-grouping {
    list database-mapping {
      tailf:info
        "Configures Locator addresses for an ETR";
      tailf:cli-incomplete-command;
      tailf:cli-suppress-mode;
      tailf:cli-delete-when-empty;
      tailf:cli-compact-syntax;
      tailf:cli-sequence-commands;
      key "prefix";
      max-elements 100;
      leaf prefix {
        type union {
          type ios:ipv4-prefix {
            tailf:info
              "A.B.C.D/nn;;EID-prefix to advertise locators for (max 100 prefixes)";
          }
          type ios:ipv6-prefix {
            tailf:info
              "X:X:X:X::X/<0-128>;;EID-prefix to advertise locators for (max 100 prefixes)";
          }
        }
      }
      choice rloc-choice {
        leaf ipv4-address {
          tailf:cli-drop-node-name;
          tailf:cli-incomplete-command;
          type inet:ipv4-address {
            tailf:info
              "A.B.C.D;;IPv4 Address of loopback or other ETR interface";
          }
        }
        container IPv4-interface {
          tailf:info
            "Use IPv4 address of interface as locator";
          tailf:cli-flatten-container;
          tailf:cli-compact-syntax;
          tailf:cli-incomplete-command;
          uses interface-name-grouping;
        }
        container IPv6-interface {
          tailf:info
            "Use IPv6 address of interface as locator";
          tailf:cli-flatten-container;
          tailf:cli-compact-syntax;
          tailf:cli-incomplete-command;
          uses interface-name-grouping;
        }
        leaf ipv6-address {
          tailf:cli-drop-node-name;
          tailf:cli-incomplete-command;
          type inet:ipv6-address {
            tailf:info
              "X:X:X:X::X;;IPv6 Address of loopback or other ETR interface";
          }
        }
        leaf auto-discover-rlocs {
          tailf:info
            "Auto discover locators registered by other xTRs";
          tailf:cli-full-command;
          type empty;
        }
        leaf locator-set {
          tailf:info
            "Use locators defined by locator-set";
          tailf:cli-full-command;
          type string {
            tailf:info
              "WORD;;Existing locator set";
          }
        }
      }
      leaf priority {
        tailf:info
          "Configures which Locators from a set are preferred";
        tailf:cli-incomplete-command;
        type uint8 {
          tailf:info
            "<0-255>;;Lower priority Locator takes preference";
        }
      }
      leaf weight {
        tailf:info
          "Traffic load-spreading among Locators";
        type uint8 {
          tailf:info
            "<0-100>;;Relative weight of locator";
        }
      }
    }
  }

  grouping router-lisp-af4-common-grouping {
    leaf map-request-source {
      tailf:info
        "Configures inner header source address in Map-Request message";
      type inet:ipv4-address {
        tailf:info
          "A.B.C.D;;IPv4 Source address of inner header in Map-Request message";
      }
    }
    container proxy-itr {
      tailf:info
        "Configures a LISP Proxy Ingress Tunnel Router (PITR)";
      tailf:cli-compact-syntax;
      tailf:cli-sequence-commands {
        tailf:cli-reset-siblings;
      }
      leaf ipv4-local-locator {
        tailf:cli-drop-node-name;
        tailf:cli-optional-in-sequence;
        type inet:ipv4-address {
          tailf:info
            "A.B.C.D;;IPv4 address in ITR-RLOC field of map-request";
        }
      }
      leaf ipv6-local-locator {
        tailf:cli-drop-node-name;
        type inet:ipv6-address {
          tailf:info
            "X:X:X:X::X;;IPv6 address in ITR-RLOC field of map-request";
        }
      }
    }
  }

  grouping router-lisp-af6-common-grouping {
    leaf map-request-source {
      tailf:info
        "Configures inner header source address in Map-Request message";
      type inet:ipv6-address {
        tailf:info
          "X:X:X:X::X;;IPv6 Source address of inner header in Map-Request message";
      }
    }
    container proxy-itr {
      tailf:info
        "Configures a LISP Proxy Ingress Tunnel Router (PITR)";
      tailf:cli-compact-syntax;
      leaf ipv6-local-locator {
        tailf:cli-drop-node-name;
        tailf:cli-reset-container;
        type inet:ipv6-address {
          tailf:info
            "X:X:X:X::X;;IPv6 address in ITR-RLOC field of map-request";
        }
      }
      leaf ipv4-local-locator {
        tailf:cli-drop-node-name;
        type inet:ipv4-address {
          tailf:info
            "A.B.C.D;;IPv4 address in ITR-RLOC field of map-request";
        }
      }
    }
  }

  grouping router-lisp-af-grouping {
    leaf map-resolver {
      tailf:info
        "Configures a LISP Map Resolver (MR)";
      type empty;
    }
    container map-resolver-conf {
      tailf:cli-drop-node-name;
      container map-resolver {
        tailf:info
          "Configures a LISP Map Resolver (MR)";
        tailf:cli-incomplete-command;
        tailf:cli-incomplete-no;
        container map-request {
          tailf:info
            "Map-Request processing options";
          container validate {
            tailf:info
              "Validation options";
            container source {
              tailf:info
                "Influence which source RLOCs map requests are accepted from";
              tailf:cli-compact-syntax;
              tailf:cli-reset-container;
              leaf registered {
                tailf:info
                  "...from RLOCs that register EID-prefixes in the same IID on a co-located MapServer";
                tailf:cli-optional-in-sequence;
                type empty;
              }
              container list {
                tailf:info
                  "Define allowed prefixes using an ip[v6] prefix list";
                choice list-choice {
                  leaf ipv4 {
                    tailf:info
                      "IPv4 prefixes";
                    type string {
                      tailf:info
                        "WORD;;IPv4 prefix-list name";
                    }
                  }
                  leaf ipv6 {
                    tailf:info
                      "IPv6 prefixes";
                    type string {
                      tailf:info
                        "WORD;;IPv6 prefix-list name";
                    }
                  }
                }
              }
            }
          }
        }
      }
    }
    container itr {
      tailf:info
        "Configures a LISP Ingress Tunnel Router (ITR)";
      tailf:cli-incomplete-command;
      tailf:cli-incomplete-no;
      list map-resolver {
        tailf:cli-suppress-mode;
        tailf:cli-delete-when-empty;
        key "address";
        leaf address {
          type union {
            type inet:ipv4-address {
              tailf:info
                "IPv4 Address of map resolver";
            }
            type inet:ipv6-address {
              tailf:info
                "IPv6 Address of map resolver";
            }
          }
        }
      }
      leaf enable {
        tailf:cli-drop-node-name;
        type empty;
      }
    }
    container etr {
      tailf:info
        "Configures a LISP Egress Tunnel Router (ETR)";
      tailf:cli-incomplete-command;
      tailf:cli-incomplete-no;
      list map-server {
        tailf:cli-suppress-mode;
        tailf:cli-delete-when-empty;
        tailf:cli-incomplete-command;
        tailf:cli-incomplete-no;
        key "address";
        leaf address {
          type union {
            type inet:ipv4-address {
              tailf:info
                "IPv4 Address of map server";
            }
            type inet:ipv6-address {
              tailf:info
                "IPv6 Address of map server";
            }
          }
        }
        container key {
          tailf:info
            "Authentication key used with map server";
          tailf:cli-compact-syntax;
          tailf:cli-sequence-commands;
          uses crypto-key-grouping;
          leaf hash-function {
            tailf:info
              "Map-Register authentication type";
            type enumeration {
              enum "sha1" {
                tailf:info
                  "Use the SHA-1-96 hash function";
              }
              enum "sha2" {
                tailf:info
                  "Use the SHA-256-128 hash function";
              }
            }
          }
        }
      }
      leaf enable {
        tailf:cli-drop-node-name;
        type empty;
      }
    }
    leaf map-cache-limit {
      tailf:info
        "Configures maximum size of map-cache";
      type uint32 {
        tailf:info
          "<0-100000>;;Maximum number of map-cache entries";
        range "0..100000";
      }
    }
    container map-cache-persistent {
      tailf:info
        "Dump map-cache onto flash, making it persistent across reboots";
      tailf:meta-data "suppress-delete-error-invalid";
      presence "true";
      leaf interval {
        tailf:info
          "Interval in minutes of how often the map-cache is saved";
        type uint16 {
          tailf:info
            "<1-1440>;;Interval in minutes, default 60";
          range "1..1440";
        }
      }
    }
    container route-import {
      tailf:info
        "Import RIB routes by a routing protocol into LISP";
      container database {
        tailf:info
          "Use RIB routes to define local EID database entries";
        list static-list {
          tailf:cli-drop-node-name;
          tailf:cli-suppress-mode;
          tailf:cli-delete-when-empty;
          tailf:cli-compact-syntax;
          tailf:cli-sequence-commands {
            tailf:cli-reset-siblings;
          }
          tailf:cli-incomplete-command;
          key "protocol";
          leaf protocol {
            type enumeration {
              enum "connected" {
                tailf:info
                  "Connected";
              }
              enum "static" {
                tailf:info
                  "Static routes";
              }
              enum "rip" {
                tailf:info
                  "Routing Information Protocol (RIP)";
              }
            }
          }
          leaf route-map {
            tailf:info
              "Route map for route selection filtering";
            tailf:cli-optional-in-sequence;
            type string {
              tailf:info
                "WORD;;Route map name";
            }
          }
          leaf locator-set {
            tailf:info
              "Locator set to use with created database mapping entries";
            type string {
              tailf:info
                "WORD;;Locator set name";
            }
          }
        }
        list id-list {
          tailf:cli-drop-node-name;
          tailf:cli-suppress-mode;
          tailf:cli-delete-when-empty;
          tailf:cli-compact-syntax;
          tailf:cli-sequence-commands {
            tailf:cli-reset-siblings;
          }
          tailf:cli-incomplete-command;
          key "protocol id";
          leaf protocol {
            type enumeration {
              enum "bgp" {
                tailf:info
                  "Border Gateway Protocol (BGP)";
              }
              enum "eigrp" {
                tailf:info
                  "Enhanced Interior Gateway Routing Protocol (EIGRP)";
              }
              enum "isis" {
                tailf:info
                  "ISO IS-IS";
              }
              enum "ospf" {
                tailf:info
                  "Open Shortest Path First (OSPF)";
              }
              enum "ospfv3" {
                tailf:info
                  "OSPFv3";
              }
              enum "rip" {
                tailf:info
                  "Routing Information Protocol (RIP)";
              }
            }
          }
          leaf id {
            tailf:cli-disallow-value "route-map";
            type string {
              tailf:info
                "WORD;;Process id";
            }
          }
          leaf route-map {
            tailf:info
              "Route map for route selection filtering";
            tailf:cli-optional-in-sequence;
            type string {
              tailf:info
                "WORD;;Route map name";
            }
          }
          leaf locator-set {
            tailf:info
              "Locator set to use with created database mapping entries";
            type string {
              tailf:info
                "WORD;;Locator set name";
            }
          }
        }
      }
    }
    container route-export {
      tailf:info
        "Export routes into RIB from LISP";
      leaf site-registration {
        tailf:info
          "Export LISP site registrations to RIB";
        type empty;
      }
    }
    container map-cache {
      tailf:info
        "Address family specific map cache configuration";
      leaf site-registration {
        tailf:info
          "Install map cache to map request for site registrations";
        type empty;
      }
    }
    leaf proxy-etr {
      tailf:info
        "Configures a LISP Proxy Engress Tunnel Router (PETR)";
      tailf:cli-full-command;
      type empty;
    }
    list use-petr {
      tailf:info
        "Encapsulate to Proxy ETR when matching forward-native entry";
      tailf:cli-suppress-mode;
      tailf:cli-delete-when-empty;
      tailf:cli-compact-syntax;
      tailf:cli-sequence-commands;
      key "address";
      leaf address {
        type union {
          type inet:ipv4-address {
            tailf:info
              "A.B.C.D;;IPv4 locator address of PETR";
          }
          type inet:ipv6-address {
            tailf:info
              "X:X:X:X::X;;IPv6 locator address of PETR";
          }
        }
      }
      leaf priority {
        tailf:info
          "Configures which Locators from a set are preferred";
        tailf:cli-incomplete-command;
        type uint8 {
          tailf:info
            "<0-255>;;Lower priority Locator takes preference";
        }
      }
      leaf weight {
        tailf:info
          "Traffic load-spreading among Locators";
        type uint8 {
          tailf:info
            "<0-100>;;Relative weight of locator";
          range "0..100";
        }
      }
    }
    leaf map-server {
      tailf:info
        "Configures a LISP Map Server (MS)";
      type empty;
    }
  }

  grouping router-lisp-eid-table-grouping {
    leaf instance-id {
      tailf:info
        "EID instance-ID";
      tailf:cli-hide-in-submode;
      type uint32 {
        tailf:info
          "<0-16777214>;;Instance-ID";
        range "0..16777214";
      }
    }
    list map-cache {
      tailf:cli-suppress-mode;
      tailf:cli-delete-when-empty;
      tailf:cli-compact-syntax;
      tailf:cli-sequence-commands;
      tailf:cli-incomplete-command;
      key "prefix";
      leaf prefix {
        type union {
          type ios:ipv4-prefix {
            tailf:info
              "A.B.C.D/nn;;IPv4 EID-prefix for RLOC static mapping";
          }
          type ios:ipv6-prefix {
            tailf:info
              "X:X:X:X::X/<0-128>;;IPv6 EID-prefix for RLOC static mapping";
          }
        }
      }
      choice map-cache-choice {
        case locator {
          leaf locator {
            tailf:cli-drop-node-name;
            tailf:cli-incomplete-command;
            type union {
              type inet:ipv4-address {
                tailf:info
                  "A.B.C.D;;IPv4 Address of loopback or other ETR interface";
              }
              type inet:ipv6-address {
                tailf:info
                  "X:X:X:X::X;;IPv6 Address of loopback or other ETR interface";
              }
            }
          }
          leaf priority {
            tailf:info
              "Lower priority Locator takes preference";
            tailf:cli-incomplete-command;
            type uint8 {
              tailf:info
                "<0-255>;;Lower priority Locator takes preference";
            }
          }
          leaf weight {
            tailf:info
              "Traffic load-spreading among Locators";
            type uint8 {
              tailf:info
                "<0-100>;;Relative weight of locator";
              range "0..100";
            }
          }
        }
        leaf map-request {
          tailf:info
            "Send Map-Request for LISP destination EID";
          tailf:cli-full-command;
          type empty;
        }
        leaf native-forward {
          tailf:info
            "Natively forward packets that match this map-cache entry";
          tailf:cli-full-command;
          type empty;
        }
        leaf drop {
          tailf:info
            "Drop packets that match this map-cache entry";
          tailf:cli-full-command;
          type empty;
        }
      }
    }
    uses router-lisp-database-mapping-grouping;
    container loc-reach-algorithm {
      tailf:info
        "Configure locator reachability algorithm";
      leaf lsb-reports {
        tailf:info
          "Configure data packet LSB report handling";
        type enumeration {
          enum "ignore" {
            tailf:info
              "Ignore data packet LSB reports";
          }
        }
      }
      leaf rloc-probing {
        tailf:info
          "Probe high priority RLOCs with Map-Requests as last resort";
        type empty;
      }
    }
    container ipv4 {
      tailf:info
        "IPv4 address family";
      uses router-lisp-af-grouping;
      uses router-lisp-af4-common-grouping;
    }
    container ipv6 {
      tailf:info
        "IPv6 address family";
      uses router-lisp-af-grouping;
      uses router-lisp-af6-common-grouping;
    }
  }

  grouping router-lisp-service-af-grouping {
    container eid-table {
      tailf:info
        "Bind an eid-table";
      leaf default {
        tailf:info
          "Default VRF";
        type empty;
      }
      leaf vrf {
        tailf:info
          "VRF name";
        tailf:cli-diff-dependency "/ios:vrf/definition" {
          tailf:xpath-root 3;
        }
        type string {
          tailf:info
            "WORD;;VRF name";
        }
      }
    }
    uses router-lisp-database-mapping-grouping;
    leaf encapsulation {
      tailf:info
        "Select encapsulation type for data packets";
      type enumeration {
        enum "lisp" {
          tailf:info
            "Use LISP encapsulation for data packets";
        }
        enum "vxlan" {
          tailf:info
            "Use VXLAN encapsulation for data packets";
        }
      }
    }
  }

  grouping router-lisp-service-grouping {
    container service {
      tailf:info
        "Select service type";
      container ipv4 {
        tailf:info
          "Select service type as IPv4";
        tailf:cli-add-mode;
        tailf:cli-mode-name "config-router-lisp-serv-ipv4";
        tailf:cli-exit-command "exit-service-ipv4" {
          tailf:info
            "Exit from LISP service-ipv4 configuration mode";
        }
        presence "true";
        uses router-lisp-service-af-grouping;
        uses router-lisp-af-grouping;
        uses router-lisp-af4-common-grouping;
      }
      container ipv6 {
        tailf:info
          "Select service type as IPv6";
        tailf:cli-add-mode;
        tailf:cli-mode-name "config-router-lisp-serv-ipv6";
        tailf:cli-exit-command "exit-service-ipv6" {
          tailf:info
            "Exit from LISP service-ipv6 configuration mode";
        }
        presence "true";
        uses router-lisp-service-af-grouping;
        uses router-lisp-af-grouping;
        uses router-lisp-af6-common-grouping;
      }
    }
  }

  grouping router-lisp-grouping {
    container syslog {
      tailf:info
        "Configure syslog option";
      leaf verbose {
        tailf:info
          "Enable verbose syslog";
        type empty;
      }
      container session {
        tailf:info
          "Enable session syslog";
        leaf changes {
          tailf:info
            "Enable session change syslog";
          type empty;
        }
      }
    }
    container etr {
      tailf:info
        "Configures a LISP Egress Tunnel Router (ETR)";
      container map-server {
        tailf:info
          "Configures map server for ETR registration";
        container source-address {
          tailf:info
            "Configures map server source address";
          uses interface-name-grouping;
        }
      }
    }
    container locator-table {
      tailf:info
        "Specify the RLOC table";
      choice locator-table-choice {
        leaf default {
          tailf:info
            "Default VRF";
          type empty;
        }
        leaf vrf {
          tailf:info
            "VRF name";
          type string {
            tailf:info
              "WORD;;VRF name";
          }
        }
      }
    }
    list locator-set {
      tailf:info
        "Configure a named locator set";
      tailf:cli-mode-name "config-router-lisp-locator-set";
      tailf:cli-full-command;
      key "name";
      leaf name {
        type string {
          tailf:info
            "Configure a named locator set";
        }
      }
      list IPv4-address {
        tailf:cli-drop-node-name;
        tailf:cli-suppress-mode;
        tailf:cli-delete-when-empty;
        tailf:cli-compact-syntax;
        tailf:cli-sequence-commands;
        tailf:cli-incomplete-command;
        key "name";
        leaf name {
          type inet:ipv4-address {
            tailf:info
              "A.B.C.D;;IP address";
          }
        }
        leaf priority {
          tailf:info
            "Configures which Locators from a set are preferred";
          tailf:cli-incomplete-command;
          type uint8 {
            tailf:info
              "<0-255>;;Lower priority Locator takes preference";
          }
        }
        leaf weight {
          tailf:info
            "Traffic load-spreading among Locators";
          type uint8 {
            tailf:info
              "<0-100>;;Relative weight of locator";
            range "0..100";
          }
        }
      }
      list IPv6-address {
        tailf:cli-drop-node-name;
        tailf:cli-suppress-mode;
        tailf:cli-delete-when-empty;
        tailf:cli-compact-syntax;
        tailf:cli-sequence-commands;
        tailf:cli-incomplete-command;
        key "name";
        leaf name {
          type inet:ipv6-address {
            tailf:info
              "X:X:X:X::X;;Address of loopback or other ETR interface";
          }
        }
        leaf priority {
          tailf:info
            "Configures which Locators from a set are preferred";
          tailf:cli-incomplete-command;
          type uint8 {
            tailf:info
              "<0-255>;;Lower priority Locator takes preference";
          }
        }
        leaf weight {
          tailf:info
            "Traffic load-spreading among Locators";
          type uint8 {
            tailf:info
              "<0-100>;;Relative weight of locator";
            range "0..100";
          }
        }
      }
      list IPv4-interface {
        tailf:info
          "Use IPv4 address of interface as locator";
        tailf:cli-suppress-mode;
        tailf:cli-delete-when-empty;
        tailf:cli-compact-syntax;
        tailf:cli-sequence-commands;
        tailf:cli-incomplete-command;
        key "name";
        leaf name {
          type string {
            tailf:info
              "WORD;;Interface name";
          }
        }
        leaf priority {
          tailf:info
            "Configures which Locators from a set are preferred";
          tailf:cli-incomplete-command;
          type uint8 {
            tailf:info
              "<0-255>;;Lower priority Locator takes preference";
          }
        }
        leaf weight {
          tailf:info
            "Traffic load-spreading among Locators";
          type uint8 {
            tailf:info
              "<0-100>;;Relative weight of locator";
            range "0..100";
          }
        }
      }
      list IPv6-interface {
        tailf:info
          "Use IPv6 address of interface as locator";
        tailf:cli-suppress-mode;
        tailf:cli-delete-when-empty;
        tailf:cli-compact-syntax;
        tailf:cli-sequence-commands;
        tailf:cli-incomplete-command;
        key "name";
        leaf name {
          type string {
            tailf:info
              "WORD;;Interface name";
          }
        }
        leaf priority {
          tailf:info
            "Configures which Locators from a set are preferred";
          tailf:cli-incomplete-command;
          type uint8 {
            tailf:info
              "<0-255>;;Lower priority Locator takes preference";
          }
        }
        leaf weight {
          tailf:info
            "Traffic load-spreading among Locators";
          type uint8 {
            tailf:info
              "<0-100>;;Relative weight of locator";
            range "0..100";
          }
        }
      }
      leaf auto-discover-rlocs {
        tailf:info
          "Auto discover locators registered by other xTRs";
        type empty;
      }
    }
    uses router-lisp-service-grouping {
      refine "service/ipv4" {
        tailf:cli-diff-dependency "../../locator-set" {
          tailf:xpath-root 3;
        }
      }
      refine "service/ipv6" {
        tailf:cli-diff-dependency "../../locator-set" {
          tailf:xpath-root 3;
        }
      }
      refine "service/ipv4/etr/map-server/key/secret" {
        tailf:meta-data "secret-password" {
          tailf:meta-value "router lisp<NL><*>service ipv4<NL><*> ::  etr map-server <map-server> key <PASSWORD>";
        }
      }
      refine "service/ipv6/etr/map-server/key/secret" {
        tailf:meta-data "secret-password" {
          tailf:meta-value "router lisp<NL><*>service ipv6<NL><*> ::  etr map-server <map-server> key <PASSWORD>";
        }
      }
    }
    container map-request {
      tailf:info
        "Configure map-request handling";
      leaf itr-rlocs {
        tailf:info
          "Configure to use the specified RLOC set as ITR RLOC in map-request";
        type string {
          tailf:info
            "WORD;;Existing locator set";
        }
        tailf:non-strict-leafref {
          path "../../locator-set/name";
        }
      }
    }
    container eid-table {
      tailf:info
        "Configure an EID instance for a VRF";
      tailf:cli-diff-dependency "../locator-set" {
        tailf:xpath-root 3;
      }
      list default-vrf {
        tailf:cli-drop-node-name;
        tailf:cli-mode-name "config-router-lisp-eid-table";
        tailf:cli-explicit-exit;
        tailf:cli-incomplete-command;
        key "name";
        leaf name {
          type enumeration {
            enum "default" {
              tailf:info
                "Default VRF";
            }
          }
        }
        uses router-lisp-eid-table-grouping;
      }
      list vrf {
        tailf:info
          "VRF name";
        tailf:cli-mode-name "config-router-lisp-eid-table";
        tailf:cli-explicit-exit;
        tailf:cli-incomplete-command;
        key "name";
        leaf name {
          tailf:cli-suppress-range;
          type string {
            tailf:info
              "WORD;;VRF name";
          }
        }
        uses router-lisp-eid-table-grouping;
      }
    }
    container loc-reach-algorithm {
      tailf:info
        "Configure locator reachability algorithm";
      leaf rloc-probing {
        tailf:info
          "Probe high priority RLOCs with Map-Requests as last resort";
        type empty;
      }
    }
    list site {
      tailf:info
        "Configure a LISP site on a map server (MS)";
      tailf:cli-mode-name "config-router-lisp-site";
      tailf:cli-full-command;
      key "name";
      leaf name {
        type string {
          tailf:info
            "WORD;;The site name";
        }
      }
      leaf description {
        tailf:info
          "Provide a description string for the LISP site";
        tailf:cli-multi-value;
        tailf:cli-preformatted;
        tailf:cli-full-command;
        type string {
          tailf:info
            "LINE;;Site description";
        }
      }
      container authentication-key {
        tailf:info
          "Authentication key used by LISP site";
        tailf:cli-compact-syntax;
        tailf:cli-sequence-commands;
        uses crypto-key-grouping;
      }
      list eid-prefix {
        tailf:info
          "Site EID address prefix";
        tailf:cli-suppress-mode;
        tailf:cli-delete-when-empty;
        tailf:cli-compact-syntax;
        key "prefix";
        leaf prefix {
          type union {
            type ios:ipv4-prefix {
              tailf:info
                "A.B.C.D/nn;;IPv4 EID prefix belonging to the SITE";
            }
            type ios:ipv6-prefix {
              tailf:info
                "X:X:X:X::X/<0-128>;;IPv6 EID prefix belonging to the SITE";
            }
          }
        }
        leaf route-tag {
          tailf:info
            "ALT RIB route tag for EID prefix";
          type uint32 {
            tailf:info
              "<0-4294967295>;;RIB route tag";
          }
        }
        leaf accept-more-specifics {
          tailf:info
            "Accept registrations for more specific EID prefixes";
          type empty;
        }
      }
      container eid-prefix-instance {
        tailf:cli-drop-node-name;
        list eid-prefix {
          tailf:cli-suppress-mode;
          tailf:cli-delete-when-empty;
          tailf:cli-compact-syntax;
          key "instance-id prefix";
          leaf instance-id {
            tailf:info
              "EID instance-ID";
            tailf:cli-expose-key-name;
            type uint32 {
              tailf:info
                "<1-16777214>;;Instance-ID";
              range "1..16777214";
            }
          }
          leaf prefix {
            type union {
              type ios:ipv4-prefix {
                tailf:info
                  "A.B.C.D/nn;;IPv4 EID prefix belonging to the SITE";
              }
              type ios:ipv6-prefix {
                tailf:info
                  "X:X:X:X::X/<0-128>;;IPv6 EID prefix belonging to the SITE";
              }
            }
          }
          leaf route-tag {
            tailf:info
              "ALT RIB route tag for EID prefix";
            type uint32 {
              tailf:info
                "<0-4294967295>;;RIB route tag";
            }
          }
          leaf accept-more-specifics {
            tailf:info
              "Accept registrations for more specific EID prefixes";
            type empty;
          }
        }
      }
      list allowed-locator {
        tailf:info
          "Locator from LISP site";
        tailf:cli-suppress-mode;
        tailf:cli-delete-when-empty;
        key "rloc";
        leaf rloc {
          type union {
            type inet:ipv4-address {
              tailf:info
                "A.B.C.D;;IPv4 locator allowed in registered locator-set";
            }
            type inet:ipv6-address {
              tailf:info
                "X:X:X:X::X;;IPv6 locator allowed in registered locator-set";
            }
          }
        }
      }
    }
    container ipv4 {
      tailf:info
        "IPv4 address family";
      uses router-lisp-af-grouping {
        refine "map-cache-persistent" {
          tailf:cli-show-no;
        }
      }
      uses router-lisp-af4-common-grouping;
    }
    container ipv6 {
      tailf:info
        "IPv6 address family";
      uses router-lisp-af-grouping {
        refine "map-cache-persistent" {
          tailf:cli-show-no;
        }
      }
      uses router-lisp-af6-common-grouping;
    }
    list instance-id {
      tailf:info
        "EID instance-ID";
      tailf:cli-mode-name "config-router-lisp-inst";
      tailf:cli-diff-dependency "../locator-set" {
        tailf:xpath-root 3;
      }
      tailf:cli-diff-dependency "/ios:vrf/definition" {
        tailf:xpath-root 3;
      }
      key "id";
      leaf id {
        tailf:cli-suppress-range;
        type uint32 {
          tailf:info
            "<0-16777214>;;Instance-ID";
          range "0..16777214";
        }
      }
      uses router-lisp-service-grouping {
        refine "service/ipv4/etr/map-server/key/secret" {
          tailf:meta-data "secret-password" {
            tailf:meta-value "router lisp<NL><*> instance-id <instance-id><NL><*>  service ipv4<NL><*> ::  etr map-server <map-server> key <PASSWORD>";
          }
        }
        refine "service/ipv6/etr/map-server/key/secret" {
          tailf:meta-data "secret-password" {
            tailf:meta-value "router lisp<NL><*> instance-id <instance-id><NL><*>  service ipv6<NL><*> ::  etr map-server <map-server> key <PASSWORD>";
          }
        }
      }
    }
  }

  grouping ip-nat-outside-source-grouping {
    leaf redundancy {
      tailf:cli-break-sequence-commands;
      tailf:info
        "NAT redundancy operation";
      type uint8 {
        tailf:info
          "<1-2>;IP redundancy ID";
      }
    }
    leaf mapping-id {
      when "../redundancy" {
        tailf:xpath-root 3;
        tailf:dependency "../redundancy";
      }
      tailf:info
        "Associate a mapping id to this mapping";
      type uint32 {
        tailf:info
          "<1-2147483647>;;Stateful NAT mapping id";
        range "1..2147483647";
      }
    }
    leaf add-route {
      tailf:info
        "Add a static route for outside local address";
      type empty;
    }
    leaf no-payload {
      tailf:info
        "No translation of embedded address/port in the payload";
      type empty;
    }
  }

  grouping ip-nat-source-static-grouping {
    leaf redundancy {
      tailf:cli-break-sequence-commands;
      tailf:info
        "NAT redundancy operation";
      type union {
        type uint8 {
          tailf:info
            "<1-2>;IP redundancy ID";
        }
        type string {
          tailf:info
            "WORD;;IP redundancy name";
        }
      }
    }
    leaf mapping-id {
      when "../redundancy" {
        tailf:xpath-root 3;
        tailf:dependency "../redundancy";
      }
      tailf:info
        "Associate a mapping id to this mapping";
      type uint32 {
        tailf:info
          "<1-2147483647>;;Stateful NAT mapping id";
        range "1..2147483647";
      }
    }
    leaf extendable {
      tailf:info
        "Extend this translation when used";
      type empty;
    }
    leaf no-alias {
      tailf:info
        "Do not create an alias for the global address";
      type empty;
    }
    leaf no-payload {
      tailf:info
        "No translation of embedded address/port in the payload";
      type empty;
    }
    leaf add-route {
      tailf:info
        "Add a static route for outside local address";
      type empty;
    }
    leaf route-map {
      tailf:info
        "Specify route-map";
      type string {
        tailf:info
          "WORD;;Route-map name";
      }
    }
    leaf reversible {
      when "../route-map" {
        tailf:xpath-root 3;
        tailf:dependency "../route-map";
      }
      type empty;
    }
    leaf match-in-vrf {
      tailf:info
        "Match incoming vrf";
      type empty;
    }
    leaf forced {
      tailf:info
        "Delete this entry and its children, even if in use";
      type empty;
    }
    leaf overload {
      tailf:info
        "Overload an address translation";
      type empty;
    }
  }

  grouping ip-nat-inside-options-grouping {
    leaf no-payload {
      tailf:cli-break-sequence-commands;
      tailf:info
        "No translation of embedded address/port in the payload";
      type empty;
    }
    leaf reversible {
      tailf:info
        "Allow out->in traffic";
      type empty;
    }
    leaf overload {
      tailf:info
        "Overload an address translation";
      type empty;
    }
    leaf oer {
      tailf:info
        "Use with vtemplate only. On new translation, if OER BR is UP, OER will select IP from outgoing Interface. All packets matching translation are forwarded over Interface for duration of translation.";
      type empty;
    }
  }

  grouping ip-nat-inside-grouping {
    leaf pool {
      tailf:info
        "Name pool of global addresses";
      tailf:cli-optional-in-sequence;
      tailf:non-strict-leafref {
        path "/ncs:devices/ncs:device/ncs:config/ios:ip/nat/pool/id" {
          tailf:xpath-root 3;
        }
      }
      type string {
        tailf:info
          "WORD;;Pool name for global addresses";
      }
    }
    leaf redundancy {
      tailf:info
        "NAT redundancy operation";
      tailf:cli-optional-in-sequence;
      type uint8 {
        tailf:info
          "<1-2>;;IP redundancy ID";
        range "1..2";
      }
    }
    leaf mapping-id {
      tailf:info
        "Associate a mapping id to this mapping";
      tailf:cli-optional-in-sequence;
      type uint32 {
        tailf:info
          "<1-2147483647>;;Stateful NAT mapping id";
        range "1..2147483647";
      }
    }
    leaf interface {
      when "not(../pool)" {
        tailf:xpath-root 3;
        tailf:dependency "../pool";
      }
      tailf:info
        "Specify interface for global address";
      tailf:cli-optional-in-sequence;
      tailf:cli-diff-dependency "../../../../../../interface" {
        tailf:xpath-root 3;
      }
      type string {
        tailf:info
          "WORD;;Interface name";
      }
    }
  }

  grouping ip-nat-inside-vrf-grouping {
    leaf pool {
      tailf:info
        "Name pool of global addresses";
      tailf:cli-prefix-key {
        tailf:cli-before-key 2;
      }
      tailf:cli-optional-in-sequence;
      type string {
        tailf:info
          "WORD;;Pool name for global addresses";
      }
      tailf:non-strict-leafref {
        path "/ncs:devices/ncs:device/ncs:config/ios:ip/nat/pool/id" {
          tailf:xpath-root 3;
        }
      }
    }
    leaf redundancy {
      tailf:info
        "NAT redundancy operation";
      tailf:cli-prefix-key {
        tailf:cli-before-key 2;
      }
      tailf:cli-optional-in-sequence;
      type uint8 {
        tailf:info
          "<1-2>;;IP redundancy ID";
        range "1..2";
      }
    }
    leaf mapping-id {
      tailf:info
        "Associate a mapping id to this mapping";
      tailf:cli-prefix-key {
        tailf:cli-before-key 2;
      }
      tailf:cli-optional-in-sequence;
      type uint32 {
        tailf:info
          "<1-2147483647>;;Stateful NAT mapping id";
        range "1..2147483647";
      }
    }
    leaf interface {
      when "not(../pool)" {
        tailf:xpath-root 3;
        tailf:dependency "../pool";
      }
      tailf:info
        "Specify interface for global address";
      tailf:cli-prefix-key {
        tailf:cli-before-key 2;
      }
      tailf:cli-optional-in-sequence;
      tailf:cli-diff-dependency "../../../../../../../interface" {
        tailf:xpath-root 3;
      }
      type string {
        tailf:info
          "WORD;;Interface name";
      }
    }
    leaf vrf {
      tailf:info
        "Specify vrf";
      tailf:cli-expose-key-name;
      type string {
        tailf:info
          "WORD;;vrf name";
      }
    }
    leaf match-in-vrf {
      tailf:info
        "Match incoming vrf";
      tailf:cli-optional-in-sequence;
      type empty;
    }
  }

  grouping mobile-ip-spi-grouping {
    choice spi-type-choice {
      leaf hex {
        tailf:cli-drop-node-name;
        type string {
          tailf:info
            "<100-FFFFFFFF>;;SPI hex value";
        }
      }
      leaf decimal {
        tailf:info
          "decimal Security parameter index - bidirectional";
        type uint32 {
          tailf:info
            "<256-4294967295>;;SPI decimal value";
          range "256..4294967295";
        }
      }
    }
  }

  grouping xconnect-interface-grouping {
    choice xconnect-choice {
      container xconnect {
        tailf:cli-add-mode;
        tailf:cli-mode-name "config-xconn";
        tailf:cli-compact-syntax;
        tailf:cli-sequence-commands;
        tailf:cli-diff-dependency "../encapsulation" {
          tailf:xpath-root 3;
        }
        leaf address {
          tailf:cli-drop-node-name;
          tailf:cli-incomplete-command;
          tailf:cli-hide-in-submode;
          type inet:ipv4-address {
            tailf:info
              "A.B.C.D;;IP address of peer";
          }
        }
        leaf vcid {
          tailf:cli-drop-node-name;
          tailf:cli-incomplete-command;
          tailf:cli-hide-in-submode;
          type uint32 {
            tailf:info
              "<1-4294967295>;;Enter VC ID value";
            range "1..4294967295";
          }
        }
        leaf encapsulation {
          tailf:info
            "Data encapsulation method";
          tailf:cli-hide-in-submode;
          type enumeration {
            enum "mpls" {
              tailf:info
                "Use MPLS encapsulation";
            }
            enum "l2tpv3" {
              tailf:info
                "Use L2TPv3 encapsulation";
            }
          }
        }
        leaf manual {
          tailf:info
            "Manually configure session parameters";
          tailf:cli-optional-in-sequence;
          tailf:cli-hide-in-submode;
          type empty;
        }
        leaf pw-class {
          tailf:info
            "Optional pseudowire-class to use for advanced configuration";
          tailf:cli-optional-in-sequence;
          tailf:cli-hide-in-submode;
          type string {
            tailf:info
              "WORD;;Pseudowire-class name";
          }
          tailf:non-strict-leafref {
            path "/ncs:devices/ncs:device/ncs:config/ios:pseudowire-class/name" {
              tailf:xpath-root 3;
            }
          }
        }
        leaf sequencing {
          tailf:info
            "Configure sequencing options for xconnect";
          tailf:cli-full-command;
          tailf:cli-hide-in-submode;
          when "../encapsulation = 'l2tpv3'" {
            tailf:xpath-root 3;
            tailf:dependency "../encapsulation";
          }
          type enumeration {
            enum "both" {
              tailf:info
                "Transmit and receive sequence numbers";
            }
            enum "receive" {
              tailf:info
                "Receive sequence numbers";
            }
            enum "transmit" {
              tailf:info
                "Transmit sequence numbers";
            }
          }
        }
        container backup {
          tailf:cli-break-sequence-commands;
          tailf:info
            "Xconnect backup configuration commands";
          container peer {
            tailf:info
              "Backup pseudowire";
            tailf:cli-compact-syntax;
            tailf:cli-sequence-commands {
              tailf:cli-reset-siblings;
            }
            leaf peer-router-ip-addr {
              tailf:cli-drop-node-name;
              tailf:cli-incomplete-command;
              type inet:ipv4-address {
                tailf:info
                  "A.B.C.D;;IP address of peer";
              }
            }
            leaf vcid {
              tailf:cli-drop-node-name;
              type uint32 {
                tailf:info
                  "<1-4294967295>;;Enter VC ID value";
                range "1..4294967295";
              }
            }
            leaf pw-class {
              tailf:cli-optional-in-sequence;
              type string {
                tailf:info
                  "Optional Pseudowire-class to use for backup pseudowire";
              }
              tailf:non-strict-leafref {
                path "/ncs:devices/ncs:device/ncs:config/ios:pseudowire-class/name" {
                  tailf:xpath-root 3;
                }
              }
            }
            leaf priority {
              tailf:info
                "Optional priority to use for backup pseudowire.";
              type uint8 {
                tailf:info
                  "Peer priority";
                range "1..10";
              }
            }
          }
          container delay {
            tailf:info
              "Backup delay";
            tailf:cli-compact-syntax;
            tailf:cli-sequence-commands;
            leaf enable-delay {
              tailf:cli-drop-node-name;
              tailf:cli-incomplete-command;
              type uint8 {
                tailf:info
                  "<0-180>;;Enable delay";
                range "0..180";
              }
              default "0";
            }
            leaf disable-delay {
              tailf:cli-drop-node-name;
              type union {
                type uint8 {
                  tailf:info
                    "<0-180>;;Disable delay";
                  range "0..180";
                }
                type enumeration {
                  enum "never" {
                    tailf:info
                      "Disallow disable";
                  }
                }
              }
              default "0";
            }
          }
        }
        container mpls {
          tailf:info
            "MPLS manual configuration commands";
          leaf control-word {
            tailf:info
              "Include control-word in pseudowire packets";
            type empty;
          }
        }
        leaf mtu {
          tailf:info
            "set XCONNECT Maximum Transfer Unit";
          tailf:cli-full-command;
          type uint16 {
            tailf:info
              "<64-9100>;;per Xconnect MTU size in bytes";
            range "64..9100";
          }
        }
        container remote {
          tailf:info
            "Xconnect remote peer configuration commands";
          container link {
            tailf:info
              "Link information";
            container failure {
              tailf:info
                "Failure information";
              leaf notification {
                tailf:info
                  "Notify in case of remote link failure";
                tailf:cli-boolean-no;
                tailf:cli-full-command;
                type boolean;
                default "true";
              }
            }
          }
        }
      }
      container xconnect-pw-class {
        tailf:cli-drop-node-name;
        container xconnect {
          tailf:info
            "Xconnect commands";
          tailf:cli-compact-syntax;
          tailf:cli-sequence-commands;
          leaf address {
            tailf:cli-drop-node-name;
            tailf:cli-incomplete-command;
            type inet:ipv4-address {
              tailf:info
                "A.B.C.D;;IP address of peer";
            }
          }
          leaf vcid {
            tailf:cli-drop-node-name;
            tailf:cli-incomplete-command;
            type uint32 {
              tailf:info
                "<1-4294967295>;;Enter VC ID value";
              range "1..4294967295";
            }
          }
          leaf pw-class {
            tailf:info
              "Pseudowire-class to use for encapsulation and protocol configuration";
            tailf:cli-full-command;
            type string {
              tailf:info
                "WORD;;Pseudowire-class name";
            }
            tailf:non-strict-leafref {
              path "/ncs:devices/ncs:device/ncs:config/ios:pseudowire-class/name" {
                tailf:xpath-root 3;
              }
            }
          }
        }
      }
      container xconnect-vfi {
        tailf:cli-drop-node-name;
        container xconnect {
          tailf:info
            "Xconnect commands";
          tailf:cli-incomplete-command;
          leaf vfi {
            tailf:info
              "connect to a virtual forwarding instance";
            tailf:cli-diff-dependency "/ios:l2/vfi" {
              tailf:xpath-root 3;
              tailf:cli-trigger-on-set;
            }
            tailf:non-strict-leafref {
              path "/ncs:devices/ncs:device/ncs:config/ios:l2/vfi/name" {
                tailf:xpath-root 3;
              }
            }
            type string {
              tailf:info
                "WORD;VFI name";
            }
          }
        }
      }
    }
  }

  grouping xconnect-grouping {
    choice xconnect-choice {
      container xconnect {
        tailf:cli-break-sequence-commands;
        tailf:cli-add-mode;
        tailf:cli-mode-name "config-xconn";
        tailf:cli-compact-syntax;
        tailf:cli-sequence-commands;
        tailf:cli-incomplete-command;
        tailf:cli-delete-when-empty;
        presence "true";
        leaf address {
          tailf:cli-drop-node-name;
          tailf:cli-incomplete-command;
          tailf:cli-hide-in-submode;
          type inet:ipv4-address {
            tailf:info
              "A.B.C.D;;IP address of peer";
          }
        }
        leaf vcid {
          tailf:cli-drop-node-name;
          tailf:cli-incomplete-command;
          tailf:cli-hide-in-submode;
          type uint32 {
            tailf:info
              "<1-4294967295>;;Enter VC ID value";
            range "1..4294967295";
          }
        }
        leaf encapsulation {
          tailf:info
            "Data encapsulation method";
          tailf:cli-hide-in-submode;
          type enumeration {
            enum "mpls" {
              tailf:info
                "Use MPLS encapsulation";
            }
            enum "l2tpv3" {
              tailf:info
                "Use L2TPv3 encapsulation";
            }
          }
        }
        leaf manual {
          tailf:info
            "Manually configure session parameters";
          tailf:cli-optional-in-sequence;
          tailf:cli-hide-in-submode;
          type empty;
        }
        leaf pw-class {
          tailf:info
            "Optional pseudowire-class to use for advanced configuration";
          tailf:cli-optional-in-sequence;
          tailf:cli-hide-in-submode;
          tailf:non-strict-leafref {
            path "/ncs:devices/ncs:device/ncs:config/ios:pseudowire-class/name" {
              tailf:xpath-root 3;
            }
          }
          type string {
            tailf:info
              "WORD;;Pseudowire-class name";
          }
        }
        leaf sequencing {
          when "../encapsulation = 'l2tpv3'" {
            tailf:xpath-root 3;
            tailf:dependency "../encapsulation";
          }
          tailf:info
            "Configure sequencing options for xconnect";
          tailf:cli-full-command;
          tailf:cli-hide-in-submode;
          type enumeration {
            enum "both" {
              tailf:info
                "Transmit and receive sequence numbers";
            }
            enum "receive" {
              tailf:info
                "Receive sequence numbers";
            }
            enum "transmit" {
              tailf:info
                "Transmit sequence numbers";
            }
          }
        }
        container backup {
          tailf:cli-break-sequence-commands;
          tailf:info
            "Xconnect backup configuration commands";
          container peer {
            tailf:info
              "Backup pseudowire";
            tailf:cli-compact-syntax;
            tailf:cli-sequence-commands {
              tailf:cli-reset-siblings;
            }
            leaf peer-router-ip-addr {
              tailf:cli-drop-node-name;
              tailf:cli-incomplete-command;
              type inet:ipv4-address {
                tailf:info
                  "A.B.C.D;;IP address of peer";
              }
            }
            leaf vcid {
              tailf:cli-drop-node-name;
              type uint32 {
                tailf:info
                  "<1-4294967295>;;Enter VC ID value";
                range "1..4294967295";
              }
            }
            leaf pw-class {
              tailf:cli-optional-in-sequence;
              tailf:non-strict-leafref {
                path "/ncs:devices/ncs:device/ncs:config/ios:pseudowire-class/name" {
                  tailf:xpath-root 3;
                }
              }
              type string {
                tailf:info
                  "Optional Pseudowire-class to use for backup pseudowire";
              }
            }
            leaf priority {
              tailf:info
                "Optional priority to use for backup pseudowire.";
              type uint8 {
                tailf:info
                  "Peer priority";
                range "1..10";
              }
            }
          }
          container delay {
            tailf:info
              "Backup delay";
            tailf:cli-compact-syntax;
            tailf:cli-sequence-commands;
            leaf enable-delay {
              tailf:cli-drop-node-name;
              tailf:cli-incomplete-command;
              type uint8 {
                tailf:info
                  "<0-180>;;Enable delay";
                range "0..180";
              }
              default "0";
            }
            leaf disable-delay {
              tailf:cli-drop-node-name;
              type union {
                type uint8 {
                  tailf:info
                    "<0-180>;;Disable delay";
                  range "0..180";
                }
                type enumeration {
                  enum "never" {
                    tailf:info
                      "Disallow disable";
                  }
                }
              }
              default "0";
            }
          }
        }
        container mpls {
          tailf:info
            "MPLS manual configuration commands";
          leaf control-word {
            tailf:info
              "Include control-word in pseudowire packets";
            type empty;
          }
        }
        leaf mtu {
          tailf:info
            "set XCONNECT Maximum Transfer Unit";
          tailf:cli-full-command;
          type uint16 {
            tailf:info
              "<64-9100>;;per Xconnect MTU size in bytes";
            range "64..9100";
          }
        }
        container remote {
          tailf:info
            "Xconnect remote peer configuration commands";
          container link {
            tailf:info
              "Link information";
            container failure {
              tailf:info
                "Failure information";
              leaf notification {
                tailf:info
                  "Notify in case of remote link failure";
                tailf:cli-boolean-no;
                tailf:cli-full-command;
                type boolean;
                default "true";
              }
            }
          }
        }
      }
      container xconnect-pw-class {
        tailf:cli-drop-node-name;
        container xconnect {
          tailf:info
            "Xconnect commands";
          tailf:cli-compact-syntax;
          tailf:cli-sequence-commands;
          tailf:cli-incomplete-command;
          leaf address {
            tailf:cli-drop-node-name;
            tailf:cli-incomplete-command;
            type inet:ipv4-address {
              tailf:info
                "A.B.C.D;;IP address of peer";
            }
          }
          leaf vcid {
            tailf:cli-drop-node-name;
            tailf:cli-incomplete-command;
            type uint32 {
              tailf:info
                "<1-4294967295>;;Enter VC ID value";
              range "1..4294967295";
            }
          }
          leaf pw-class {
            tailf:info
              "Pseudowire-class to use for encapsulation and protocol configuration";
            tailf:cli-full-command;
            tailf:non-strict-leafref {
              path "/ncs:devices/ncs:device/ncs:config/ios:pseudowire-class/name" {
                tailf:xpath-root 3;
              }
            }
            type string {
              tailf:info
                "WORD;;Pseudowire-class name";
            }
          }
        }
      }
    }
  }

  grouping ip-pim-grouping {
    container ssm {
      tailf:info
        "Configure Source Specific Multicast";
      choice ip-pim-ssm-choice {
        leaf default {
          tailf:info
            "Use 232/8 group range for SSM";
          type empty;
        }
        leaf range {
          tailf:info
            "ACL for group range to be used for SSM";
          type union {
            type uint16 {
              tailf:info
                "<1-99>;;Access list number";
              range "1..99";
            }
            type string {
              tailf:info
                "WORD;;IP named access list";
              pattern '[a-zA-Z].*';
            }
          }
        }
      }
    }
    container register-source {
      tailf:info
        "Source address for PIM Register";
      uses interface-name-grouping;
    }
    leaf snooping {
      tailf:info
        "Global PIM Snooping enable for Catalyst Vlans";
      type empty;
    }
    list bsr-candidate {
      tailf:info
        "Candidate bootstrap router (candidate BSR)";
      tailf:cli-suppress-mode;
      tailf:cli-delete-when-empty;
      tailf:cli-compact-syntax;
      tailf:cli-sequence-commands;
      key "name";
      leaf name {
        type string {
          tailf:info
            "WORD;;Interface name";
        }
      }
      leaf hash-mask-length {
        tailf:cli-drop-node-name;
        type uint8 {
          tailf:info
            "<0-32>;;Hash Mask length for RP selection";
          range "0..32";
        }
      }
      leaf priority {
        tailf:cli-drop-node-name;
        type uint8 {
          tailf:info
            "<0-255>;;Priority value for candidate bootstrap router";
        }
      }
      leaf accept-rp-candidate {
        tailf:info
          "BSR RP candidate filter";
        type exp-ip-acl-type;
      }
    }
    container send-rp-announce {
      tailf:info
        "Auto-RP send RP announcement";
      tailf:cli-compact-syntax;
      container interface {
        tailf:cli-drop-node-name;
        tailf:cli-flatten-container;
        tailf:cli-compact-syntax;
        uses interface-name-grouping;
      }
      leaf scope {
        tailf:info
          "RP announcement scope";
        type uint8 {
          tailf:info
            "<1-255>;;TTL of the RP announce packet ";
          range "1..255";
        }
      }
      leaf group-list {
        tailf:info
          "Group access-list";
        type union {
          type uint16 {
            tailf:info
              "<1-99>;;Access list number";
            range "1..99";
          }
          type string {
            tailf:info
              "WORD;;IP named access list";
            pattern '[a-zA-Z].*';
          }
        }
      }
      leaf interval {
        tailf:info
          "RP announcement interval";
        type uint16 {
          tailf:info
            "<1-16383>;;number of seconds";
          range "1..16383";
        }
      }
    }
    container send-rp-discovery {
      tailf:info
        "Auto-RP send RP discovery message (as RP-mapping agent)";
      container scope {
        tailf:info
          "Scope of the RP discovery packets";
        tailf:cli-compact-syntax;
        tailf:cli-sequence-commands {
          tailf:cli-reset-siblings;
        }
        leaf ttl {
          tailf:cli-drop-node-name;
          type uint8 {
            tailf:info
              "<1-255>;;TTL";
            range "1..255";
          }
        }
        leaf interval {
          tailf:info
            "RP discovery interval";
          type uint16 {
            tailf:info
              "<1-16383>;;number of seconds";
            range "1..16383";
          }
        }
      }
    }
    list rp-address {
      tailf:info
        "PIM RP-address (Rendezvous Point)";
      tailf:cli-suppress-mode;
      tailf:cli-delete-when-empty;
      tailf:cli-compact-syntax;
      tailf:cli-sequence-commands {
        tailf:cli-reset-siblings;
      }
      key "address";
      leaf address {
        type inet:ipv4-address {
          tailf:info
            "A.B.C.D;;IP address of Rendezvous-point for group";
        }
      }
      leaf access-list {
        tailf:cli-drop-node-name;
        tailf:cli-optional-in-sequence;
        tailf:cli-disallow-value "override";
        type std-acl-type;
      }
      leaf override {
        tailf:info
          "Overrides dynamically learnt RP mappings";
        type empty;
      }
    }
    list rp-candidate {
      tailf:info
        "To be a PIMv2 RP candidate";
      tailf:cli-suppress-mode;
      tailf:cli-delete-when-empty;
      tailf:cli-compact-syntax;
      key "name";
      leaf name {
        type string {
          tailf:info
            "WORD;;Interface name";
        }
      }
      leaf bidir {
        type empty;
      }
      leaf group-list {
        tailf:info
          "group-list";
        type union {
          type uint8 {
            tailf:info
              "<1-99>;;Access-list reference for group prefixes";
            range "1..99";
          }
          type string {
            tailf:info
              "WORD;;Named access list";
          }
        }
      }
      leaf interval {
        tailf:info
          "RP candidate advertisement interval";
        type uint16 {
          tailf:info
            "<1-16383>;;number of seconds";
          range "1..16383";
        }
      }
      leaf priority {
        tailf:info
          "RP candidate priority";
        type uint8 {
          tailf:info
            "<0-255>;;Priority value";
        }
      }
    }
    container spt-threshold {
      tailf:info
        "Source-tree switching threshold";
      leaf value {
        tailf:cli-drop-node-name;
        tailf:cli-full-command;
        type union {
          type enumeration {
            enum "infinity" {
              tailf:info
                "Never switch to source-tree";
            }
          }
          type uint32 {
            tailf:info
              "<0-4294967>;;Traffic rate in kilobits per second";
            range "0..4294967";
          }
        }
      }
      list group-list {
        tailf:cli-drop-node-name;
        tailf:cli-suppress-mode;
        tailf:cli-delete-when-empty;
        tailf:cli-compact-syntax;
        tailf:cli-sequence-commands;
        key "group-list";
        leaf value {
          tailf:cli-drop-node-name;
          tailf:cli-prefix-key;
          type union {
            type enumeration {
              enum "infinity" {
                tailf:info
                  "Never switch to source-tree";
              }
            }
            type uint32 {
              tailf:info
                "<0-4294967>;;Traffic rate in kilobits per second";
              range "0..4294967";
            }
          }
        }
        leaf group-list {
          tailf:info
            "Group address access-list";
          tailf:cli-expose-key-name;
          type std-acl-type;
        }
      }
    }
    choice autorp-choice {
      leaf autorp {
        tailf:info
          "Configure AutoRP global operations";
        tailf:cli-boolean-no;
        tailf:cli-full-command;
        type boolean;
        default "true";
      }
      container conf {
        tailf:cli-drop-node-name;
        container autorp {
          tailf:info
            "Configure AutoRP global operations";
          tailf:cli-incomplete-no;
          tailf:cli-incomplete-command;
          leaf listener {
            tailf:info
              "Allow AutoRP packets across sparse mode interface";
            type empty;
          }
        }
      }
    }
    leaf dm-fallback {
      tailf:info
        "Fallback group mode is Dense";
      tailf:cli-full-command;
      type empty;
    }
  }

  grouping event-manager-applet-event-grouping {
    container none {
      tailf:info
        "Manually run policy event";
      leaf maxrun {
        tailf:info
          "Maximum runtime of applet";
        type uint32 {
          tailf:info
            "<0-31536000>;;Enter seconds[.milliseconds] value";
        }
      }
    }
    container snmp-notification {
      tailf:info
        "SNMP Notification Event";
      tailf:cli-compact-syntax;
      tailf:cli-reset-container;
      leaf oid {
        tailf:info
          "Object ID of data element";
        type string {
          tailf:info
            "WORD;;OID string";
        }
      }
      leaf oid-val {
        tailf:info
          "Comparison value";
        type string {
          tailf:info
            "WORD;;Comparision value";
        }
      }
      leaf op {
        tailf:info
          "Operator";
        type operator-type;
      }
      leaf src-ip-address {
        tailf:info
          "Source ip address";
        type union {
          type inet:ipv4-address {
            tailf:info
              "A.B.C.D;;Source ip address value";
          }
          type inet:ipv6-address {
            tailf:info
              "X:X:X:X::X;;Source ip address value";
          }
        }
      }
      leaf dest-ip-address {
        tailf:info
          "Destination ip address";
        type union {
          type inet:ipv4-address {
            tailf:info
              "A.B.C.D;;Destination ip address value";
          }
          type inet:ipv6-address {
            tailf:info
              "X:X:X:X::X;;Destination ip address value";
          }
        }
      }
    }
    container syslog {
      tailf:info
        "Syslog event";
      leaf pattern {
        tailf:info
          "Pattern match string for the entire message";
        type string {
          tailf:info
            "WORD;;Pattern match string for the entire message";
        }
      }
    }
    container cli {
      tailf:info
        "CLI event";
      tailf:cli-compact-syntax;
      container pattern {
        tailf:info
          "CLI command pattern match";
        tailf:cli-compact-syntax;
        tailf:cli-sequence-commands {
          tailf:cli-reset-siblings;
        }
        leaf regular-expression {
          tailf:cli-drop-node-name;
          type string {
            tailf:info
              "WORD;;Pattern match string";
          }
        }
        leaf sync {
          tailf:info
            "CLI and EEM policy execution sync or async";
          tailf:cli-optional-in-sequence;
          type enumeration {
            enum "no" {
              tailf:info
                "Policy and CLI will run asynchronously";
            }
            enum "yes" {
              tailf:info
                "Run policy and the result determines whether to run CLI";
            }
          }
        }
        leaf skip {
          tailf:info
            "Whether to skip CLI command execution";
          type enumeration {
            enum "no" {
              tailf:info
                "CLI command should be executed";
            }
            enum "yes" {
              tailf:info
                "CLI command should not be executed";
            }
          }
        }
      }
    }
    container track {
      tailf:info
        "Tracking object event";
      tailf:cli-compact-syntax;
      tailf:cli-sequence-commands;
      leaf object-number {
        tailf:cli-drop-node-name;
        type uint16 {
          tailf:info
            "<1-1000>;;Tracking object number";
        }
      }
      leaf state {
        tailf:info
          "State of tracking object";
        tailf:cli-optional-in-sequence;
        type enumeration {
          enum "any" {
            tailf:info
              "Any state";
          }
          enum "down" {
            tailf:info
              "Down state";
          }
          enum "up" {
            tailf:info
              "Up state";
          }
        }
      }
      leaf maxrun {
        tailf:info
          "Maximum runtime of applet";
        type uint32 {
          tailf:info
            "<0-31536000>;;Enter seconds[.milliseconds] value";
          range "0..31536000";
        }
      }
    }
    container neighbor-discovery {
      tailf:info
        "Neighbor Discovery event";
      tailf:cli-compact-syntax;
      container interface {
        tailf:info
          "Interface name";
        tailf:cli-flatten-container;
        leaf regexp {
          tailf:info
            "Specify a regexp for interfaces";
          type string {
            tailf:info
              "WORD;;interface name string";
          }
        }
      }
      leaf cdp {
        tailf:info
          "Monitor CDP events";
        type enumeration {
          enum "add" {
            tailf:info
              "Monitor only CDP add events";
          }
          enum "all" {
            tailf:info
              "Monitor all CDP events";
          }
          enum "delete" {
            tailf:info
              "Monitor only CDP delete events";
          }
          enum "update" {
            tailf:info
              "Monitor CDP add and update events";
          }
        }
      }
    }
    container timer {
      tailf:info
        "Timer event";
      tailf:cli-compact-syntax;
      tailf:cli-reset-container;
      leaf trigger {
        tailf:cli-drop-node-name;
        tailf:cli-incomplete-command;
        type enumeration {
          enum "absolute" {
            tailf:info
              "Absolute timer event";
          }
          enum "countdown" {
            tailf:info
              "Countdown timer event";
          }
          enum "watchdog" {
            tailf:info
              "Watchdog timer event";
          }
          enum "cron" {
            tailf:info
              "Cron timer event";
          }
        }
      }
      leaf name {
        tailf:info
          "Name of the timer";
        type string {
          tailf:info
            "WORD;;Timer name string";
        }
      }
      leaf cron-entry {
        tailf:info
          "Cron entry for cron timer";
        type string {
          tailf:info
            "WORD;;Cron entry string";
        }
      }
      leaf time {
        tailf:info
          "Time period for watchdog / countdown / absolute timer";
        type uint32 {
          tailf:info
            "<1-4294967295>;;Enter seconds[.milliseconds] value";
          range "1..4294967295";
        }
      }
      leaf maxrun {
        tailf:info
          "Maximum runtime of applet";
        type uint32 {
          tailf:info
            "<0-31536000>;;Enter seconds[.milliseconds] value";
          range "0..31536000";
        }
      }
      leaf ratelimit {
        tailf:info
          "Limit trigger to once per given time period";
        type uint32 {
          tailf:info
            "<0-31536000>;;Enter seconds[.milliseconds] value";
          range "0..31536000";
        }
      }
    }
    container snmp {
      tailf:info
        "SNMP event";
      tailf:cli-compact-syntax;
      tailf:cli-sequence-commands {
        tailf:cli-reset-siblings;
      }
      leaf oid {
        tailf:info
          "Object ID of data element";
        type string {
          tailf:info
            "WORD;;OID string";
        }
      }
      leaf get-type {
        tailf:cli-break-sequence-commands;
        tailf:info
          "Type of SNMP get operation";
        type enumeration {
          enum "exact" {
            tailf:info
              "Exact oid specified";
          }
          enum "next" {
            tailf:info
              "Next available oid";
          }
        }
      }
      leaf entry-op {
        tailf:info
          "Entry comparison operator";
        type operator-type;
      }
      leaf entry-val {
        tailf:info
          "Entry comparison value";
        type string {
          tailf:info
            "WORD;;Entry value";
        }
      }
      leaf exit-op {
        tailf:info
          "Exit operator";
        type operator-type;
      }
      leaf exit-val {
        tailf:info
          "Exit comparison value";
        type string {
          tailf:info
            "WORD;;Entry value";
        }
      }
      leaf poll-interval {
        tailf:info
          "Poll interval value";
        type uint32 {
          tailf:info
            "<0-4294967295>;;Enter seconds[.milliseconds] value";
        }
      }
    }
    container ipsla {
      tailf:info
        "IPSLA Event";
      tailf:cli-compact-syntax;
      tailf:cli-reset-container;
      leaf operation-id {
        tailf:info
          "IPSLA Operation ID";
        type uint32 {
          tailf:info
            "<1-2147483647>;;Operation ID value";
          range "1..2147483647";
        }
      }
      leaf reaction-type {
        tailf:info
          "IPSLA Reaction Type";
        type string {
          tailf:info
            "WORD;;Reaction Type";
        }
      }
      leaf maxrun {
        tailf:info
          "Maximum runtime of applet";
        type uint32 {
          tailf:info
            "<0-31536000>;;Enter seconds[.milliseconds] value";
          range "0..31536000";
        }
      }
    }
  }

  grouping route-target-grouping {
    list export {
      tailf:info
        "Export Target-VPN community";
      tailf:cli-suppress-mode;
      tailf:cli-delete-when-empty;
      key "asn-ip";
      leaf asn-ip {
        type asn-ip-type {
          tailf:info
            "ASN:nn or IP-address:nn;;Target VPN Extended Community";
        }
      }
    }
    list import {
      tailf:info
        "Import Target-VPN community";
      tailf:cli-suppress-mode;
      tailf:cli-delete-when-empty;
      key "asn-ip";
      leaf asn-ip {
        type asn-ip-type {
          tailf:info
            "ASN:nn or IP-address:nn;;Target VPN Extended Community";
        }
      }
    }
  }

  grouping vrf-definition-af-grouping {
    container export {
      tailf:info
        "VRF export";
      leaf map {
        tailf:info
          "Route-map based VRF export";
        type string {
          tailf:info
            "WORD;;Route-map reference";
        }
      }
    }
    container route-target {
      tailf:info
        "Specify Target VPN Extended Communities";
      uses route-target-grouping;
    }
    container maximum {
      tailf:info
        "Set a limit";
      container routes {
        tailf:info
          "Maximum number of routes allowed in this routing table";
        tailf:cli-compact-syntax;
        tailf:cli-sequence-commands {
          tailf:cli-reset-siblings;
        }
        leaf limit {
          tailf:cli-drop-node-name;
          tailf:cli-incomplete-command;
          type uint32 {
            tailf:info
              "<1-4294967294>;;Maximum number of routes allowed";
          }
        }
        choice action {
          case a {
            leaf warning-only {
              tailf:info
                "Only give a warning message if limit is exceeded";
              type empty;
            }
          }
          case b {
            leaf warn-threshold {
              tailf:cli-drop-node-name;
              type uint8 {
                tailf:info
                  "<1-100>;;Threshold value (%) at which to generate a warning msg";
                range "1..100";
              }
            }
            leaf reinstall {
              tailf:info
                "Reinstall previous rejected route due to over maximum route limit";
              type uint8 {
                tailf:info
                  "<1-100>;;Threshold value (%) at which to reinstall routes back to VRF";
                range "1..100";
              }
            }
          }
        }
      }
    }
  }

  grouping snmp-server-host-grouping {
    leaf message-type {
      tailf:cli-optional-in-sequence;
      tailf:cli-drop-node-name;
      tailf:cli-incomplete-command;
      type enumeration {
        enum "informs" {
          tailf:info
            "Send Inform messages to this host";
        }
        enum "traps" {
          tailf:info
            "Send Trap messages to this host";
        }
      }
      default "traps";
    }
    container version {
      tailf:info
        "SNMP version to use for notification messages";
      tailf:cli-optional-in-sequence;
      tailf:cli-flatten-container;
      tailf:cli-compact-syntax;
      tailf:cli-incomplete-command;
      leaf version {
        tailf:cli-drop-node-name;
        type enumeration {
          enum "1" {
            tailf:info
              "Use SNMPv1";
          }
          enum "2c" {
            tailf:info
              "Use SNMPv2c";
          }
          enum "3" {
            tailf:info
              "Use SNMPv3";
          }
        }
      }
      leaf security-level {
        tailf:cli-drop-node-name;
        when "../version = '3'" {
          tailf:xpath-root 3;
          tailf:dependency "../version";
        }
        type enumeration {
          enum "auth" {
            tailf:info
              "Use the SNMPv3 authNoPriv Security Level";
          }
          enum "noauth" {
            tailf:info
              "Use the SNMPv3 noAuthNoPriv Security Level";
          }
          enum "priv" {
            tailf:info
              "Use the SNMPv3 authPriv Security Level";
          }
        }
      }
    }
    leaf community-string {
      tailf:cli-drop-node-name;
      tailf:cli-disallow-value "version|informs|traps|vrf";
      type string {
        tailf:info
          "WORD;;SNMPv1/v2c community string or SNMPv3 user name";
      }
    }
    leaf-list allowed-traps {
      tailf:cli-drop-node-name;
      tailf:cli-flat-list-syntax {
        tailf:cli-replace-all;
      }
      type enumeration {
        enum "aaa_server" {
          tailf:info
            "Allow SNMP AAA traps";
        }
        enum "alarms" {
          tailf:info
            "Allow SNMP alarms traps";
        }
        enum "atm" {
          tailf:info
            "Allow SNMP atm traps";
        }
        enum "bfd" {
          tailf:info
            "Allow SNMP BFD traps";
        }
        enum "bgp" {
          tailf:info
            "Allow BGP state change traps";
        }
        enum "bstun" {
          tailf:info
            "Allow bstun event traps";
        }
        enum "bulkstat" {
          tailf:info
            "Allow Data-Collection-MIB traps";
        }
        enum "cable" {
          tailf:info
            "Allow SNMP cable traps";
        }
        enum "call-home" {
          tailf:info
            "Allow SNMP CISCO-CALLHOME-MIB traps";
        }
        enum "casa" {
          tailf:info
            "Allow casa event traps";
        }
        enum "cef" {
          tailf:info
            "Allows cef traps";
        }
        enum "cnpd" {
          tailf:info
            "Allow NBAR Protocol Discovery traps";
        }
        enum "config" {
          tailf:info
            "Allow SNMP config traps";
        }
        enum "config-copy" {
          tailf:info
            "Allow SNMP config-copy traps";
        }
        enum "config-ctid" {
          tailf:info
            "Allow SNMP config-ctid traps";
        }
        enum "cpu" {
          tailf:info
            "Allow cpu related traps";
        }
        enum "dhcp" {
          tailf:info
            "Allow dhcp traps";
        }
        enum "dlsw" {
          tailf:info
            "Allow dlsw traps";
        }
        enum "ds1" {
          tailf:info
            "Allow SNMP ds1 traps";
        }
        enum "dsp" {
          tailf:info
            "Allow SNMP DSP traps";
        }
        enum "dspu" {
          tailf:info
            "Allow dspu event traps";
        }
        enum "eigrp" {
          tailf:info
            "Allow SNMP EIGRP traps";
        }
        enum "entity" {
          tailf:info
            "Allow SNMP entity traps";
        }
        enum "entity-diag" {
          tailf:info
            "Allow SNMP CISCO-ENTITY-DIAG-MIB traps";
        }
        enum "entity-qfp" {
          tailf:info
            "Allow SNMP CISCO-ENTITY-QFP-MIB traps";
        }
        enum "entity-state" {
          tailf:info
            "Allow ENTITY-STATE-MIB traps";
        }
        enum "envmon" {
          tailf:info
            "Allow environmental monitor traps";
        }
        enum "ethernet-cfm" {
          tailf:info
            "Allow SNMP Ethernet CFM traps";
        }
        enum "evc" {
          tailf:info
            "Allow SNMP EVC traps";
        }
        enum "event-manager" {
          tailf:info
            "Allow SNMP Embedded Event Manager traps";
        }
        enum "firewall" {
          tailf:info
            "Allow SNMP Firewall traps";
        }
        enum "flash" {
          tailf:info
            "Allow SNMP FLASH traps";
        }
        enum "flowmon" {
          tailf:info
            "Allow SNMP flow monitor notifications";
        }
        enum "frame-relay" {
          tailf:info
            "Allow SNMP frame-relay traps";
        }
        enum "fru-ctrl" {
          tailf:info
            "Allow entity FRU control traps";
        }
        enum "gdoi" {
          tailf:info
            "Allows gdoi traps";
        }
        enum "hsrp" {
          tailf:info
            "Allow SNMP HSRP traps";
        }
        enum "iplocalpool" {
          tailf:info
            "Allow SNMP IP Local Pool traps";
        }
        enum "ipmulticast" {
          tailf:info
            "Allow SNMP ipmulticast traps";
        }
        enum "ipsec" {
          tailf:info
            "Allow SNMP IPsec traps";
        }
        enum "ipsla" {
          tailf:info
            "Allow SNMP Host IP SLA traps";
        }
        enum "isakmp" {
          tailf:info
            "Allow SNMP ISAKMP traps";
        }
        enum "isg-mib" {
          tailf:info
            "Allow SNMP isgmib traps";
        }
        enum "isis" {
          tailf:info
            "Allow IS-IS traps";
        }
        enum "l2tun-pseudowire-status" {
          tailf:info
            "Allow SNMP L2 pseudowire status traps";
        }
        enum "l2tun-session" {
          tailf:info
            "Allow SNMP L2 session traps";
        }
        enum "license" {
          tailf:info
            "Allow license traps";
        }
        enum "mac-notification" {
          tailf:info
            "Allow SNMP MAC Notification Traps";
        }
        enum "memory" {
          tailf:info
            "Allow SNMP Mempool traps";
        }
        enum "mpls-fast-reroute" {
          tailf:info
            "Allow SNMP MPLS traffic engineering fast reroute traps";
        }
        enum "mpls-ldp" {
          tailf:info
            "Allow SNMP MPLS label distribution protocol traps";
        }
        enum "mpls-traffic-eng" {
          tailf:info
            "Allow SNMP MPLS traffic engineering traps";
        }
        enum "mpls-vpn" {
          tailf:info
            "Allow SNMP MPLS Virtual Private Network traps";
        }
        enum "msdp" {
          tailf:info
            "Allow SNMP MSDP traps";
        }
        enum "mvpn" {
          tailf:info
            "Allow Multicast Virtual Private Network traps";
        }
        enum "nhrp" {
          tailf:info
            "Allow SNMP NHRP traps";
        }
        enum "ospf" {
          tailf:info
            "Allow OSPF traps";
        }
        enum "ospfv3" {
          tailf:info
            "Allow OSPFv3 traps";
        }
        enum "pfr" {
          tailf:info
            "Allow SNMP PfR traps";
        }
        enum "pim" {
          tailf:info
            "Allow SNMP PIM traps";
        }
        enum "pw-vc" {
          tailf:info
            "Allow SNMP Pseudowire VC traps";
        }
        enum "resource-policy" {
          tailf:info
            "Enable CISCO-ERM-MIB notifications";
        }
        enum "rf" {
          tailf:info
            "Allow all SNMP traps defined in CISCO-RF-MIB";
        }
        enum "rsrb" {
          tailf:info
            "Allow rsrb event traps";
        }
        enum "rsvp" {
          tailf:info
            "Allow RSVP flow change traps";
        }
        enum "sdlc" {
          tailf:info
            "Allow sdlc event traps";
        }
        enum "sdllc" {
          tailf:info
            "Allow sdllc event traps";
        }
        enum "snmp" {
          tailf:info
            "Allow SNMP-type notifications";
        }
        enum "sonet" {
          tailf:info
            "Allow SNMP SONET traps";
        }
        enum "srp" {
          tailf:info
            "Allow SRP protocol traps";
        }
        enum "stun" {
          tailf:info
            "Allow stun event traps";
        }
        enum "syslog" {
          tailf:info
            "Allow SNMP syslog traps";
        }
        enum "trustsec-sxp" {
          tailf:info
            "Allow SNMP CISCO-TRUSTSEC-SXP-MIB traps";
        }
        enum "tty" {
          tailf:info
            "Allow TCP connection traps";
        }
        enum "udp-port" {
          tailf:info
            "The notification host's UDP port number (default port 162)";
        }
        enum "voice" {
          tailf:info
            "Allow SNMP Voice traps";
        }
        enum "vrfmib" {
          tailf:info
            "Allow SNMP vrfmib traps";
        }
        enum "vrrp" {
          tailf:info
            "Allow SNMP vrrp traps";
        }
        enum "x25" {
          tailf:info
            "Allow x25 event traps";
        }
      }
    }
  }

  grouping aaa-authentication-method-grouping {
    leaf cache {
      tailf:info
        "Use Cached-group";
      type aaa-group-type;
    }
    leaf group {
      tailf:info
        "Use Server-group";
      type aaa-group-type;
    }
    container group2 {
      when "../group" {
        tailf:xpath-root 3;
        tailf:dependency "../group";
      }
      tailf:cli-drop-node-name;
      tailf:cli-flatten-container;
      tailf:cli-compact-syntax;
      leaf group {
        tailf:info
          "Use Server-group 2";
        type aaa-group-type;
      }
    }
    leaf krb5 {
      tailf:info
        "Use Kerberos 5 authentication.";
      type empty;
    }
    choice local-choice {
      leaf local {
        tailf:info
          "Use local username authentication.";
        type empty;
      }
      leaf local-case {
        tailf:info
          "Use case-sensitive local username authentication.";
        type empty;
      }
    }
    leaf tacacsplus {
      tailf:alt-name "tacacs+";
      tailf:info
        "Use enable password for authentication.";
      type empty;
    }
    leaf line {
      tailf:info
        "Use line password for authentication.";
      type empty;
    }
    leaf enable {
      tailf:info
        "Use enable password for authentication.";
      type empty;
    }
    leaf none {
      tailf:info
        "NO authentication.";
      tailf:cli-full-command;
      type empty;
    }
  }

  grouping aaa-authorization-method-grouping {
    leaf cache {
      tailf:info
        "Use Cached-group";
      type aaa-group-type;
    }
    leaf group {
      tailf:info
        "Use server-group.";
      type aaa-group-type;
    }
    leaf krb5-instance {
      tailf:info
        "Use Kerberos instance privilege maps.";
      type empty;
    }
    leaf tacacsplus {
      tailf:alt-name "tacacs+";
      tailf:info
        "Use enable password for authorization.";
      type empty;
    }
    leaf local {
      tailf:info
        "Use local database.";
      type empty;
    }
    leaf if-authenticated {
      tailf:info
        "Succeed if user has authenticated.";
      type empty;
    }
    leaf none {
      tailf:info
        "No authorization (always succeeds).";
      tailf:cli-full-command;
      type empty;
    }
  }

  grouping aaa-accounting-method-grouping {
    leaf action-type {
      tailf:cli-drop-node-name;
      tailf:cli-no-value-on-delete;
      type enumeration {
        enum "none" {
          tailf:info
            "No accounting.";
        }
        enum "start-stop" {
          tailf:info
            "Record start and stop without waiting";
        }
        enum "stop-only" {
          tailf:info
            "Record stop when service terminates.";
        }
      }
    }
    leaf broadcast {
      tailf:info
        "Use Broadcast for Accounting";
      tailf:cli-no-name-on-delete;
      type empty;
    }
    leaf group {
      tailf:info
        "Use Server-group";
      tailf:cli-no-name-on-delete;
      tailf:cli-no-value-on-delete;
      type aaa-group-type;
    }
  }

  grouping cable-modulation-profile-grouping {
    leaf fec-tbytes {
      tailf:cli-drop-node-name;
      tailf:cli-incomplete-command;
      type uint8 {
        tailf:info
          "<0-16>;;FEC tbytes";
      }
    }
    leaf fec-len {
      tailf:cli-drop-node-name;
      tailf:cli-incomplete-command;
      type uint8 {
        tailf:info
          "<16-253>;;FEC codeword length in k bytes";
      }
    }
    leaf burst-len {
      tailf:cli-drop-node-name;
      tailf:cli-incomplete-command;
      type uint8 {
        tailf:info
          "<0-255>;;max burst size in minislots";
      }
    }
    leaf guard-t {
      tailf:cli-drop-node-name;
      tailf:cli-incomplete-command;
      type uint8 {
        tailf:info
          "<0-255>;;guard time in symbols";
      }
    }
    leaf mod {
      tailf:cli-drop-node-name;
      tailf:cli-incomplete-command;
      type enumeration {
        enum "8qam" {
          tailf:info
            "8-QAM modulation";
        }
        enum "16qam" {
          tailf:info
            "16-QAM modulation";
        }
        enum "32qam" {
          tailf:info
            "32-QAM modulation";
        }
        enum "64qam" {
          tailf:info
            "64-QAM modulation";
        }
        enum "qpsk" {
          tailf:info
            "qpsk modulation";
        }
      }
    }
    leaf scrambler {
      tailf:cli-drop-node-name;
      tailf:cli-incomplete-command;
      type enumeration {
        enum "no-scrambler" {
          tailf:info
            "scrambler disabled";
        }
        enum "scrambler" {
          tailf:info
            "scrambler enabled";
        }
      }
    }
    leaf seed {
      when "../scrambler = 'scrambler'" {
        tailf:xpath-root 3;
        tailf:dependency "../scrambler";
      }
      tailf:cli-drop-node-name;
      tailf:cli-incomplete-command;
      type string {
        tailf:info
          "<0x0-0x7FFF>;;scrambler seed in hex";
      }
    }
    leaf diff {
      tailf:cli-drop-node-name;
      tailf:cli-incomplete-command;
      type enumeration {
        enum "diff" {
          tailf:info
            "diff encoding enabled";
        }
        enum "no-diff" {
          tailf:info
            "diff encoding disabled";
        }
      }
    }
    leaf pre-len {
      tailf:cli-drop-node-name;
      tailf:cli-incomplete-command;
      type uint16 {
        tailf:info
          "<4-1536>;;preamble length in bits";
      }
    }
    leaf last-cw {
      tailf:cli-drop-node-name;
      type enumeration {
        enum "fixed" {
          tailf:info
            "fixed codeword";
        }
        enum "shortened" {
          tailf:info
            "shortened codeword";
        }
      }
    }
    leaf preamble {
      tailf:cli-drop-node-name;
      type enumeration {
        enum "qpsk0" {
          tailf:info
            "QPSK0 preamble";
        }
        enum "qpsk1" {
          tailf:info
            "QPSK1 preamble";
        }
      }
    }
    leaf rs-interleave-depth {
      tailf:cli-drop-node-name;
      type uint8 {
        tailf:info
          "<0-114>;;RS interleave depth";
      }
    }
    leaf rs-interleave-block {
      tailf:cli-drop-node-name;
      type uint16 {
        tailf:info
          "<18-2048>;;RS interleave block size";
      }
    }
  }

  grouping cable-modulation-profile-list-grouping {
    container request {
      tailf:info
        "Request Burst";
      tailf:cli-compact-syntax;
      tailf:cli-sequence-commands {
        tailf:cli-reset-all-siblings;
      }
      uses cable-modulation-profile-grouping;
    }
    container initial {
      tailf:info
        "Initial Ranging Burst";
      tailf:cli-compact-syntax;
      tailf:cli-sequence-commands {
        tailf:cli-reset-all-siblings;
      }
      uses cable-modulation-profile-grouping;
    }
    container station {
      tailf:info
        "Station Ranging Burst";
      tailf:cli-compact-syntax;
      tailf:cli-sequence-commands {
        tailf:cli-reset-all-siblings;
      }
      uses cable-modulation-profile-grouping;
    }
    container short {
      tailf:info
        "Short Grant Burst";
      tailf:cli-compact-syntax;
      tailf:cli-sequence-commands {
        tailf:cli-reset-all-siblings;
      }
      uses cable-modulation-profile-grouping;
    }
    container long {
      tailf:info
        "Long Grant Burst";
      tailf:cli-compact-syntax;
      tailf:cli-sequence-commands {
        tailf:cli-reset-all-siblings;
      }
      uses cable-modulation-profile-grouping;
    }
    container a-short {
      tailf:info
        "Advanced Phy Short Grant Burst";
      tailf:cli-compact-syntax;
      tailf:cli-sequence-commands {
        tailf:cli-reset-all-siblings;
      }
      uses cable-modulation-profile-grouping;
    }
    container a-long {
      tailf:info
        "Advanced Phy Long Grant Burst";
      tailf:cli-compact-syntax;
      tailf:cli-sequence-commands {
        tailf:cli-reset-all-siblings;
      }
      uses cable-modulation-profile-grouping;
    }
    container a-ugs {
      tailf:info
        "Advanced Phy Unsolicited Grant Burst";
      tailf:cli-compact-syntax;
      tailf:cli-sequence-commands {
        tailf:cli-reset-all-siblings;
      }
      uses cable-modulation-profile-grouping;
    }
  }

  grouping cable-load-balance-docsis-group-grouping {
    leaf restricted {
      tailf:info
        "Set load balance group as restricted";
      type empty;
    }
    container downstream {
      tailf:info
        "Set downstream RF channels";
      list Modular-Cable {
        tailf:info
          "Modular cable";
        tailf:cli-allow-join-with-key;
        tailf:cli-suppress-mode;
        tailf:cli-delete-when-empty;
        key "name";
        leaf name {
          type string {
            tailf:info
              "<slot>/<card>/<port>;;Enter slot/subslot/bay";
          }
        }
        leaf rf-channel {
          tailf:info
            "RF channel";
          tailf:cli-multi-value;
          type string {
            tailf:info
              "<grouplist>;;List of port numbers and number ranges";
          }
        }
      }
      list Integrated-Cable {
        tailf:info
          "Integrated cable";
        tailf:cli-allow-join-with-key;
        tailf:cli-suppress-mode;
        tailf:cli-delete-when-empty;
        key "name";
        leaf name {
          type string {
            tailf:info
              "<slot>/<card>/<port>;;Enter slot/subslot/bay";
          }
        }
        leaf rf-channel {
          tailf:info
            "RF channel";
          tailf:cli-multi-value;
          type string {
            tailf:info
              "<grouplist>;;List of port numbers and number ranges";
          }
        }
      }
    }
    container upstream {
      tailf:info
        "Set upstream channels";
      list Upstream-Cable {
        tailf:info
          "Upstream Cable Controller";
        tailf:cli-allow-join-with-key;
        tailf:cli-suppress-mode;
        tailf:cli-delete-when-empty;
        key "name";
        leaf name {
          type string {
            tailf:info
              "<slot>/<card>/<port>;;Enter slot/subslot/bay";
          }
        }
        leaf us-channel {
          tailf:info
            "Associate physical us channels";
          tailf:cli-multi-value;
          type string {
            tailf:info
              "<grouplist>;;Physical us channel numbers and number ranges";
          }
        }
      }
      list Cable {
        tailf:info
          "CMTS interface";
        tailf:cli-allow-join-with-key;
        tailf:cli-suppress-mode;
        tailf:cli-delete-when-empty;
        key "name";
        leaf name {
          type string {
            tailf:info
              "<slot>/<card>/<port>;;Enter slot/subslot/bay";
          }
        }
        leaf upstream-list {
          tailf:cli-drop-node-name;
          type string {
            tailf:info
              "<grouplist>;;List of Ranges for upstream channels <0-7>";
          }
        }
      }
    }
    container method {
      tailf:info
        "Set load balancing type/method";
      container utilization {
        tailf:info
          "Interface utilization";
        presence "true";
      }
    }
    container threshold {
      tailf:info
        "Load balancing threshold in %";
      container load {
        tailf:info
          "Interface load threshold settings";
        leaf percentage {
          tailf:cli-drop-node-name;
          type uint8 {
            tailf:info
              "<1-100>;;Threshold value in %";
            range "1..100";
          }
        }
        leaf minimum {
          tailf:info
            "Set minimum number of modems/flows difference before loadbalancing starts";
          type uint8 {
            tailf:info
              "<1-100>;;Minimum number of modems/flows";
            range "1..100";
          }
        }
      }
      leaf stability {
        tailf:info
          "Threshold for stability detection";
        type uint8 {
          tailf:info
            "<0-100>;;Stability condition detection threshold in %";
          range "0..100";
        }
      }
    }
    leaf policy {
      tailf:info
        "Set load balancing policy";
      type enumeration {
        tailf:info
          "pure-ds-load;;Do not count US load when calculating DS utilization";
        enum "pcmm" {
          tailf:info
            "Enable balancing of modems with active PCMM service flows";
        }
        enum "pure-ds-load" {
          tailf:info
            "Do not count US load when calculating DS utilization";
        }
        enum "ugs" {
          tailf:info
            "Enable balancing of modems with active UGS service flows";
        }
        enum "us-across-ds" {
          tailf:info
            "Load balancing on US groups across DS, DS method will be ignored";
        }
      }
    }
    leaf interval {
      tailf:info
        "Set interface polling interval";
      type uint16 {
        tailf:info
          "<1-1000>;;Interface polling interval in seconds";
        range "1..1000";
      }
    }
    container init-tech-list {
      tailf:info
        "Set DCC initialization technique list";
      tailf:cli-compact-syntax;
      tailf:cli-sequence-commands {
        tailf:cli-reset-all-siblings;
      }
      leaf grouplist {
        tailf:cli-drop-node-name;
        type string {
          tailf:info
            "<grouplist> ";
        }
      }
      leaf ucc {
        tailf:info
          "Allow the use of UCC in upstream load balancing";
        type empty;
      }
    }
    leaf docsis-policy {
      tailf:info
        "Enter load balance group policy";
      type uint32 {
        tailf:info
          "<0-4294967295>;;Load balance group policy number";
        range "0..4294967295";
      }
    }
    list tag {
      tailf:info
        "Add tag to load balancing group";
      tailf:cli-suppress-mode;
      tailf:cli-delete-when-empty;
      key "name";
      leaf name {
        type string {
          tailf:info
            "WORD;;tag name";
        }
      }
    }
  }

  grouping facility-alarm-grouping {
    container major {
      tailf:info
        "Major warning threshold";
      leaf temperature {
        tailf:cli-drop-node-name;
        type uint8 {
          tailf:info
            "<20-100>;;<##> threshold temperature (degrees C)";
          range "20..100";
        }
      }
    }
    container minor {
      tailf:info
        "Minor warning threshold";
      leaf temperature {
        tailf:cli-drop-node-name;
        type uint8 {
          tailf:info
            "<20-100>;;<##> threshold temperature (degrees C)";
          range "20..100";
        }
      }
    }
    container critical {
      tailf:info
        "Critical warning threshold";
      leaf exceed-action {
        tailf:info
          "Critical outlet temperature exceed action";
        tailf:cli-full-command;
        type enumeration {
          enum "shutdown" {
            tailf:info
              "Auto-shutdown when critical outlet temperature is exceeded";
          }
        }
      }
      leaf temperature {
        tailf:cli-drop-node-name;
        tailf:cli-full-command;
        type uint8 {
          tailf:info
            "<1-255>;;<##> threshold temperature (degrees C)";
          range "1..255";
        }
      }
    }
  }

  grouping process-cpu-threshold-grouping {
    leaf rising {
      tailf:info
        "rising threshold";
      tailf:cli-incomplete-command;
      type uint8 {
        tailf:info
          "<1-100>";
        range "1..100";
      }
    }
    leaf interval {
      tailf:info
        "observation interval";
      type uint32 {
        tailf:info
          "<5-86400>";
        range "5..86400";
      }
    }
    leaf falling {
      tailf:info
        "falling threshold ";
      type uint8 {
        tailf:info
          "<1-100>";
        range "1..100";
      }
    }
    container falling-interval {
      tailf:cli-flatten-container;
      tailf:cli-drop-node-name;
      leaf interval {
        tailf:info
          "observation interval";
        type uint32 {
          tailf:info
            "<5-86400>";
          range "5..86400";
        }
      }
    }
  }

  grouping cable-submgmt-default-filter-group-grouping {
    leaf upstream {
      tailf:info
        "Default Upstream Group";
      type uint8 {
        tailf:info
          "<1-254>;;Group ID";
        range "1..254";
      }
    }
    leaf downstream {
      tailf:info
        "Default Downstream Group";
      type uint8 {
        tailf:info
          "<1-254>;;Group ID";
        range "1..254";
      }
    }
  }

  grouping storm-control-level-bps-pps-grouping {
    container level-bps-pps {
      tailf:cli-drop-node-name;
      container level {
        tailf:info
          "Set storm suppression level on this interface";
        choice level-choice {
          leaf bps {
            tailf:info
              "Enter suppression level in bits per second";
            type string {
              tailf:info
                "<0.0 - 10000000000.0>[k|m|g];;Enter rising threshold";
            }
          }
          leaf pps {
            tailf:info
              "Enter suppression level in packets per second";
            type string {
              tailf:info
                "<0.0 - 10000000000.0>[k|m|g];;Enter rising threshold";
            }
          }
        }
      }
    }
  }

  grouping logging-host-grouping {
    leaf discriminator {
      tailf:info
        "Specify a message discriminator identifier for this logging session";
      type string {
        tailf:info
          "WORD;;Message discriminator identifier for this logging session (8 chars. max)";
      }
    }
    container session-id {
      tailf:info
        "Specify syslog message session ID tagging";
      tailf:cli-flatten-container;
      choice session-id-choice {
        leaf hostname {
          tailf:info
            "Include hostname in session ID tag";
          type empty;
        }
        leaf ipv4 {
          tailf:info
            "Include logging source IP address in session ID tag";
          type empty;
        }
        leaf ipv6 {
          tailf:info
            "Include logging source IPV6 address in session ID tag";
          type empty;
        }
        leaf string {
          tailf:info
            "Include custom string in session ID tag";
          type string {
            tailf:info
              "WORD;;Custom string in [s_id=\"custom_string\"] tag";
          }
        }
      }
    }
    leaf transport {
      tailf:info
        "Specify the transport protocol (default=UDP)";
      type enumeration {
        enum "beep" {
          tailf:info
            "Blocks Extensible Exchange Protocol";
        }
        enum "tcp" {
          tailf:info
            "Transport Control Protocol";
        }
        enum "udp" {
          tailf:info
            "User Datagram Protocol";
        }
      }
    }
    leaf port {
      tailf:info
        "Specify the transport port number";
      when "../transport" {
        tailf:xpath-root 3;
        tailf:dependency "../transport";
      }
      type uint16 {
        tailf:info
          "<1-65535>;;Port number";
        range "1..65535";
      }
    }
  }

  grouping crypto-ikev2-profile-aaa-authorization-group-list {
    container list {
      tailf:info
        "AAA method list";
      tailf:cli-compact-syntax;
      tailf:cli-sequence-commands {
        tailf:cli-reset-siblings;
      }
      leaf list-name {
        tailf:cli-drop-node-name;
        type string {
          tailf:info
            "WORD;;AAA list name";
        }
      }
      leaf aaa-username {
        tailf:cli-break-sequence-commands;
        tailf:cli-drop-node-name;
        type string {
          tailf:info
            "WORD;;AAA username";
        }
      }
      leaf name-mangler {
        tailf:info
          "Specify the name-mangler to derive AAA username";
        tailf:non-strict-leafref {
          path "../../../../../../../../ikev2/name-mangler/name";
        }
        type string {
          tailf:info
            "WORD;;mangler name";
        }
      }
      container password {
        tailf:info
          "Specify the AAA password";
        tailf:cli-flatten-container;
        tailf:cli-compact-syntax;
        tailf:cli-sequence-commands;
        uses crypto-key-grouping;
      }
    }
  }

  grouping parameter-map-grouping {
    leaf alert {
      tailf:info
        "Turn on/off alert";
      type enumeration {
        enum "off" {
          tailf:info
            "Turn off alert";
        }
        enum "on" {
          tailf:info
            "Turn on alert";
        }
      }
    }
    leaf audit-trail {
      tailf:info
        "Turn on/off audit trail";
      type enumeration {
        enum "off" {
          tailf:info
            "Turn off audit trail";
        }
        enum "on" {
          tailf:info
            "Turn on audit trail";
        }
      }
    }
    leaf dns-timeout {
      tailf:info
        "Specify timeout for DNS";
      type uint32 {
        tailf:info
          "<1-2147483>;;Timeout in seconds";
        range "1..2147483";
      }
    }
    container icmp {
      tailf:info
        "Config timeout values for icmp";
      tailf:cli-compact-syntax;
      tailf:cli-sequence-commands {
        tailf:cli-reset-siblings;
      }
      leaf idle-time {
        tailf:info
          "Specify timeout for icmp";
        type uint32 {
          tailf:info
            "<1-2147483>;;Timeout in seconds";
          range "1..2147483";
        }
      }
      leaf ageout-time {
        tailf:info
          "Specify aggressive age-out time for icmp";
        type uint32 {
          tailf:info
            "<1-2147483>;;Timeout in seconds";
          range "1..2147483";
        }
      }
    }
    leaf max-destination {
      tailf:info
        "config maximum destination";
      type uint32 {
        tailf:info
          "<1-4294967295>;;maximum destination value";
        range "1..4294967295";
      }
    }
    container max-incomplete {
      tailf:info
        "Specify maximum number of incomplete connections before clamping";
      container half-open-sessions {
        tailf:cli-drop-node-name;
        tailf:cli-compact-syntax;
        tailf:cli-sequence-commands {
          tailf:cli-reset-siblings;
        }
        leaf number {
          tailf:cli-drop-node-name;
          type uint32 {
            tailf:info
              "<1-4294967295>;;half-open sessions";
            range "1..4294967295";
          }
        }
        container aggressive-aging {
          tailf:info
            "Aggressive Aging parameters";
          tailf:cli-flatten-container;
          tailf:cli-compact-syntax;
          tailf:cli-sequence-commands;
          leaf high {
            tailf:info
              "Specify the high watermark for aggressive-aging";
            type uint32 {
              tailf:info
                "<1-4294967295>;;High watermark in absolute values";
              range "1..4294967295";
            }
          }
          leaf low {
            tailf:info
              "Specify the low watermark for aggressive-aging";
            type uint32 {
              tailf:info
                "<1-4294967295>;;Low watermark in absolute values";
              range "1..4294967295";
            }
          }
        }
      }
      leaf high {
        tailf:info
          "Specify high-watermark for clamping";
        tailf:cli-full-command;
        type uint32 {
          tailf:info
            "<1-2147483647>;;Number of connections";
          range "1..2147483647";
        }
      }
      leaf low {
        tailf:info
          "Specify low-watermark for clamping";
        tailf:cli-full-command;
        type uint32 {
          tailf:info
            "<1-2147483647>;;Number of connections";
          range "1..2147483647";
        }
      }
    }
    container one-minute {
      tailf:info
        "Specify one-minute-sample watermarks for clamping";
      leaf high {
        tailf:info
          "Specify high-watermark for clamping";
        type uint32 {
          tailf:info
            "<1-2147483647>;;Number of connections";
          range "1..2147483647";
        }
      }
      leaf low {
        tailf:info
          "Specify low-watermark for clamping";
        type uint32 {
          tailf:info
            "<1-2147483647>;;Number of connections";
          range "1..2147483647";
        }
      }
    }
    container session {
      tailf:info
        "Configure session total";
      container total {
        tailf:cli-compact-syntax;
        tailf:cli-sequence-commands {
          tailf:cli-reset-siblings;
        }
        leaf number {
          tailf:cli-drop-node-name;
          type uint32 {
            tailf:info
              "<1-4294967295>;;session total number";
            range "1..4294967295";
          }
        }
        container aggressive-aging {
          tailf:info
            "Aggressive Aging parameters";
          tailf:cli-flatten-container;
          tailf:cli-compact-syntax;
          tailf:cli-sequence-commands;
          leaf high {
            tailf:info
              "Specify the high watermark for aggressive-aging";
            type uint32 {
              tailf:info
                "<1-4294967295>;;High watermark in absolute values";
              range "1..4294967295";
            }
          }
          leaf low {
            tailf:info
              "Specify the low watermark for aggressive-aging";
            type uint32 {
              tailf:info
                "<1-4294967295>;;Low watermark in absolute values";
              range "1..4294967295";
            }
          }
        }
      }
    }
    container sessions {
      tailf:info
        "Maximum number of inspect sessions";
      leaf maximum {
        tailf:info
          "Maximum sessions";
        type uint32 {
          tailf:info
            "<1-2147483647>;;Number of sessions";
          range "1..2147483647";
        }
      }
    }
    container tcp {
      tailf:info
        "Config timeout values for tcp connections";
      container finwait-time {
        tailf:info
          "Specify timeout for TCP connections after a FIN";
        tailf:cli-compact-syntax;
        tailf:cli-sequence-commands {
          tailf:cli-reset-siblings;
        }
        leaf seconds {
          tailf:cli-drop-node-name;
          type uint32 {
            tailf:info
              "<1-2147483>;;Timeout in seconds";
            range "1..2147483";
          }
        }
        leaf ageout-time {
          tailf:info
            "Specify aggressive age-out time for fin wait=time";
          type uint32 {
            tailf:info
              "<1-2147483>;;Timeout in seconds";
          }
        }
      }
      container idle-time {
        tailf:info
          "Specify idle timeout for tcp connections";
        tailf:cli-compact-syntax;
        tailf:cli-sequence-commands {
          tailf:cli-reset-siblings;
        }
        leaf seconds {
          tailf:cli-drop-node-name;
          type uint32 {
            tailf:info
              "<1-2147483>;;Timeout in seconds";
            range "1..2147483";
          }
        }
        leaf ageout-time {
          tailf:info
            "Specify aggressive age-out time for tcp";
          type uint32 {
            tailf:info
              "<1-2147483>;;Timeout in seconds";
            range "1..2147483";
          }
        }
      }
      container max-incomplete {
        tailf:info
          "Specify max half-open connection per host";
        leaf host {
          tailf:info
            "Specify max half-open connection per host";
          type uint32 {
            tailf:info
              "<1-4294967295>;;half-open sessions";
            range "1..4294967295";
          }
        }
      }
      container synwait-time {
        tailf:info
          "Specify timeout for TCP connections after a SYN and no";
        tailf:cli-compact-syntax;
        tailf:cli-sequence-commands {
          tailf:cli-reset-siblings;
        }
        leaf seconds {
          tailf:cli-drop-node-name;
          type uint32 {
            tailf:info
              "<1-2147483>;;Timeout in seconds";
            range "1..2147483";
          }
        }
        leaf ageout-time {
          tailf:info
            "Specify aggressive age-out time syn wait-time";
          type uint32 {
            tailf:info
              "<1-2147483>;;Timeout in seconds";
            range "1..2147483";
          }
        }
      }
      container syn-flood {
        tailf:info
          "syn-flood config";
        leaf limit {
          tailf:info
            "syn-flood limit";
          type uint32 {
            tailf:info
              "<1-4294967295>;;number of half-open connections that triggers SYN cookie";
            range "1..4294967295";
          }
        }
        container rate {
          tailf:info
            "maximum syn packet rate";
          leaf per-destination {
            tailf:info
              "per destination";
            type uint32 {
              tailf:info
                "<1-1000000000>;;maximum rate of TCP SYN packets";
              range "1..1000000000";
            }
          }
        }
      }
    }
    container udp {
      tailf:info
        "Config timeout values for udp flows";
      container idle-time {
        tailf:info
          "Specify idle timeout for udp";
        tailf:cli-compact-syntax;
        tailf:cli-sequence-commands {
          tailf:cli-reset-siblings;
        }
        leaf seconds {
          tailf:cli-drop-node-name;
          type uint32 {
            tailf:info
              "<1-2147483>;;Timeout in seconds";
            range "1..2147483";
          }
        }
        leaf ageout-time {
          tailf:info
            "Specify aggressive age-out time for udp";
          type uint32 {
            tailf:info
              "<1-2147483>;;Timeout in seconds";
            range "1..2147483";
          }
        }
      }
      container half-open {
        tailf:info
          "Config timeout values for udp half open flow";
        container idle-time {
          tailf:info
            "Specify idle timeout for udp half open";
          tailf:cli-compact-syntax;
          tailf:cli-sequence-commands {
            tailf:cli-reset-siblings;
          }
          leaf seconds {
            tailf:cli-drop-node-name;
            type uint32 {
              tailf:info
                "<1-2147483>;;Timeout in miliseconds";
              range "1..2147483";
            }
          }
          leaf ageout-time {
            tailf:info
              "Specify aggressive age-out time for udp half open";
            type uint32 {
              tailf:info
                "<1-2147483>;;Timeout in miliseconds";
              range "1..2147483";
            }
          }
        }
      }
    }
    container log {
      tailf:info
        "Inspect packet logging";
      leaf dropped-packets {
        tailf:info
          "log packets dropped by the firewall";
        type empty;
      }
    }
    container threat-detection {
      tailf:info
        "Configure Threat Detection";
      leaf basic-threat {
        tailf:info
          "Enable Threat Detection";
        tailf:cli-full-command;
        type empty;
      }
      container rate {
        tailf:info
          "Configure Threat Detection rate";
        container syn-attack {
          tailf:info
            "Configure Threat Detection rate for syn attack events";
          tailf:cli-compact-syntax;
          tailf:cli-sequence-commands {
            tailf:cli-reset-siblings;
          }
          leaf average-time-frame {
            tailf:info
              "Configure Threat Detection average time frame";
            tailf:cli-incomplete-command;
            type uint16 {
              tailf:info
                "<600-3600>;;average time frame in seconds";
              range "6..3600";
            }
          }
          leaf average-threshold {
            tailf:info
              "Configure Threat Detection average threshold";
            tailf:cli-incomplete-command;
            type uint32 {
              tailf:info
                "<1-4294967295>;;average threshold in pkts/sec";
              range "1..4294967295";
            }
          }
          leaf burst-threshold {
            tailf:info
              "Configure Threat Detection burst threshold";
            type uint32 {
              tailf:info
                "<1-1000000000>;;burst threshold in pkts/sec";
              range "1..1000000000";
            }
          }
        }
        container inspect-drop {
          tailf:info
            "Configure Threat Detection rate for firewall inspection based drop events";
          tailf:cli-compact-syntax;
          tailf:cli-sequence-commands {
            tailf:cli-reset-siblings;
          }
          leaf average-time-frame {
            tailf:info
              "Configure Threat Detection average time frame";
            tailf:cli-incomplete-command;
            type uint16 {
              tailf:info
                "<600-3600>;;average time frame in seconds";
              range "6..3600";
            }
          }
          leaf average-threshold {
            tailf:info
              "Configure Threat Detection average threshold";
            tailf:cli-incomplete-command;
            type uint32 {
              tailf:info
                "<1-4294967295>;;average threshold in pkts/sec";
              range "1..4294967295";
            }
          }
          leaf burst-threshold {
            tailf:info
              "Configure Threat Detection burst threshold";
            type uint32 {
              tailf:info
                "<1-1000000000>;;burst threshold in pkts/sec";
              range "1..1000000000";
            }
          }
        }
        container fw-drop {
          tailf:info
            "Configure Threat Detection rate for firewall drop events";
          tailf:cli-compact-syntax;
          tailf:cli-sequence-commands {
            tailf:cli-reset-siblings;
          }
          leaf average-time-frame {
            tailf:info
              "Configure Threat Detection average time frame";
            tailf:cli-incomplete-command;
            type uint16 {
              tailf:info
                "<600-3600>;;average time frame in seconds";
              range "6..3600";
            }
          }
          leaf average-threshold {
            tailf:info
              "Configure Threat Detection average threshold";
            tailf:cli-incomplete-command;
            type uint32 {
              tailf:info
                "<1-4294967295>;;average threshold in pkts/sec";
              range "1..4294967295";
            }
          }
          leaf burst-threshold {
            tailf:info
              "Configure Threat Detection burst threshold";
            type uint32 {
              tailf:info
                "<1-1000000000>;;burst threshold in pkts/sec";
              range "1..1000000000";
            }
          }
        }
      }
    }
    list vrf {
      tailf:info
        "vrf binding with parameter map";
      tailf:cli-suppress-mode;
      tailf:cli-delete-when-empty;
      tailf:cli-incomplete-command;
      key "vrf";
      leaf vrf {
        tailf:cli-diff-dependency "../../../../../ip/vrf" {
          tailf:xpath-root 3;
        }
        tailf:cli-diff-dependency "../../../../../vrf/definition" {
          tailf:xpath-root 3;
        }
        type string {
          tailf:info
            "WORD;;vrf name";
        }
      }
      leaf inspect {
        tailf:info
          "vrf binding with parameter map";
        tailf:non-strict-leafref {
          path "../../../inspect-vrf/name";
        }
        type string {
          tailf:info
            "WORD;;parameter-map name";
        }
      }
    }
  }

  grouping dscp-value-0-7-grouping {
    leaf dscp-value0 {
      tailf:cli-drop-node-name;
      tailf:cli-prefix-key;
      type uint8 {
        tailf:info
          "<0-63>;;DSCP values separated by spaces (up to 8 values total)";
        range "0..63";
      }
    }
    leaf dscp-value1 {
      tailf:cli-drop-node-name;
      tailf:cli-optional-in-sequence;
      tailf:cli-prefix-key;
      type uint8 {
        tailf:info
          "<0-63>;;DSCP values separated by spaces (up to 8 values total)";
        range "0..63";
      }
    }
    leaf dscp-value2 {
      tailf:cli-drop-node-name;
      tailf:cli-optional-in-sequence;
      tailf:cli-prefix-key;
      type uint8 {
        tailf:info
          "<0-63>;;DSCP values separated by spaces (up to 8 values total)";
        range "0..63";
      }
    }
    leaf dscp-value3 {
      tailf:cli-drop-node-name;
      tailf:cli-optional-in-sequence;
      tailf:cli-prefix-key;
      type uint8 {
        tailf:info
          "<0-63>;;DSCP values separated by spaces (up to 8 values total)";
        range "0..63";
      }
    }
    leaf dscp-value4 {
      tailf:cli-drop-node-name;
      tailf:cli-optional-in-sequence;
      tailf:cli-prefix-key;
      type uint8 {
        tailf:info
          "<0-63>;;DSCP values separated by spaces (up to 8 values total)";
        range "0..63";
      }
    }
    leaf dscp-value5 {
      tailf:cli-drop-node-name;
      tailf:cli-optional-in-sequence;
      tailf:cli-prefix-key;
      type uint8 {
        tailf:info
          "<0-63>;;DSCP values separated by spaces (up to 8 values total)";
        range "0..63";
      }
    }
    leaf dscp-value6 {
      tailf:cli-drop-node-name;
      tailf:cli-optional-in-sequence;
      tailf:cli-prefix-key;
      type uint8 {
        tailf:info
          "<0-63>;;DSCP values separated by spaces (up to 8 values total)";
        range "0..63";
      }
    }
    leaf dscp-value7 {
      tailf:cli-drop-node-name;
      tailf:cli-optional-in-sequence;
      tailf:cli-prefix-key;
      type uint8 {
        tailf:info
          "<0-63>;;DSCP values separated by spaces (up to 8 values total)";
        range "0..63";
      }
    }
  }

  grouping cos-value-0-7-grouping {
    leaf cos-value0 {
      tailf:cli-drop-node-name;
      tailf:cli-prefix-key;
      type uint8 {
        tailf:info
          "<0-7>;;CoS values separated by spaces (up to 8 values total)";
        range "0..7";
      }
    }
    leaf cos-value1 {
      tailf:cli-drop-node-name;
      tailf:cli-optional-in-sequence;
      tailf:cli-prefix-key;
      type uint8 {
        tailf:info
          "<0-7>;;CoS values separated by spaces (up to 8 values total)";
        range "0..7";
      }
    }
    leaf cos-value2 {
      tailf:cli-drop-node-name;
      tailf:cli-optional-in-sequence;
      tailf:cli-prefix-key;
      type uint8 {
        tailf:info
          "<0-7>;;CoS values separated by spaces (up to 8 values total)";
        range "0..7";
      }
    }
    leaf cos-value3 {
      tailf:cli-drop-node-name;
      tailf:cli-optional-in-sequence;
      tailf:cli-prefix-key;
      type uint8 {
        tailf:info
          "<0-7>;;CoS values separated by spaces (up to 8 values total)";
        range "0..7";
      }
    }
    leaf cos-value4 {
      tailf:cli-drop-node-name;
      tailf:cli-optional-in-sequence;
      tailf:cli-prefix-key;
      type uint8 {
        tailf:info
          "<0-7>;;CoS values separated by spaces (up to 8 values total)";
        range "0..7";
      }
    }
    leaf cos-value5 {
      tailf:cli-drop-node-name;
      tailf:cli-optional-in-sequence;
      tailf:cli-prefix-key;
      type uint8 {
        tailf:info
          "<0-7>;;CoS values separated by spaces (up to 8 values total)";
        range "0..7";
      }
    }
    leaf cos-value6 {
      tailf:cli-drop-node-name;
      tailf:cli-optional-in-sequence;
      tailf:cli-prefix-key;
      type uint8 {
        tailf:info
          "<0-7>;;CoS values separated by spaces (up to 8 values total)";
        range "0..7";
      }
    }
    leaf cos-value7 {
      tailf:cli-drop-node-name;
      tailf:cli-optional-in-sequence;
      tailf:cli-prefix-key;
      type uint8 {
        tailf:info
          "<0-7>;;CoS values separated by spaces (up to 8 values total)";
        range "0..7";
      }
    }
  }

  grouping controller-modular-cable-rf-channel-grouping {
    list rf-channel {
      tailf:info
        "RF channel configuration";
      tailf:cli-suppress-mode;
      tailf:cli-delete-when-empty;
      key "rf-port";
      leaf rf-port {
        type uint8 {
          tailf:info
            "<0-23>;;RF channel number";
          range "0..23";
        }
      }
      leaf description {
        tailf:info
          "configure RF channel name/description";
        tailf:cli-multi-value;
        tailf:cli-preformatted;
        tailf:cli-full-command;
        type string {
          tailf:info
            "LINE;;Description of this RF channel that will be truncated to 80 characters";
        }
      }
      container cable {
        tailf:info
          "configure RF channel cable downstream channel-id";
        container downstream {
          tailf:info
            "configure RF channel cable downstream channel-id";
          leaf channel-id {
            tailf:info
              "configure RF channel cable downstream channel-id";
            type uint8 {
              tailf:info
                "<1-255>;;RF channel cable downstream channel-id";
              range "1..255";
            }
          }
        }
      }
      container frequency {
        tailf:info
          "configure RF channel frequency in Hz";
        tailf:cli-compact-syntax;
        tailf:cli-sequence-commands {
          tailf:cli-reset-siblings;
        }
        leaf freq {
          tailf:cli-drop-node-name;
          type union {
            type uint32 {
              tailf:info
                "<55000000-1050000000>;;Frequency in Hz";
              range "55000000..1050000000";
            }
            type enumeration {
              enum "none" {
                tailf:info
                  "No Frequency configured";
              }
            }
          }
        }
        leaf annex {
          tailf:info
            "ITU-T J.83 MPEG standard";
          tailf:cli-incomplete-command;
          type enumeration {
            enum "A" {
              tailf:info
                "Annex A, European Standard";
            }
            enum "B" {
              tailf:info
                "Annex B, North American Standard";
            }
          }
        }
        leaf modulation {
          tailf:info
            "configure RF channel modulation type";
          type enumeration {
            enum "256qam" {
              tailf:info
                "256-QAM modulation";
            }
            enum "64qam" {
              tailf:info
                "64-QAM modulation";
            }
          }
        }
        leaf interleave {
          tailf:info
            "Interleave depth";
          type enumeration {
            enum "128" {
              tailf:info
                "R/S Interleave I=128, J=1";
            }
            enum "16" {
              tailf:info
                "R/S Interleave I=16, J=8";
            }
            enum "32" {
              tailf:info
                "R/S Interleave I=32, J=4";
            }
            enum "64" {
              tailf:info
                "R/S Interleave I=64, J=2";
            }
            enum "8" {
              tailf:info
                "R/S Interleave I=8, J=16";
            }
            enum "12" {
              tailf:info
                "R/S Interleave I=12, J=17";
            }
          }
        }
      }
      container ip-address {
        tailf:info
          "configure IP address of edge QAM";
        tailf:cli-compact-syntax;
        tailf:cli-sequence-commands {
          tailf:cli-reset-siblings;
        }
        leaf ip-address {
          tailf:cli-drop-node-name;
          tailf:cli-incomplete-command;
          type inet:ipv4-address {
            tailf:info
              "A.B.C.D;;IP address of edge QAM";
          }
        }
        leaf mac-address {
          tailf:info
            "MAC address of edge QAM";
          tailf:cli-incomplete-command;
          type string {
            tailf:info
              "H.H.H;;MAC address of edge QAM";
          }
        }
        leaf depi-remote-id {
          tailf:info
            "configure DEPI session ID for edge QAM";
          type uint32 {
            tailf:info
              "<1-4294967295>;;DEPI remote ID";
            range "1..4294967295";
          }
        }
        leaf eqam-headroom {
          tailf:info
            "Headroom for Edge QAM channel";
          type uint8 {
            tailf:info
              "<0-28>;;EdgeQAM Headroom";
            range "0..28";
          }
        }
      }
      container network-delay {
        tailf:info
          "Delay through Converged Interconnect Network (CIN) to EQAM";
        choice network-delay-choice {
          leaf usec {
            tailf:cli-drop-node-name;
            type uint16 {
              tailf:info
                "<0-3000>;;CIN delay in usec";
              range "0..3000";
            }
          }
          container auto {
            tailf:info
              "CIN Delay via DLM Measurements";
            tailf:cli-delete-when-empty;
            presence "true";
            leaf sampling-rate {
              tailf:info
                "Sampling Rate for DLM Request";
              type uint16 {
                tailf:info
                  "<1-500>;;DLM Sampling Rate in sec";
                range "1..500";
              }
            }
          }
        }
      }
      container depi-tunnel {
        tailf:info
          "DEPI Data Session Configuration";
        tailf:cli-compact-syntax;
        tailf:cli-sequence-commands {
          tailf:cli-reset-siblings;
        }
        leaf depi-tunnel-name {
          tailf:cli-drop-node-name;
          tailf:cli-incomplete-command;
          type string {
            tailf:info
              "WORD;;depi-tunnel name";
          }
        }
        leaf tsid {
          tailf:info
            "tsid ";
          type uint16 {
            tailf:info
              "<0-65535>;;tsid value";
          }
        }
      }
      leaf rf-power {
        tailf:info
          "Set RF Power";
        type string {
          tailf:info
            "<1-100>;;dBmV (The format is XY.Z; by default, .Z is .0)";
        }
      }
      leaf rf-shutdown {
        tailf:cli-boolean-no;
        tailf:cli-full-command;
        type boolean;
        default "true";
      }
    }
  }

  grouping controller-integrated-cable-rf-chan-grouping {
    leaf type {
      tailf:info
        "QAM Data Type";
      type enumeration {
        enum "DOCSIS" {
          tailf:info
            "DOCSIS";
        }
        enum "VIDEO" {
          tailf:info
            "VIDEO";
        }
      }
    }
    leaf frequency {
      tailf:info
        "RF Channel Frequency";
      type uint32 {
        tailf:info
          "<93000000-861000000>;;frequency";
        range "93000000..861000000";
      }
    }
    leaf rf-output {
      tailf:info
        "QAM Output Mode";
      type enumeration {
        enum "ALT" {
          tailf:info
            "ALT";
        }
        enum "CW" {
          tailf:info
            "CW";
        }
        enum "NORMAL" {
          tailf:info
            "NORMAL";
        }
        enum "PRBS" {
          tailf:info
            "PRBS";
        }
      }
    }
    leaf power-adjust {
      tailf:info
        "Channel Power Adjust";
      type string {
        tailf:info
          "WORD;;Power Adjust Range:  -8.0 -  0.0 dBmV";
      }
    }
    leaf qam-profile {
      tailf:info
        "QAM Profile Number";
      type uint8 {
        tailf:info
          "<0-31>;;qam profile number";
        range "0..31";
      }
    }
    leaf docsis-channel-id {
      tailf:info
        "Docsis Channel Id";
      type uint8 {
        tailf:info
          "<1-255>;;dcid";
        range "1..255";
      }
    }
  }

  grouping object-group-service-protocol-match {
    choice match-choice {
      leaf eq {
        tailf:info
          "Match only packets on a given port number";
        tailf:cli-prefix-key {
          tailf:cli-before-key 1;
        }
        type empty;
      }
      leaf gt {
        tailf:info
          "Match only packets with a greater port number";
        tailf:cli-prefix-key {
          tailf:cli-before-key 1;
        }
        type empty;
      }
      leaf lt {
        tailf:info
          "Match only packets with a lower port number";
        tailf:cli-prefix-key {
          tailf:cli-before-key 1;
        }
        type empty;
      }
    }
  }

  grouping arp-grouping {
    list arp-list {
      tailf:cli-drop-node-name;
      tailf:cli-suppress-mode;
      tailf:cli-delete-when-empty;
      tailf:cli-incomplete-command;
      tailf:cli-compact-syntax;
      tailf:cli-sequence-commands {
        tailf:cli-reset-all-siblings;
      }
      key "ip-address";
      leaf ip-address {
        type inet:ipv4-address {
          tailf:info
            "A.B.C.D;;IP address of ARP entry";
        }
      }
      leaf hardware-address {
        tailf:cli-drop-node-name;
        tailf:cli-incomplete-command;
        type string {
          tailf:info
            "H.H.H;;48-bit hardware address of ARP entry";
          pattern '[0-9a-fA-F]+\.[0-9a-fA-F]+\.[0-9a-fA-F]+';
        }
      }
      leaf type {
        tailf:cli-drop-node-name;
        type enumeration {
          enum "ARPA" {
            tailf:info
              "ARP type ARPA";
          }
          enum "SAP" {
            tailf:info
              "ARP type SAP (HP's ARP type)";
          }
          enum "SMDS" {
            tailf:info
              "ARP type SMDS";
          }
          enum "SNAP" {
            tailf:info
              "ARP type SNAP (FDDI and TokenRing)";
          }
          enum "SRP-A" {
            tailf:info
              "ARP type SRP (side A)";
          }
          enum "SRP-B" {
            tailf:info
              "ARP type SRP (side B)";
          }
        }
      }
      leaf alias {
        tailf:info
          "Respond to ARP requests for the IP address";
        type empty;
      }
    }
  }

  grouping interface-encryption-mode-grouping {
    container mode {
      tailf:info
        "encryption mode";
      container ciphers {
        tailf:info
          "Optional data ciphers";
        tailf:cli-flatten-container;
        tailf:cli-compact-syntax;
        tailf:cli-reset-container;
        choice suite-choice {
          leaf ckip {
            tailf:info
              "Cisco Per packet key hashing";
            type empty;
          }
          leaf ckip-cmic {
            tailf:info
              "Cisco Per packet key hashing and MIC (MMH)";
            type empty;
          }
          leaf cmic {
            tailf:info
              "Cisco MIC (MMH)";
            type empty;
          }
          case a {
            leaf aes-ccm {
              tailf:info
                "WPA AES CCMP";
              type empty;
            }
            leaf tkip {
              tailf:info
                "WPA Temporal Key encryption";
              type empty;
            }
            leaf wep {
              tailf:cli-drop-node-name;
              type enumeration {
                enum "wep128" {
                  tailf:info
                    "128 bit key";
                }
                enum "wep40" {
                  tailf:info
                    "40 bit key";
                }
              }
            }
          }
        }
      }
    }
  }

  grouping ip-ssh-algorithm-grouping {
    container algorithm {
      tailf:info
        "Configure different algorithms used in SSH";
      leaf-list mac {
        tailf:info
          "MAC algorithms advertised to other party";
        tailf:cli-replace-all;
        tailf:cli-flat-list-syntax;
        type enumeration {
          enum "hmac-sha1" {
            tailf:info
              "HMAC-SHA1 (digest length = key length = 160 bits)";
          }
          enum "hmac-sha1-96" {
            tailf:info
              "HMAC-SHA1-96 (digest length = 96 bits, key length = 160 bits)";
          }
        }
      }
      leaf-list encryption {
        tailf:info
          "Encrytption algorithms advertised to other party";
        tailf:cli-replace-all;
        tailf:cli-flat-list-syntax;
        ordered-by user;
        type enumeration {
          enum "3des-cbc" {
            tailf:info
              "Three-key 3DES in CBC mode";
          }
          enum "aes128-cbc" {
            tailf:info
              "AES with 128-bit key in CBC mode";
          }
          enum "aes128-ctr" {
            tailf:info
              "AES with 128-bit key in CTR mode";
          }
          enum "aes192-cbc" {
            tailf:info
              "AES with 192-bit key in CBC mode";
          }
          enum "aes192-ctr" {
            tailf:info
              "AES with 192-bit key in CTR mode";
          }
          enum "aes256-cbc" {
            tailf:info
              "AES with 256-bit key in CBC mode";
          }
          enum "aes256-ctr" {
            tailf:info
              "AES with 256-bit key in CTR mode";
          }
        }
      }
    }
  }

  grouping bandwidth-remaining-account-grouping {
    container account {
      tailf:info
        "Overhead Accounting";
      tailf:cli-flatten-container;
      tailf:cli-compact-syntax;
      tailf:cli-sequence-commands;
      choice account-choice {
        case dot1q-qing {
          leaf bras-side {
            tailf:cli-drop-node-name;
            tailf:cli-incomplete-command;
            type enumeration {
              enum "dot1q" {
                tailf:info
                  "dot1Q at BRAS side";
              }
              enum "qinq" {
                tailf:info
                  "QinQ at BRAS side";
              }
            }
          }
          leaf aal {
            tailf:cli-drop-node-name;
            tailf:cli-incomplete-command;
            type enumeration {
              enum "aal3" {
                tailf:info
                  "AAL3 Layer type";
              }
              enum "aal5" {
                tailf:info
                  "AAL5 Layer type";
              }
            }
          }
          leaf subscriber-encapsulation {
            tailf:cli-drop-node-name;
            type enumeration {
              enum "mux-1483routed" {
                tailf:info
                  "Mux 1483 Routed";
              }
              enum "mux-dot1q-rbe" {
                tailf:info
                  "Mux Bridging and dot1Q encapsulation";
              }
              enum "mux-pppoa" {
                tailf:info
                  "Mux PPPoA";
              }
              enum "mux-rbe" {
                tailf:info
                  "Mux Bridging encapsulation";
              }
              enum "snap-1483routed" {
                tailf:info
                  "Snap 1483 Routed";
              }
              enum "snap-dot1q-rbe" {
                tailf:info
                  "Snap Bridging and dot1Q encapsulation";
              }
              enum "snap-pppoa" {
                tailf:info
                  "Snap PPPoA encapsulation";
              }
              enum "snap-rbe" {
                tailf:info
                  "Snap Bridging encapsulation";
              }
            }
          }
        }
        leaf user-defined {
          tailf:info
            "Offset Size";
          type int8 {
            tailf:info
              "<-63 - 63>;;User Defined size";
          }
        }
      }
    }
  }

  grouping result-type-method-grouping {
    leaf authoritative {
      tailf:info
        "failure type";
      type empty;
    }
    leaf agent-not-found {
      tailf:info
        "agent not found type";
      type empty;
    }
    leaf none {
      tailf:info
        "no type";
      type empty;
    }
    leaf success {
      tailf:info
        "success type";
      type empty;
    }
    leaf method-timeout {
      tailf:info
        "method_timeout type";
      type empty;
    }
    leaf aaa-timeout {
      tailf:info
        "aaa timeout type";
      type empty;
    }
  }

  grouping interface-vrrp-grouping {
    leaf description {
      tailf:info
        "Group specific description";
      tailf:cli-multi-value;
      tailf:cli-preformatted;
      tailf:cli-full-command;
      type string {
        tailf:info
          "LINE;;Up to 80 characters describing this group";
        length "1..80";
      }
    }
    container vrrs {
      tailf:info
        "VRRS related commands";
      list leader {
        tailf:info
          "Name of VRRS Tag for which this group is the leader";
        tailf:cli-suppress-mode;
        tailf:cli-delete-when-empty;
        key "name";
        leaf name {
          type string {
            tailf:info
              "WORD;;Name of the VRRS Tag to lead";
          }
        }
      }
    }
    container preempt {
      tailf:info
        "Enable preemption of lower priority Master";
      container delay {
        tailf:info
          "Wait before preempting";
        leaf minimum {
          tailf:info
            "Delay at least this long";
          type uint16 {
            tailf:info
              "<0-3600>;;Seconds to delay";
            range "0..3600";
          }
        }
      }
    }
    leaf priority {
      tailf:info
        "Priority of this VRRP group";
      tailf:cli-full-command;
      type uint8 {
        tailf:info
          "<1-254>;;Priority level";
        range "1..254";
      }
    }
    container timers {
      tailf:info
        "Set the VRRP timers";
      container advertise {
        tailf:info
          "Set the Advertisement timer";
        leaf seconds {
          tailf:cli-drop-node-name;
          type uint8 {
            tailf:info
              "<1-255>;;Advertisement interval in seconds";
            range "1..255";
          }
        }
        leaf msec {
          tailf:info
            "Specify time in milliseconds";
          tailf:cli-full-command;
          type uint16 {
            tailf:info
              "<50-999>;;Advertisement interval in milliseconds";
            range "50..999";
          }
        }
      }
      leaf learn {
        tailf:info
          "Learn timer values from current Master";
        tailf:cli-full-command;
        type empty;
      }
    }
    list track {
      tailf:info
        "Event Tracking";
      tailf:cli-suppress-mode;
      tailf:cli-delete-when-empty;
      key "name";
      leaf name {
        type uint16 {
          tailf:info
            "<1-1000>;;Tracked object";
          range "1..1000";
        }
      }
      leaf decrement {
        tailf:info
          "Priority decrement";
        tailf:cli-full-command;
        type uint16 {
          tailf:info
            "<1-255>;;Decrement value";
        }
      }
    }
    leaf shutdown {
      tailf:info
        "Disable VRRP Configuration";
      tailf:cli-full-command;
      type empty;
    }
  }

  grouping router-bgp-aggregate-address-content-grouping {
    leaf as-set {
      tailf:cli-break-sequence-commands;
      tailf:info
        "Generate AS set path information";
      type empty;
    }
    leaf summary-only {
      tailf:info
        "Filter more specific routes from updates";
      type empty;
    }
    leaf attribute-map {
      tailf:info
        "Set attributes of aggregate";
      type string {
        tailf:info
          "WORD;;Route map for parameter control";
      }
    }
    leaf advertise-map {
      tailf:info
        "Set condition to advertise attribute";
      type string {
        tailf:info
          "WORD;;Route map to control attribute advertisement";
      }
    }
    leaf suppress-map {
      tailf:info
        "Conditionally filter more specific routes from updates";
      type string {
        tailf:info
          "WORD;;Route map for suppression";
      }
    }
    leaf as-override {
      tailf:info
        "Override matching AS-number while sending update";
      type empty;
    }
    leaf route-map {
      tailf:info
        "Set parameters of aggregate";
      type string {
        tailf:info
          "WORD;;Route map for parameter control";
      }
    }
  }

  grouping ip-dns-view-grouping {
    container domain {
      tailf:info
        "Configure DNS Resolver parameters";
      container name-server {
        tailf:info
          "Domain server IP address";
        list vrf {
          tailf:cli-suppress-mode;
          tailf:cli-delete-when-empty;
          tailf:cli-show-long-obu-diffs;
          ordered-by user;
          key "name address";
          leaf name {
            type string {
              tailf:info
                "WORD;;VRF name";
            }
          }
          leaf address {
            type union {
              type inet:ipv4-address {
                tailf:info
                  "A.B.C.D;;Host IP address";
              }
              type inet:ipv6-address {
                tailf:info
                  "X:X:X:X::X;;Host IPv6 address";
              }
            }
          }
        }
        container interface {
          tailf:info
            "Gather dynamically from interface address acquisition";
          uses interface-name-grouping;
        }
      }
    }
    container dns {
      tailf:info
        "Configure DNS Server parameters";
      container forwarding {
        tailf:info
          "Configure DNS server forwarding";
        container source-interface {
          tailf:info
            "Specify source address when forwarding queries";
          uses interface-name-grouping;
        }
      }
    }
  }

  grouping ip-igmp-grouping {
    leaf limit {
      tailf:info
        "IGMP limit";
      tailf:cli-full-command;
      type uint16 {
        tailf:info
          "<1-64000>;;Max Allowed State";
        range "1..64000";
      }
    }
    container ssm-map {
      tailf:info
        "SSM mapping commands";
      leaf enable {
        tailf:info
          "Enable SSM group to source mapping";
        type empty;
      }
      container query {
        tailf:info
          "Which database should we query for the source";
        leaf dns {
          tailf:info
            "Use DNS for source lookup";
          tailf:cli-boolean-no;
          type boolean;
          default "true";
        }
      }
      container static {
        tailf:info
          "SSM static group to source mapping";
        tailf:cli-compact-syntax;
        tailf:cli-sequence-commands;
        leaf access-list {
          tailf:cli-drop-node-name;
          tailf:cli-incomplete-command;
          type std-ip-acl-type;
        }
        leaf source-address {
          tailf:cli-drop-node-name;
          type inet:ipv4-address {
            tailf:info
              "A.B.C.D;;SSM source address";
          }
        }
      }
    }
  }

  grouping ip-msdp-grouping {
    list peer {
      tailf:info
        "Configure an MSDP peer";
      tailf:cli-suppress-mode;
      tailf:cli-delete-when-empty;
      key "address";
      leaf address {
        type inet:host {
          tailf:info
            "Hostname or A.B.C.D;;Peer name or address";
        }
      }
      container connect-source {
        tailf:info
          "Configure source address used for MSDP connection";
        tailf:cli-flatten-container;
        tailf:cli-compact-syntax;
        uses interface-name-grouping;
      }
      leaf remote-as {
        tailf:info
          "Configured AS number";
        type uint16 {
          tailf:info
            "<1-65535>;;Autonomous System Number";
          range "1..65535";
        }
      }
    }
    list description {
      tailf:info
        "Peer specific description";
      tailf:cli-suppress-mode;
      tailf:cli-delete-when-empty;
      tailf:cli-diff-dependency "../peer" {
        tailf:xpath-root 3;
      }
      key "address";
      leaf address {
        type inet:host {
          tailf:info
            "Hostname or A.B.C.D;;Peer name or address";
        }
      }
      leaf text {
        tailf:cli-drop-node-name;
        tailf:cli-multi-value;
        tailf:cli-preformatted;
        type string {
          tailf:info
            "LINE;;Up to 80 characters describing this pee";
        }
      }
    }
    list keepalive {
      tailf:info
        "Configure keepalive parameters for a peer";
      tailf:cli-suppress-mode;
      tailf:cli-delete-when-empty;
      tailf:cli-compact-syntax;
      tailf:cli-incomplete-command;
      tailf:cli-diff-dependency "../peer" {
        tailf:xpath-root 3;
      }
      key "address";
      leaf address {
        type inet:host {
          tailf:info
            "Hostname or A.B.C.D;;Peer name or address";
        }
      }
      leaf keepalive-interval {
        tailf:cli-drop-node-name;
        type uint8 {
          tailf:info
            "<1-60>;;Send keepalive period in seconds";
          range "1..60";
        }
      }
      leaf hold-time-interval {
        tailf:cli-drop-node-name;
        type uint8 {
          tailf:info
            "<1-75>;;Maximum time in seconds to wait for a message";
          range "1..75";
        }
      }
    }
    list sa-filter {
      tailf:info
        "Filter SA messages from peer";
      tailf:cli-suppress-mode;
      tailf:cli-delete-when-empty;
      tailf:cli-compact-syntax;
      tailf:cli-incomplete-command;
      tailf:cli-diff-dependency "../peer" {
        tailf:xpath-root 3;
      }
      key "direction address";
      leaf direction {
        type enumeration {
          enum "in" {
            tailf:info
              "Enable incoming SA filtering";
          }
          enum "out" {
            tailf:info
              "Enable outgoing SA filtering";
          }
        }
      }
      leaf address {
        type inet:host {
          tailf:info
            "Hostname or A.B.C.D;;Peer name or address";
        }
      }
      choice list-choice {
        leaf list {
          tailf:info
            "Access-list";
          type ext-acl-type;
        }
        leaf route-map {
          tailf:info
            "Route-map";
          type string {
            tailf:info
              "WORD;;route-map name";
          }
        }
        leaf rp-list {
          tailf:info
            "Access-list for originating RP";
          type union {
            type uint16 {
              tailf:info
                "<1-99>;;Standard IP access list";
              range "1..99";
            }
            type string {
              tailf:info
                "WORD;;IP Named Standard Access list";
            }
          }
        }
        leaf rp-route-map {
          tailf:info
            "Route-map for originating RP";
          type string {
            tailf:info
              "WORD;;Route-map reference";
          }
        }
      }
    }
    container originator-id {
      tailf:info
        "Configure MSDP Originator ID";
      uses interface-name-grouping;
    }
    container mesh-group {
      tailf:info
        "Configure an MSDP mesh-group";
      tailf:cli-compact-syntax;
      tailf:cli-sequence-commands {
        tailf:cli-reset-siblings;
      }
      leaf name {
        tailf:cli-drop-node-name;
        type string {
          tailf:info
            "WORD;;Name of mesh-group";
        }
      }
      leaf address {
        tailf:cli-drop-node-name;
        type inet:host {
          tailf:info
            "Hostname or A.B.C.D;;Peer name or address";
        }
      }
    }
  }

  grouping if-srv-encapsulation-dot1q-grouping {
    leaf-list id {
      tailf:cli-drop-node-name;
      tailf:cli-range-list-syntax;
      tailf:cli-replace-all;
      type union {
        type uint16 {
          tailf:info
            "<1-4094>;;VLAN id";
          range "1..4094";
        }
        type enumeration {
          enum "any" {
            tailf:info
              "For all VLANS [1-4094]";
          }
        }
      }
    }
    leaf second-dot1q {
      tailf:cli-break-sequence-commands;
      tailf:info
        "inner 802.1Q Virtual LAN or C-VLAN";
      type union {
        type uint16 {
          tailf:info
            "<1-4094>;;VLAN id";
          range "1..4094";
        }
        type enumeration {
          enum "any" {
            tailf:info
              "For all VLANS [1-4094]";
          }
        }
      }
    }
    leaf cos {
      tailf:info
        "cos Vlan";
      type uint8 {
        tailf:info
          "<0-7>;;cos values";
        range "0..7";
      }
    }
    leaf etype {
      tailf:info
        "payload ethertype after Vlan Field";
      type enumeration {
        enum "ipv4" {
          tailf:info
            "IPv4";
        }
        enum "ipv6" {
          tailf:info
            "IPv6";
        }
        enum "pppoe-all" {
          tailf:info
            "PPPoE ALL";
        }
        enum "pppoe-discovery" {
          tailf:info
            "PPPoE Discovery Stage";
        }
        enum "pppoe-session" {
          tailf:info
            "PPPoE Session Stage";
        }
      }
    }
  }

  grouping ip-wccp-grouping {
    container source-interface {
      tailf:info
        "Set source interface for Router ID";
      uses interface-name-grouping;
    }
    container web-cache {
      tailf:info
        "Standard web caching service";
      presence "true";
    }
    list wccp-list {
      tailf:cli-drop-node-name;
      tailf:cli-suppress-mode;
      tailf:cli-delete-when-empty;
      tailf:cli-compact-syntax;
      tailf:cli-sequence-commands {
        tailf:cli-reset-all-siblings;
      }
      key "service-number";
      leaf service-number {
        tailf:cli-suppress-range;
        type uint8 {
          tailf:info
            "<0-254>;;Dynamically defined service identifier number";
          range "0..254";
        }
      }
      leaf redirect-list {
        tailf:cli-break-sequence-commands;
        tailf:info
          "Set the access-list used to permit redirection";
        type exp-ip-acl-type;
      }
      leaf group-list {
        tailf:info
          "Set the access-list used to permit group membership";
        type std-acl-type;
      }
      container password {
        tailf:info
          "Authentication password (key)";
        tailf:cli-flatten-container;
        tailf:cli-compact-syntax;
        tailf:cli-sequence-commands;
        uses password-grouping;
      }
    }
  }

  grouping interface-ip-wccp-grouping {
    list wccp-list {
      tailf:cli-drop-node-name;
      tailf:cli-suppress-mode;
      tailf:cli-delete-when-empty;
      key "service-number";
      leaf service-number {
        tailf:cli-suppress-range;
        type uint8 {
          tailf:info
            "<0-254>;;Dynamically defined service identifier number";
          range "0..254";
        }
      }
      container redirect {
        tailf:info
          "Set packet redirection options for the service";
        leaf in {
          tailf:info
            "Redirect to a Cache Engine appropriate inbound packets";
          type empty;
        }
        leaf out {
          tailf:info
            "Redirect to a Cache Engine appropriate outbound packets";
          type empty;
        }
      }
    }
  }

  grouping spanning-tree-portfast-grouping {
    leaf default {
      tailf:info
        "Enable portfast by default on all access ports";
      tailf:cli-full-command;
      type empty;
    }
    container bpdufilter {
      tailf:info
        "Enable portfast bdpu filter on this switch";
      leaf default {
        tailf:info
          "Enable portfast by default on all access ports";
        type empty;
      }
    }
    container bpduguard {
      tailf:info
        "Enable portfast bpdu guard on this switch";
      leaf default {
        tailf:info
          "Enable portfast by default on all access ports";
        type empty;
      }
    }
  }

  grouping domain-path-preference-grouping {
    container path-preference {
      tailf:info
        "Specify the preferred provider";
      tailf:cli-compact-syntax;
      tailf:cli-sequence-commands {
        tailf:cli-reset-siblings;
      }
      leaf path1 {
        tailf:cli-drop-node-name;
        tailf:cli-incomplete-command;
        type string {
          tailf:info
            "WORD;;Primary service provider";
        }
      }
      leaf path2 {
        tailf:cli-optional-in-sequence;
        tailf:cli-drop-node-name;
        tailf:cli-incomplete-command;
        tailf:cli-disallow-value "fallback";
        type string {
          tailf:info
            "WORD;;Primary service provider";
        }
      }
      leaf path3 {
        tailf:cli-optional-in-sequence;
        tailf:cli-drop-node-name;
        tailf:cli-incomplete-command;
        tailf:cli-disallow-value "fallback";
        type string {
          tailf:info
            "WORD;;Primary service provider";
        }
      }
      leaf fallback {
        tailf:info
          "Specify the fallback provider's color";
        tailf:cli-incomplete-command;
        type empty;
      }
      leaf fallback-path1 {
        tailf:cli-optional-in-sequence;
        tailf:cli-drop-node-name;
        tailf:cli-disallow-value "blackhole|routing|next-fallback";
        type string {
          tailf:info
            "WORD;;Fallback service provider";
        }
      }
      leaf fallback-path2 {
        tailf:cli-optional-in-sequence;
        tailf:cli-drop-node-name;
        tailf:cli-disallow-value "blackhole|routing|next-fallback";
        type string {
          tailf:info
            "WORD;;Fallback service provider";
        }
      }
      leaf fallback-path3 {
        tailf:cli-optional-in-sequence;
        tailf:cli-drop-node-name;
        tailf:cli-disallow-value "blackhole|routing|next-fallback";
        type string {
          tailf:info
            "WORD;;Fallback service provider";
        }
      }
      leaf next-fallback {
        when "../fallback-path1" {
          tailf:xpath-root 3;
          tailf:dependency "../fallback-path1";
        }
        tailf:info
          "Specify the next-fallback service provider";
        tailf:cli-optional-in-sequence;
        tailf:cli-incomplete-command;
        type empty;
      }
      leaf blackhole {
        tailf:info
          "Drop the packet if primary unavailable";
        tailf:cli-optional-in-sequence;
        tailf:cli-full-command;
        type empty;
      }
      leaf routing {
        tailf:info
          "No Fallback provider";
        tailf:cli-optional-in-sequence;
        tailf:cli-full-command;
        type empty;
      }
      leaf next-fallback-path1 {
        tailf:cli-drop-node-name;
        tailf:cli-disallow-value "blackhole|routing|next-fallback";
        type string {
          tailf:info
            "WORD;;Next-fallback service provider";
        }
      }
      leaf next-fallback-path2 {
        tailf:cli-drop-node-name;
        type string {
          tailf:info
            "WORD;;Next-fallback service provider";
        }
      }
      leaf next-fallback-path3 {
        tailf:cli-drop-node-name;
        type string {
          tailf:info
            "WORD;;Next-fallback service provider";
        }
      }
    }
  }

  grouping lifetime-grouping {
    leaf start-time {
      tailf:cli-drop-node-name;
      tailf:cli-incomplete-command;
      type hhmm-type {
        tailf:info
          "hh:mm;;Time to start (hh:mm)";
      }
    }
    leaf start-month {
      tailf:cli-drop-node-name;
      tailf:cli-incomplete-command;
      type month-type {
        tailf:info
          "MONTH;;Month of the year to start";
      }
    }
    leaf start-date {
      tailf:cli-drop-node-name;
      tailf:cli-incomplete-command;
      type uint8 {
        tailf:info
          "<1-31>;;Day of the month to start";
        range "1..31";
      }
    }
    leaf start-year {
      tailf:cli-drop-node-name;
      tailf:cli-incomplete-command;
      type uint16 {
        tailf:info
          "<1993-2035>;;Year to start";
        range "1993..2035";
      }
    }
    leaf duration {
      tailf:info
        "Set key lifetime duration";
      tailf:cli-optional-in-sequence;
      tailf:cli-full-command;
      type uint32 {
        tailf:info
          "<1-2147483646>;;Seconds";
        range "1..2147483646";
      }
    }
    leaf infinite {
      tailf:info
        "Never expires";
      tailf:cli-optional-in-sequence;
      tailf:cli-full-command;
      type empty;
    }
    leaf stop-time {
      tailf:cli-drop-node-name;
      tailf:cli-incomplete-command;
      type hhmm-type {
        tailf:info
          "hh:mm;;Time to stop (hh:mm)";
      }
    }
    leaf stop-month {
      tailf:cli-drop-node-name;
      tailf:cli-incomplete-command;
      type month-type {
        tailf:info
          "MONTH;;Month of the year to stop";
      }
    }
    leaf stop-date {
      tailf:cli-drop-node-name;
      tailf:cli-incomplete-command;
      type uint8 {
        tailf:info
          "<1-31>;;Day of the month to stop";
        range "1..31";
      }
    }
    leaf stop-year {
      tailf:cli-drop-node-name;
      type uint16 {
        tailf:info
          "<1993-2035>;;Year to stop";
        range "1993..2035";
      }
    }
  }

  grouping us-channel-grouping {
    list us-channel {
      tailf:info
        "Upstream channel configuration";
      tailf:cli-suppress-mode;
      tailf:cli-delete-when-empty;
      key "id";
      leaf id {
        type uint8 {
          tailf:info
            "<0-11>;;Upstream channel number";
          range "0..11";
        }
      }
      leaf frequency {
        tailf:info
          "Frequency";
        type uint32 {
          tailf:info
            "<5000000-85000000>;;Upstream Frequency in Hz";
          range "5000000..85000000";
        }
      }
      container channel-width {
        tailf:info
          "Channel width in HZ";
        tailf:cli-compact-syntax;
        tailf:cli-sequence-commands {
          tailf:cli-reset-siblings;
        }
        leaf first-choice-width {
          tailf:cli-drop-node-name;
          type uint32 {
            tailf:info
              "Channel width Hz";
          }
        }
        leaf last-choice-width {
          tailf:cli-drop-node-name;
          type uint32 {
            tailf:info
              "Channel width Hz";
          }
        }
      }
      leaf power-level {
        tailf:info
          "Input power level";
        type int8 {
          tailf:info
            "<-13 - 23>;;Power level in dBmV";
          range "-13..23";
        }
      }
      leaf docsis-mode {
        tailf:info
          "Upstream channel DOCSIS mode";
        type enumeration {
          enum "atdma" {
            tailf:info
              "DOCSIS 2.0 ATDMA-only channel";
          }
          enum "scdma" {
            tailf:info
              "DOCSIS 2.0 SCDMA-only channel";
          }
          enum "tdma" {
            tailf:info
              "DOCSIS 1.x-only channel";
          }
          enum "tdma-atdma" {
            tailf:info
              "DOCSIS 1.x and DOCSIS 2.0 mixed channel";
          }
        }
      }
      leaf minislot-size {
        tailf:info
          "Minislot size";
        type uint8 {
          tailf:info
            "Minislot size in time ticks";
          range "1|2|4|8|16|32|64|128";
        }
      }
      container modulation-profile {
        tailf:info
          "Modulation Profile Number";
        tailf:cli-compact-syntax;
        tailf:cli-sequence-commands {
          tailf:cli-reset-siblings;
        }
        leaf primary-profile-number {
          tailf:cli-drop-node-name;
          type uint8 {
            tailf:info
              "VALUE;;modulation number";
          }
        }
        leaf secondary-profile-number {
          tailf:cli-drop-node-name;
          type uint8 {
            tailf:info
              "VALUE;;secondary modulation number";
          }
        }
        leaf tertiary-profile-number {
          tailf:cli-drop-node-name;
          type uint8 {
            tailf:info
              "VALUE;;tertiary modulation number";
          }
        }
      }
      leaf equalization-coefficient {
        tailf:info
          "Enable equalization coefficient";
        type empty;
      }
      leaf shutdown {
        tailf:info
          "Shutdown the upstream channel";
        tailf:cli-show-no;
        type empty;
      }
    }
  }

  grouping ip-explicit-path-grouping {
    list index {
      tailf:info
        "Specify entry index ";
      tailf:cli-suppress-mode;
      tailf:cli-delete-when-empty;
      tailf:cli-compact-syntax;
      key "id";
      leaf id {
        type uint16 {
          tailf:info
            "<1-65535>;;Entry index number";
        }
      }
      choice address-choice {
        leaf next-address {
          tailf:info
            "Specify the next address in the path";
          tailf:cli-no-name-on-delete;
          tailf:cli-no-value-on-delete;
          type inet:ipv4-address {
            tailf:info
              "WORD;;Enter IP address (A.B.C.D)";
          }
        }
        container next-address-loose {
          tailf:cli-drop-node-name;
          container next-address {
            tailf:info
              "Specify the next address in the path";
            tailf:cli-incomplete-no;
            tailf:cli-incomplete-command;
            leaf loose {
              tailf:info
                "Target address is loose";
              tailf:cli-no-name-on-delete;
              tailf:cli-no-value-on-delete;
              type inet:ipv4-address {
                tailf:info
                  "WORD;;Enter IP address (A.B.C.D)";
              }
            }
          }
        }
        leaf exclude-address {
          tailf:info
            "Exclude an address from subsequent partial path segments";
          tailf:cli-no-name-on-delete;
          tailf:cli-no-value-on-delete;
          type inet:ipv4-address {
            tailf:info
              "WORD;;Enter IP address (A.B.C.D)";
          }
        }
      }
    }
  }

  grouping radius-server-grouping {
    leaf auth-port {
      tailf:info
        "UDP port for RADIUS authentication server (default is 1645)";
      type uint16 {
        tailf:info
          "<0-65535>;;Port number";
        range "0..65535";
      }
    }
    leaf acct-port {
      tailf:info
        "UDP port for RADIUS accounting server (default is 1646)";
      type uint16 {
        tailf:info
          "<0-65535>;;Port number";
        range "0..65535";
      }
    }
    leaf timeout {
      tailf:info
        "Time to wait for this RADIUS server to reply (overrides default)";
      type uint16 {
        tailf:info
          "<1-1000>;;Timeout value in seconds to wait for server to reply";
        range "1..1000";
      }
    }
    leaf retransmit {
      tailf:info
        "Specify the number of retries to active server (overrides default)";
      type uint8 {
        tailf:info
          "<0-100>;;Number of retries to this server for a transaction";
        range "0..100";
      }
    }
    container test {
      tailf:info
        "Configure server automated testing.";
      tailf:cli-flatten-container;
      leaf username {
        tailf:info
          "A name (from local database) that should be used to send requests.";
        type string {
          tailf:info
            "WORD;;User Name";
        }
      }
    }
    container key {
      tailf:info
        "per-server encryption key (overrides default)";
      tailf:cli-flatten-container;
      tailf:cli-compact-syntax;
      uses password-grouping;
    }
  }

  grouping domain-advanced-smart-probes-grouping {
    container smart-probes {
      tailf:info
        "Smart probes configuration";
      container burst {
        tailf:info
          "Specify smart probe burst profile for channels monitored by general monitor";
        container burst {
          tailf:cli-drop-node-name;
          tailf:cli-compact-syntax;
          tailf:cli-sequence-commands;
          leaf number {
            tailf:cli-drop-node-name;
            tailf:cli-incomplete-command;
            type uint8 {
              tailf:info
                "<1-100>;;Specify number of packets in one burst";
              range "1..100";
            }
          }
          leaf packets {
            tailf:info
              "packet(s) in every burst";
            tailf:cli-incomplete-command;
            type empty;
          }
          leaf every {
            tailf:info
              "every burst interval";
            tailf:cli-incomplete-command;
            type empty;
          }
          leaf interval {
            tailf:cli-drop-node-name;
            tailf:cli-incomplete-command;
            type uint8 {
              tailf:info
                "<1-30>;;Specify the interval between the starts of two adjacent bursts";
              range "1..30";
            }
          }
          leaf seconds {
            tailf:info
              "interval length in the scale of seconds";
            type empty;
          }
        }
        container quick {
          tailf:info
            "Specify smart probe burst profile for channels monitored by quick monitor";
          tailf:cli-compact-syntax;
          tailf:cli-sequence-commands;
          leaf number {
            tailf:cli-drop-node-name;
            tailf:cli-incomplete-command;
            type uint8 {
              tailf:info
                "<1-100>;;Specify number of packets in one burst";
              range "1..100";
            }
          }
          leaf packets {
            tailf:info
              "packet(s) in every burst";
            tailf:cli-incomplete-command;
            type empty;
          }
          leaf every {
            tailf:info
              "every burst interval";
            tailf:cli-incomplete-command;
            type empty;
          }
          leaf interval {
            tailf:cli-drop-node-name;
            tailf:cli-incomplete-command;
            type uint8 {
              tailf:info
                "<1-30>;;Specify the interval between the starts of two adjacent bursts";
              range "1..30";
            }
          }
          leaf seconds {
            tailf:info
              "interval length in the scale of seconds";
            type empty;
          }
        }
      }
    }
  }

  grouping domain-master-grouping {
    list master {
      tailf:info
        "Enter master controller configuration submode";
      tailf:cli-mode-name "config-domain-vrf-mc";
      tailf:cli-sequence-commands;
      max-elements 1;
      key "type";
      leaf type {
        type enumeration {
          enum "branch" {
            tailf:info
              "Set master type as branch hub";
          }
          enum "hub" {
            tailf:info
              "Set master type as a hub";
          }
          enum "regional-hub" {
            tailf:info
              "Set master type as a regional hub";
          }
          enum "transit" {
            tailf:info
              "Set master type as a transit hub";
          }
        }
      }
      leaf pop-id {
        when "../type = 'transit'" {
          tailf:xpath-root 3;
          tailf:dependency "../type";
        }
        tailf:cli-drop-node-name;
        tailf:cli-hide-in-submode;
        tailf:cli-full-command;
        type uint8 {
          tailf:info
            "<1-62>;;Pop ID";
          range "1..62";
        }
      }
      container source-interface {
        tailf:info
          "Source Interface for master controller";
        tailf:cli-break-sequence-commands;
        uses interface-name-grouping;
      }
      container site-prefixes {
        tailf:info
          "site prefixes configuration";
        leaf prefix-list {
          tailf:info
            "Specify prefix-list with static site prefixes";
          type string {
            tailf:info
              "WORD;;prefix-list containing list of site prefixes";
          }
        }
      }
      leaf hub {
        tailf:info
          "Specify regional-hub master controller to peer with";
        tailf:cli-remove-before-change;
        tailf:cli-full-command;
        type inet:ipv4-address {
          tailf:info
            "A.B.C.D;;IP address of regional-hub master controller";
        }
      }
      container collector {
        tailf:info
          "NMS/v9 collector configuration";
        tailf:cli-compact-syntax;
        tailf:cli-sequence-commands {
          tailf:cli-reset-siblings;
        }
        leaf ip-address {
          tailf:cli-drop-node-name;
          type inet:ipv4-address {
            tailf:info
              "A.B.C.D;;IP address of NMS/v9 collector";
          }
        }
        leaf port {
          tailf:info
            "Specify collector port number";
          type uint16 {
            tailf:info
              "<1-65535>;;Specify collector port number";
            range "1..65535";
          }
        }
      }
      container load-balance {
        tailf:info
          "load balance non-policy traffic";
        tailf:cli-add-mode;
        tailf:cli-mode-name "config-domain-vrf-mc-load-balance";
        leaf option {
          tailf:cli-drop-node-name;
          tailf:cli-hide-in-submode;
          type enumeration {
            enum "advanced" {
              tailf:info
                "Load balancing configuration mode";
            }
          }
          default "advanced";
        }
        uses domain-path-preference-grouping;
      }
      container password {
        tailf:info
          "MD5 password to be used with BRs";
        tailf:cli-compact-syntax;
        tailf:cli-sequence-commands;
        uses password-grouping;
      }
      container enterprise-prefix {
        tailf:info
          "Enterprise prefix configuration";
        leaf prefix-list {
          tailf:info
            "Specify prefix-list with static site targets";
          type string {
            tailf:info
              "WORD;;prefix-list containing list of site targets";
          }
        }
      }
      list monitor-interval {
        tailf:info
          "Monitoring interval";
        tailf:cli-suppress-mode;
        tailf:cli-delete-when-empty;
        key "seconds dscp";
        leaf seconds {
          type uint16 {
            tailf:info
              "<1-300>;;interval (second)";
          }
        }
        leaf dscp {
          tailf:info
            "specify DSCP";
          tailf:cli-expose-key-name;
          type dscp-type;
        }
      }
      container advanced {
        tailf:info
          "Advanced configuration submode";
        tailf:cli-add-mode;
        tailf:cli-mode-name "config-domain-vrf-mc-advanced";
        presence "true";
        uses domain-advanced-smart-probes-grouping;
        leaf channel-unreachable-timer {
          tailf:info
            "Unreach interval detection";
          tailf:cli-full-command;
          type uint16 {
            tailf:info
              "<1-65535>;;Specify new timer interval value in seconds";
            range "1..65535";
          }
        }
      }
      list class {
        tailf:info
          "Create domain class and enter domain class command mode";
        tailf:cli-mode-name "config-domain-vrf-mc-class";
        tailf:cli-sequence-commands;
        tailf:cli-incomplete-command;
        key "name";
        leaf name {
          type string {
            tailf:info
              "WORD;;domain class name";
          }
        }
        leaf sequence {
          tailf:info
            "Set the Sequence for the class";
          tailf:cli-hide-in-submode;
          type uint16 {
            tailf:info
              "<1-65535>;;Sequence number for the class";
            range "1..65535";
          }
        }
        container match {
          tailf:info
            "Specify the applications the policy applies to.";
          tailf:cli-break-sequence-commands;
          list dscp {
            tailf:info
              "specify DSCP";
            tailf:cli-suppress-mode;
            tailf:cli-delete-when-empty;
            tailf:cli-incomplete-command;
            key "services-value";
            leaf services-value {
              type dscp-type;
            }
            leaf policy {
              tailf:info
                "Specify the policy (user defined/predefined)";
              type enumeration {
                enum "best-effort" {
                  tailf:info
                    "domain policy type best effort";
                }
                enum "bulk-data" {
                  tailf:info
                    "domain policy type bulk data";
                }
                enum "custom" {
                  tailf:info
                    "custom user-defined policy";
                }
                enum "low-latency-data" {
                  tailf:info
                    "domain policy type low latency data";
                }
                enum "real-time-video" {
                  tailf:info
                    "domain policy type real-time-video";
                }
                enum "scavenger" {
                  tailf:info
                    "domain policy type scavenger";
                }
                enum "voice" {
                  tailf:info
                    "domain policy type voice";
                }
              }
            }
          }
          list application {
            tailf:info
              "Specify the application names";
            tailf:cli-suppress-mode;
            tailf:cli-delete-when-empty;
            tailf:cli-incomplete-command;
            key "services-value";
            leaf services-value {
              type string {
                tailf:info
                  "WORD;;user-defined application name";
              }
            }
            leaf policy {
              tailf:info
                "Specify the policy (user defined/predefined)";
              type enumeration {
                enum "best-effort" {
                  tailf:info
                    "domain policy type best effort";
                }
                enum "bulk-data" {
                  tailf:info
                    "domain policy type bulk data";
                }
                enum "custom" {
                  tailf:info
                    "custom user-defined policy";
                }
                enum "low-latency-data" {
                  tailf:info
                    "domain policy type low latency data";
                }
                enum "real-time-video" {
                  tailf:info
                    "domain policy type real-time-video";
                }
                enum "scavenger" {
                  tailf:info
                    "domain policy type scavenger";
                }
                enum "voice" {
                  tailf:info
                    "domain policy type voice";
                }
              }
            }
          }
        }
        uses domain-path-preference-grouping;
        leaf path-last-resort {
          tailf:info
            "Specify path of last resort provider";
          type string {
            tailf:info
              "Specify path of last resort provider";
          }
        }
      }
    }
  }

  grouping domain-border-grouping {
    container border {
      tailf:info
        "Enter border router configuration submode";
      tailf:cli-add-mode;
      tailf:cli-mode-name "config-domain-vrf-br";
      tailf:cli-full-command;
      presence "true";
      leaf master {
        tailf:info
          "Specify IP address of Domain master controller";
        tailf:cli-remove-before-change;
        tailf:cli-full-command;
        type union {
          type inet:ipv4-address {
            tailf:info
              "A.B.C.D;;IP address of Domain master controller";
          }
          type enumeration {
            enum "local" {
              tailf:info
                "local;;Local Domain master controller";
            }
          }
        }
      }
      container source-interface {
        tailf:info
          "Source Interface for border";
        uses interface-name-grouping;
      }
      container password {
        tailf:info
          "MD5 password to be used with MC";
        tailf:cli-compact-syntax;
        tailf:cli-sequence-commands;
        uses password-grouping;
      }
    }
  }

  grouping carrier-delay-grouping {
    choice delay-choice {
      leaf seconds {
        tailf:cli-drop-node-name;
        type uint8 {
          tailf:info
            "<0-60>;;Carrier Transitions delay seconds";
          range "0..60";
        }
      }
      leaf msec {
        tailf:info
          "delay specified in milliseconds";
        type uint16 {
          tailf:info
            "<0-1000>;;Carrier Transitions delay milliseconds";
          range "0..1000";
        }
      }
    }
  }

  augment "/ncs:devices/ncs:device/ncs:config" {
    container upgrade {
      tailf:ncs-device-type "cli-ned";
      tailf:display-when "not(../../ncs:module) or ../../ncs:module[ncs:name='tailf-ned-cisco-ios']";
      tailf:info
        "Global upgrade configuration subcommands";
      container fpd {
        tailf:info
          "Configure field programmable devices upgrade options";
        leaf auto {
          tailf:info
            "Auto upgrade all FPD images";
          type empty;
        }
        leaf path {
          tailf:info
            "Set path to locate the FPD image package file for auto upgrade";
          type string;
        }
      }
    }
    container tailfned {
      tailf:ncs-device-type "cli-ned";
      tailf:display-when "not(../../ncs:module) or ../../ncs:module[ncs:name='tailf-ned-cisco-ios']";
      leaf police {
        tailf:cli-no-value-on-delete;
        tailf:cli-suppress-no;
        type string {
          tailf:info
            "cirmode | bpsflat | numflat | cirflat";
        }
      }
      container api {
        tailf:info
          "DO NOT MODIFY, contents here are set by ned-settings only";
        leaf new-ip-access-list {
          tailf:info
            "DO NOT MODIFY, this leaf is set by ned-settings only";
          type empty;
        }
      }
    }
    leaf version {
      tailf:ncs-device-type "cli-ned";
      tailf:display-when "not(../../ncs:module) or ../../ncs:module[ncs:name='tailf-ned-cisco-ios']";
      tailf:info
        "Version";
      type string {
        tailf:info
          "WORD;;Version number";
      }
    }
    container service {
      tailf:ncs-device-type "cli-ned";
      tailf:display-when "not(../../ncs:module) or ../../ncs:module[ncs:name='tailf-ned-cisco-ios']";
      tailf:info
        "Modify use of network based services";
      leaf config {
        tailf:info
          "TFTP load config files";
        tailf:cli-full-command;
        type empty;
      }
      leaf exec-callback {
        tailf:info
          "Enable exec callback";
        tailf:cli-full-command;
        type empty;
      }
      leaf nagle {
        tailf:info
          "Enable Nagle's congestion control algorithm";
        tailf:cli-full-command;
        type empty;
      }
      leaf slave-log {
        tailf:info
          "Enable log capability of slave IPs";
        tailf:cli-boolean-no;
        tailf:cli-full-command;
        type boolean;
        default "true";
      }
      container pad {
        tailf:info
          "Enable PAD commands";
        tailf:cli-incomplete-no;
        tailf:cli-incomplete-command;
        leaf to-xot {
          tailf:info
            "Allow outgoing PAD over XOT connections";
          tailf:cli-full-command;
          type empty;
        }
        leaf from-xot {
          tailf:info
            "Accept XOT to PAD connections";
          tailf:cli-full-command;
          type empty;
        }
        leaf cmns {
          tailf:info
            "Enable PAD over CMNS connections";
          tailf:cli-full-command;
          type empty;
        }
      }
      container conf {
        tailf:cli-drop-node-name;
        leaf pad {
          tailf:cli-boolean-no;
          tailf:cli-full-command;
          type boolean;
          default "true";
        }
      }
      leaf tcp-keepalives-in {
        tailf:info
          "Generate keepalives on idle incoming network connections";
        tailf:cli-full-command;
        type empty;
      }
      leaf tcp-keepalives-out {
        tailf:info
          "Generate keepalives on idle outgoing network connections";
        tailf:cli-full-command;
        type empty;
      }
      container timestamps {
        tailf:info
          "Timestamp debug/log messages";
        tailf:cli-compact-syntax;
        tailf:cli-delete-when-empty;
        presence "true";
        container debug {
          tailf:info
            "Timestamp debug messages";
          choice timestamp-choice {
            leaf uptime {
              tailf:info
                "Timestamp with system uptime";
              type empty;
            }
            container datetime {
              tailf:info
                "Timestamp with date and time";
              tailf:cli-compact-syntax;
              tailf:cli-delete-when-empty;
              presence "true";
              leaf msec {
                tailf:info
                  "Include milliseconds in timestamp";
                type empty;
              }
              leaf localtime {
                tailf:info
                  "Use local time zone for timestamps";
                type empty;
              }
              leaf show-timezone {
                tailf:info
                  "Add time zone information to timestamp";
                type empty;
              }
              leaf year {
                tailf:info
                  "Include year in timestamp";
                type empty;
              }
            }
          }
        }
        container log {
          tailf:info
            "Timestamp log messages";
          choice timestamp-choice {
            leaf uptime {
              tailf:info
                "Timestamp with system uptime";
              type empty;
            }
            container datetime {
              tailf:info
                "Timestamp with date and time";
              tailf:cli-compact-syntax;
              tailf:cli-delete-when-empty;
              presence "true";
              leaf msec {
                tailf:info
                  "Include milliseconds in timestamp";
                type empty;
              }
              leaf localtime {
                tailf:info
                  "Use local time zone for timestamps";
                type empty;
              }
              leaf show-timezone {
                tailf:info
                  "Add time zone information to timestamp";
                type empty;
              }
              leaf year {
                tailf:info
                  "Include year in timestamp";
                type empty;
              }
            }
          }
        }
      }
      container password-encryption {
        tailf:info
          "Encrypt system passwords";
        tailf:cli-show-no;
        presence "true";
      }
      leaf password-recovery {
        tailf:info
          "Disable password recovery";
        tailf:cli-boolean-no;
        tailf:cli-full-command;
        type boolean;
      }
      leaf exec-wait {
        tailf:info
          "Delay EXEC startup on noisy lines";
        tailf:cli-full-command;
        type empty;
      }
      leaf linenumber {
        tailf:info
          "enable line number banner for each exec";
        tailf:cli-full-command;
        type empty;
      }
      leaf compress-config {
        tailf:info
          "Compress the configuration file";
        tailf:cli-full-command;
        type empty;
      }
      leaf udp-small-servers {
        tailf:info
          "Enable small UDP servers (e.g., ECHO)";
        tailf:cli-full-command;
        type empty;
      }
      container prompt {
        tailf:info
          "Enable mode specific prompt (WARNING: will deadlock NED) if set to 'no'";
        leaf config {
          tailf:info
            "Enable configuration mode prompt";
          tailf:cli-boolean-no;
          type boolean;
          default "true";
        }
      }
      leaf tcp-small-servers {
        tailf:info
          "Enable small TCP servers (e.g., ECHO)";
        tailf:cli-full-command;
        type empty;
      }
      leaf old-slip-prompts {
        tailf:info
          "Allow old scripts to operate with slip/ppp";
        tailf:cli-full-command;
        type empty;
      }
      leaf pt-vty-logging {
        tailf:info
          "Log significant VTY-Async events";
        tailf:cli-full-command;
        type empty;
      }
      leaf disable-ip-fast-frag {
        tailf:info
          "Disable IP particle-based fast fragmentation";
        tailf:cli-full-command;
        type empty;
      }
      leaf sequence-numbers {
        tailf:info
          "Stamp logger messages with a sequence number";
        tailf:cli-full-command;
        type empty;
      }
      container divert-rate-limit {
        tailf:info
          "Set WAN-side divert-rate-limit parameters";
        list ip {
          tailf:info
            "WAN-IPv4 configuration";
          tailf:cli-suppress-mode;
          tailf:cli-delete-when-empty;
          tailf:cli-compact-syntax;
          tailf:cli-sequence-commands;
          tailf:cli-incomplete-command;
          key "divert-code";
          leaf divert-code {
            type string {
              tailf:info
                "WORD;;divert code";
            }
          }
          leaf rate {
            tailf:info
              "rate in packets/sec";
            tailf:cli-incomplete-command;
            type uint16 {
              tailf:info
                "<1-65535>;;rate in packets/second";
            }
          }
          leaf limit {
            tailf:info
              "limit in packets";
            type uint16 {
              tailf:info
                "<4-4194>;;limit in packets";
              range "4..4194";
            }
          }
        }
        list ipv6 {
          tailf:info
            "WAN-IPv6 configuration";
          tailf:cli-suppress-mode;
          tailf:cli-delete-when-empty;
          tailf:cli-compact-syntax;
          tailf:cli-sequence-commands;
          tailf:cli-incomplete-command;
          key "divert-code";
          leaf divert-code {
            type string {
              tailf:info
                "WORD;;divert code";
            }
          }
          leaf rate {
            tailf:info
              "rate in packets/sec";
            tailf:cli-incomplete-command;
            type uint16 {
              tailf:info
                "<1-65535>;;rate in packets/second";
            }
          }
          leaf limit {
            tailf:info
              "limit in packets";
            type uint16 {
              tailf:info
                "<4-4194>;;limit in packets";
              range "4..4194";
            }
          }
        }
        list trusted-site {
          tailf:info
            "trusted-site configuration for WAN-IPv4";
          tailf:cli-suppress-mode;
          tailf:cli-delete-when-empty;
          key "ip-address mask-ip-address tos mask";
          max-elements 4;
          leaf ip-address {
            type inet:ipv4-address {
              tailf:info
                "A.B.C.D;;source IP address";
            }
          }
          leaf mask-ip-address {
            type inet:ipv4-address {
              tailf:info
                "A.B.C.D;;IP prefix mask";
            }
          }
          leaf tos {
            tailf:info
              "ToS value";
            tailf:cli-expose-key-name;
            type string {
              tailf:info
                "<0-255>;;ToS value";
            }
          }
          leaf mask {
            tailf:info
              "ToS mask";
            tailf:cli-expose-key-name;
            type string {
              tailf:info
                "<0-255>;;ToS mask";
            }
          }
        }
        list trusted-site-ipv6 {
          tailf:info
            "trusted-site configuration for WAN-IPv6";
          tailf:cli-suppress-mode;
          tailf:cli-delete-when-empty;
          key "ip-address traffic-class mask";
          max-elements 4;
          leaf ip-address {
            type ios:ipv6-prefix {
              tailf:info
                "X:X:X:X::X/<0-128>;;IPv6 Source address/Prefix length.(e.g., 1234::1/<prefix-length>)";
            }
          }
          leaf traffic-class {
            tailf:info
              "traffic-class value";
            tailf:cli-expose-key-name;
            type string {
              tailf:info
                "<0-255>;;traffic-class value";
            }
          }
          leaf mask {
            tailf:info
              "traffic-class mask";
            tailf:cli-expose-key-name;
            type string {
              tailf:info
                "<0-255>;;traffic-class mask";
            }
          }
        }
      }
      container counters {
        tailf:info
          "Control aging of interface counters";
        container max {
          tailf:info
            "Maximum counter aging threshold";
          leaf age {
            tailf:info
              "Aging threshold";
            type uint8 {
              tailf:info
                "<0-60>;;Aging threshold value in seconds";
              range "0..60";
            }
          }
        }
      }
      container alignment {
        tailf:info
          "Control alignment correction and logging";
        leaf detection {
          tailf:info
            "Enable detection of alignment issues";
          tailf:cli-boolean-no;
          tailf:cli-full-command;
          type boolean;
          default "true";
        }
        leaf logging {
          tailf:info
            "Enable logging of alignment issues";
          tailf:cli-boolean-no;
          tailf:cli-full-command;
          type boolean;
          default "true";
        }
      }
      leaf call-home {
        tailf:info
          "Enable call-home service";
        tailf:cli-full-command;
        type empty;
      }
      leaf dhcp {
        tailf:info
          "Enable DHCP server and relay agent";
        tailf:cli-boolean-no;
        tailf:cli-full-command;
        type boolean;
        default "true";
      }
      leaf finger {
        tailf:info
          "Allow responses to finger requests";
        tailf:cli-full-command;
        type empty;
      }
      container heartbeat {
        tailf:info
          "Enable heartbeat processing";
        leaf fatal-count {
          tailf:info
            "Set heartbeat fatal count";
          type uint8 {
            tailf:info
              "<1-60>;;Number of timeouts until fatal error occurs";
            range "1..60";
          }
        }
        leaf interrupt-interval {
          tailf:info
            "Set heartbeat interrupt test interval";
          type uint8 {
            tailf:info
              "<0-60>;;Interval between interrupt level tests";
            range "0..60";
          }
        }
        leaf interrupt-max {
          tailf:info
            "Set maximum message count from interrupt test";
          type uint8 {
            tailf:info
              "<0-60>;;Maximum number of messages from interrupt test";
            range "0..60";
          }
        }
        leaf transmit-interval {
          tailf:info
            "Set heartbeat transmit interval";
          type uint8 {
            tailf:info
              "<1-30>;;Interval between heartbeat transmissions";
            range "1..30";
          }
        }
        leaf warning-timeout {
          tailf:info
            "Set heartbeat warning timeout interval";
          type uint8 {
            tailf:info
              "<3-60>;;Interval between heartbeat timeout warnings";
            range "3..60";
          }
        }
        leaf fatal-timeout {
          tailf:info
            "Set heartbeat warning timeout interval";
          type uint8 {
            tailf:info
              "<5-60>;;Interval between heartbeat timeouts until a fatal timeout error occurs";
            range "5..60";
          }
        }
        leaf cslipc-timeout {
          tailf:info
            "Set heartbeat csl ipc timeout interval";
          type uint16 {
            tailf:info
              "<10-4800>;;Interval between linecard insertion and csl ipc reception";
            range "10..4800";
          }
        }
        leaf alive-timeout {
          tailf:info
            "Set heartbeat alive timeout interval";
          type uint16 {
            tailf:info
              "<600-1200>;;Interval between linecard insertion and heartbeat starting";
            range "600..1200";
          }
        }
      }
      leaf hide-telnet-addresses {
        tailf:info
          "Hide destination addresses in telnet command";
        tailf:cli-full-command;
        type empty;
      }
      leaf unsupported-transceiver {
        tailf:cli-full-command;
        type empty;
      }
      leaf internal {
        type empty;
      }
    }
    container boot {
      tailf:ncs-device-type "cli-ned";
      tailf:display-when "not(../../ncs:module) or ../../ncs:module[ncs:name='tailf-ned-cisco-ios']";
      tailf:info
        "Modify system boot parameters";
      leaf config {
        tailf:info
          "Configuration file";
        tailf:cli-full-command;
        type string {
          tailf:info
            "WORD;;URL of the config file";
        }
      }
      container network {
        tailf:info
          "Network-wide config file";
        leaf remote-url {
          tailf:cli-drop-node-name;
          type string {
            tailf:info
              "WORD;;TFTP filename or URL";
          }
        }
      }
    }
    container password {
      tailf:ncs-device-type "cli-ned";
      tailf:display-when "not(../../ncs:module) or ../../ncs:module[ncs:name='tailf-ned-cisco-ios']";
      tailf:info
        "Configure encryption password (key)";
      container encryption {
        tailf:info
          "Encrypt system passwords";
        leaf aes {
          tailf:info
            "Enable stronger (AES) password encryption";
          type empty;
        }
      }
    }
    container login {
      tailf:ncs-device-type "cli-ned";
      tailf:display-when "not(../../ncs:module) or ../../ncs:module[ncs:name='tailf-ned-cisco-ios']";
      tailf:info
        "Enable secure login checking";
      container block-for {
        tailf:info
          "Set quiet-mode active time period";
        tailf:cli-compact-syntax;
        tailf:cli-sequence-commands {
          tailf:cli-reset-siblings;
        }
        leaf seconds {
          tailf:cli-drop-node-name;
          tailf:cli-incomplete-command;
          type uint16 {
            tailf:info
              "<1-65535>;;Time period in seconds";
            range "1..65535";
          }
        }
        leaf attempts {
          tailf:info
            "Set max number of fail attempts";
          tailf:cli-incomplete-command;
          type uint16 {
            tailf:info
              "<1-65535>;;Fail attempts max value";
            range "1..65535";
          }
        }
        leaf within {
          tailf:info
            "Watch period for fail attempts";
          type uint16 {
            tailf:info
              "<1-65535>;;Time period in seconds";
            range "1..65535";
          }
        }
      }
      container on-failure {
        tailf:info
          "Set options for failed login attempt";
        tailf:cli-compact-syntax;
        tailf:cli-sequence-commands {
          tailf:cli-reset-siblings;
        }
        leaf log {
          tailf:info
            "Generate syslogs on failure logins";
          type empty;
        }
        leaf every {
          tailf:info
            "Periodicity for logs generated";
          type uint16 {
            tailf:info
              "<1-65535>;;Number defining periodicity";
            range "1..65535";
          }
          default "1";
        }
      }
      container on-success {
        tailf:info
          "Set options for successful login attempt";
        tailf:cli-compact-syntax;
        tailf:cli-sequence-commands {
          tailf:cli-reset-siblings;
        }
        leaf log {
          tailf:info
            "Generate syslogs on successful logins";
          type empty;
        }
        leaf every {
          tailf:info
            "Periodicity for logs generated";
          type uint16 {
            tailf:info
              "<1-65535>;;Number defining periodicity";
            range "1..65535";
          }
          default "1";
        }
      }
    }
    container cdp {
      tailf:ncs-device-type "cli-ned";
      tailf:display-when "not(../../ncs:module) or ../../ncs:module[ncs:name='tailf-ned-cisco-ios']";
      tailf:info
        "Global CDP configuration subcommands";
      leaf run {
        tailf:info
          "Enable CDP";
        tailf:cli-boolean-no;
        tailf:cli-full-command;
        type boolean;
        default "true";
      }
      leaf advertise-v2 {
        tailf:info
          "CDP sends version-2 advertisements";
        tailf:cli-boolean-no;
        type boolean;
        default "true";
      }
      container tlv {
        tailf:info
          "Enable exchange of specific tlv information";
        leaf location {
          tailf:cli-boolean-no;
          tailf:cli-full-command;
          type boolean;
          default "true";
        }
        leaf app {
          tailf:info
            "Enable app tlv";
          tailf:cli-boolean-no;
          tailf:cli-full-command;
          type boolean;
          default "true";
        }
      }
    }
    container platform {
      tailf:ncs-device-type "cli-ned";
      tailf:display-when "not(../../ncs:module) or ../../ncs:module[ncs:name='tailf-ned-cisco-ios']";
      tailf:info
        "platform specific configuration";
      leaf shell {
        tailf:info
          "Control platform shell access command availability";
        tailf:cli-full-command;
        type empty;
      }
      leaf console {
        tailf:info
          "Direct IOS output to console";
        tailf:cli-full-command;
        type enumeration {
          enum "auto" {
            tailf:info
              "Autodetect console (Serial,VGA) for IOS output";
          }
          enum "serial" {
            tailf:info
              "Use Serial console for IOS output";
          }
          enum "virtual" {
            tailf:info
              "Use VM (VGA) console for IOS output";
          }
        }
      }
      container bfd {
        tailf:info
          "Platform specific BFD commands";
        leaf allow-svi {
          tailf:cli-full-command;
          type empty;
        }
      }
      leaf bfd-debug-trace {
        tailf:cli-full-command;
        type uint32;
      }
      container enable {
        list controller {
          tailf:cli-suppress-mode;
          tailf:cli-delete-when-empty;
          key "name";
          leaf name {
            tailf:cli-multi-word-key;
            type string {
              tailf:info
                "WORD;;Controller name";
            }
          }
        }
      }
      container hardware {
        tailf:info
          "Configure platform hardware";
        container throughput {
          tailf:info
            "Configure throughput";
          container level {
            tailf:info
              "Configure the current traffic throughput level";
            choice throughput-choice {
              leaf MB {
                tailf:info
                  "throughput in mbps";
                type uint32;
              }
              leaf kbps {
                tailf:cli-drop-node-name;
                type uint32;
              }
            }
          }
        }
      }
      container ipccl {
        leaf log-history {
          type uint32;
        }
      }
      container ipv4 {
        container pbr {
          container optimize {
            leaf tcam {
              type empty;
            }
          }
        }
      }
      container ring {
        leaf rx {
          type uint32;
        }
      }
      container tcam-parity-error {
        leaf enable {
          type empty;
        }
      }
      container tcam-threshold {
        leaf alarm-frequency {
          type uint32;
        }
      }
      container multicast {
        tailf:info
          "Configure multicast";
        container lre {
          leaf off {
            type empty;
          }
        }
      }
      container punt-keepalive {
        tailf:info
          "punt-keepalive messages";
        leaf disable-kernel-core {
          tailf:info
            "Disable IOSXE kernel core generation for keepalive fault";
          tailf:cli-boolean-no;
          type boolean;
        }
      }
      list punt-policer {
        tailf:info
          "Configures punt policers";
        tailf:cli-suppress-mode;
        tailf:cli-delete-when-empty;
        tailf:cli-incomplete-command;
        key "cause";
        leaf cause {
          type uint8 {
            tailf:info
              "<1-108>;;Punt cause to be policed";
            range "1..108";
          }
        }
        leaf rate {
          tailf:cli-drop-node-name;
          type uint32 {
            tailf:info
              "<10-146484>;;max punt rate for cause Incomplete adjacency";
            range "10..146484";
          }
        }
      }
      container punt-policer-high {
        tailf:cli-drop-node-name;
        list punt-policer {
          tailf:info
            "Configures punt policers";
          tailf:cli-suppress-mode;
          tailf:cli-delete-when-empty;
          tailf:cli-compact-syntax;
          tailf:cli-incomplete-command;
          key "cause";
          leaf cause {
            type uint8 {
              tailf:info
                "<1-108>;;Punt cause to be policed";
              range "1..108";
            }
          }
          leaf rate {
            tailf:cli-drop-node-name;
            tailf:cli-incomplete-command;
            type uint32 {
              tailf:info
                "<10-146484>;;max punt rate for cause Incomplete adjacency";
              range "10..146484";
            }
          }
          leaf high {
            tailf:info
              "High priority traffic only";
            type empty;
          }
        }
      }
      container punt-sbrl {
        tailf:info
          "Punt-path Source-Based Rate-Limit configuration";
        container wan {
          tailf:info
            "SBRL WAN-side config";
          list punt-cause {
            tailf:info
              "sub-side punt-cause for per-MAC-addr rate-limiting";
            tailf:cli-suppress-mode;
            tailf:cli-delete-when-empty;
            tailf:cli-compact-syntax;
            tailf:cli-sequence-commands {
              tailf:cli-reset-siblings;
            }
            tailf:cli-incomplete-command;
            key "cause";
            leaf cause {
              type uint8 {
                tailf:info
                  "<1-108>;;Punt cause to be policed";
                range "1..108";
              }
            }
            leaf rate {
              tailf:info
                "WAN-side rate in pkts-per-sec";
              type uint16 {
                tailf:info
                  "<1-256>;;rate in pkts/sec (powers-of-2 only) for: MPLS ICMP Can't Fragment";
                range "1..256";
              }
            }
            leaf quarantine-time {
              tailf:info
                "WAN-side quarantine time";
              tailf:cli-incomplete-command;
              type uint8 {
                tailf:info
                  "<1-60>;;quarantine time in minutes";
                range "1..60";
              }
            }
            leaf burst-factor {
              tailf:info
                "WAN-side quarantine burst-factor";
              type uint16 {
                tailf:info
                  "<50-1000>;;quarantine burst-factor in packets";
                range "50..1000";
              }
            }
          }
        }
        container subscriber {
          tailf:info
            "SBRL subscriber-side config";
          leaf rate {
            tailf:info
              "subscriber-side CM rate in pkts-per-sec";
            type uint16 {
              tailf:info
                "<1-256>;;rate (powers-of-2 only)";
              range "1..256";
            }
          }
        }
      }
      container qos {
        tailf:info
          "Platform specific qos configuration";
        leaf marker-statistics {
          tailf:info
            "Configure marking statistics";
          tailf:cli-full-command;
          type empty;
        }
        container match-statistics {
          tailf:info
            "Configure match stats";
          leaf per-filter {
            tailf:info
              "Configure per-filter match statistics";
            type empty;
          }
          leaf per-ace {
            tailf:info
              "Configure per-ace match statistics(per-filter must be enabled first)";
            tailf:cli-diff-dependency "../per-filter" {
              tailf:xpath-root 3;
            }
            type empty;
          }
        }
        leaf performance-monitor {
          tailf:info
            "Configure performance-monitor statistics";
          tailf:cli-full-command;
          type empty;
        }
        leaf punt-path-matching {
          tailf:info
            "Configure punt-path matching on input interface (PPPoE-Discovery, PPPoE-PPP-LCP)";
          tailf:cli-full-command;
          type empty;
        }
      }
      container power {
        container redundancy-mode {
          leaf nplus1 {
            type empty;
          }
        }
      }
    }
    leaf hostname {
      tailf:ncs-device-type "cli-ned";
      tailf:display-when "not(../../ncs:module) or ../../ncs:module[ncs:name='tailf-ned-cisco-ios']";
      tailf:info
        "Set system's network name";
      type string {
        tailf:info
          "This system's network name";
      }
    }
    container boot-marker {
      tailf:ncs-device-type "cli-ned";
      tailf:display-when "not(../../ncs:module) or ../../ncs:module[ncs:name='tailf-ned-cisco-ios']";
      tailf:cli-drop-node-name;
      container boot {
        tailf:info
          "Modify system boot parameters";
        list system {
          tailf:info
            "System image file";
          tailf:cli-suppress-mode;
          tailf:cli-delete-when-empty;
          key "entry";
          leaf entry {
            tailf:cli-multi-word-key;
            type string {
              tailf:info
                "WORD;;boot system entry";
            }
          }
        }
      }
    }
    container shell {
      tailf:ncs-device-type "cli-ned";
      tailf:display-when "not(../../ncs:module) or ../../ncs:module[ncs:name='tailf-ned-cisco-ios']";
      tailf:info
        "Configure shell command";
      leaf processing {
        tailf:cli-boolean-no;
        tailf:cli-full-command;
        type boolean;
        default "true";
      }
    }
    container aqm-register-fnf {
      tailf:ncs-device-type "cli-ned";
      tailf:display-when "not(../../ncs:module) or ../../ncs:module[ncs:name='tailf-ned-cisco-ios']";
      tailf:info
        "Export audio/voice stats to flow record";
      presence "true";
    }
    container service-module {
      tailf:ncs-device-type "cli-ned";
      tailf:display-when "not(../../ncs:module) or ../../ncs:module[ncs:name='tailf-ned-cisco-ios']";
      tailf:info
        "Service Module bootimage config";
      list wlan-ap {
        tailf:cli-suppress-mode;
        tailf:cli-delete-when-empty;
        tailf:cli-compact-syntax;
        tailf:cli-sequence-commands {
          tailf:cli-reset-siblings;
        }
        tailf:cli-incomplete-command;
        key "interface-number";
        leaf interface-number {
          type uint8 {
            tailf:info
              "<0-0>;;wlan-ap interface number";
            range "0";
          }
        }
        leaf bootimage {
          tailf:info
            "AP boot image";
          type enumeration {
            enum "autonomous" {
              tailf:info
                "Set AP boot image to autonomous";
            }
            enum "unified" {
              tailf:info
                "Set AP boot image to unified";
            }
          }
        }
      }
    }
    container vrf {
      tailf:ncs-device-type "cli-ned";
      tailf:display-when "not(../../ncs:module) or ../../ncs:module[ncs:name='tailf-ned-cisco-ios']";
      tailf:info
        "VRF commands";
      list definition {
        tailf:info
          "VRF definition mode";
        tailf:cli-full-command;
        tailf:cli-mode-name "config-vrf";
        unique "rd";
        key "name";
        leaf name {
          type string {
            tailf:info
              "WORD;;VRF name";
          }
        }
        leaf description {
          tailf:info
            "VRF specific description";
          tailf:cli-multi-value;
          tailf:cli-preformatted;
          tailf:cli-full-command;
          type string {
            tailf:info
              "LINE;;Up to 244 characters describing this VRF";
            length "1..244";
          }
        }
        leaf rd {
          tailf:info
            "Specify Route Distinguisher";
          tailf:cli-remove-before-change;
          tailf:cli-full-command;
          type rd-type;
        }
        container route-target {
          tailf:info
            "Specify Target VPN Extended Communities";
          tailf:cli-diff-dependency "../rd" {
            tailf:xpath-root 3;
          }
          uses route-target-grouping;
        }
        container address-family {
          tailf:info
            "Enter Address Family command mode";
          container ipv4 {
            tailf:info
              "Address family";
            tailf:cli-add-mode;
            tailf:cli-mode-name "config-vrf-af";
            tailf:cli-exit-command "exit-address-family";
            tailf:cli-full-command;
            presence "true";
            uses vrf-definition-af-grouping;
            container mdt {
              tailf:info
                "Backbone Multicast Distribution Tree";
              container default {
                tailf:info
                  "The default group";
                leaf address {
                  tailf:cli-drop-node-name;
                  tailf:cli-full-command;
                  tailf:cli-remove-before-change;
                  type inet:ipv4-address {
                    tailf:info
                      "A.B.C.D;;IP multicast group address";
                  }
                }
                container mpls {
                  tailf:info
                    "MPLS tunnel options";
                  leaf mldp {
                    tailf:info
                      "Use a MLDP LSP to create the default MDT";
                    type inet:ipv4-address {
                      tailf:info
                        "A.B.C.D;;MP2MP LSP root address";
                    }
                  }
                }
              }
              container data {
                tailf:info
                  "MDT data trees";
                list multicast {
                  tailf:cli-drop-node-name;
                  tailf:cli-suppress-mode;
                  tailf:cli-delete-when-empty;
                  key "address wildcard";
                  leaf address {
                    type inet:ipv4-address {
                      tailf:info
                        "A.B.C.D;;IP multicast group address";
                    }
                  }
                  leaf wildcard {
                    type inet:ipv4-address {
                      tailf:info
                        "A.B.C.D;;Wildcard bits";
                    }
                  }
                }
                leaf list {
                  tailf:info
                    "Access-list";
                  type ext-acl-type;
                }
                leaf threshold {
                  tailf:info
                    "MDT switching threshold";
                  type uint32 {
                    tailf:info
                      "<1-4294967>;;Traffic rate in kilobits per second";
                  }
                }
              }
              leaf log-reuse {
                tailf:info
                  "Event logging for data MDT reuse";
                type empty;
              }
              leaf-list preference {
                tailf:info
                  "MDT preference (default pim mldp)";
                tailf:cli-flat-list-syntax {
                  tailf:cli-replace-all;
                }
                type enumeration {
                  enum "mldp" {
                    tailf:info
                      "MDT preference mLDP";
                  }
                  enum "pim" {
                    tailf:info
                      "MDT preference PIM";
                  }
                }
              }
            }
          }
          container ipv6 {
            tailf:info
              "Address family";
            tailf:cli-add-mode;
            tailf:cli-mode-name "config-vrf-af";
            tailf:cli-exit-command "exit-address-family";
            tailf:cli-full-command;
            presence "true";
            uses vrf-definition-af-grouping;
          }
        }
      }
    }
    container security {
      tailf:ncs-device-type "cli-ned";
      tailf:display-when "not(../../ncs:module) or ../../ncs:module[ncs:name='tailf-ned-cisco-ios']";
      tailf:info
        "Infra Security CLIs";
      container passwords {
        tailf:info
          "Password security CLIs";
        leaf min-length {
          tailf:info
            "Minimum length of passwords";
          type uint8 {
            tailf:info
              "<0-16>;;Minimum length of all user/enable passwords";
            range "0..16";
          }
        }
      }
      container authentication {
        tailf:info
          "Authentication security CLIs";
        container failure {
          tailf:info
            "Authentication failure logging";
          tailf:cli-compact-syntax;
          tailf:cli-sequence-commands {
            tailf:cli-reset-siblings;
          }
          leaf rate {
            tailf:info
              "Authentication failure threshold rate";
            tailf:cli-incomplete-command;
            type uint16 {
              tailf:info
                "<2-1024>;;Authentication failure threshold rate";
              range "2..1024";
            }
          }
          leaf log {
            tailf:info
              "log a message if the Authentication failures over the last one minute equalled this number";
            type empty;
          }
        }
      }
    }
    container enable {
      tailf:ncs-device-type "cli-ned";
      tailf:display-when "not(../../ncs:module) or ../../ncs:module[ncs:name='tailf-ned-cisco-ios']";
      tailf:info
        "Modify enable password parameters";
      container password {
        tailf:info
          "Assign the privileged level password (MAX of 25 characters)";
        tailf:cli-compact-syntax;
        tailf:cli-sequence-commands;
        uses password-grouping;
      }
      container password-conf {
        tailf:cli-drop-node-name;
        container password {
          tailf:info
            "Assign the privileged level password (MAX of 25 characters)";
          list level {
            tailf:info
              "Set exec level password";
            tailf:cli-suppress-mode;
            tailf:cli-delete-when-empty;
            tailf:cli-compact-syntax;
            tailf:cli-sequence-commands;
            key "level";
            leaf level {
              type uint8 {
                tailf:info
                  "<1-15>;;Level number";
                range "1..15";
              }
            }
            uses password-grouping;
          }
        }
      }
      leaf last-resort {
        tailf:info
          "Define enable action if no TACACS servers respond";
        tailf:cli-full-command;
        type enumeration {
          enum "password" {
            tailf:info
              "Enable by giving the local enable password";
          }
          enum "succeed" {
            tailf:info
              "Enable without further question";
          }
        }
      }
      container secret {
        tailf:info
          "Assign the privileged level secret";
        tailf:cli-compact-syntax;
        tailf:cli-sequence-commands {
          tailf:cli-reset-siblings;
        }
        leaf type {
          tailf:cli-drop-node-name;
          tailf:cli-optional-in-sequence;
          tailf:cli-incomplete-command;
          type enumeration {
            enum "0" {
              tailf:info
                "Specifies an UNENCRYPTED password will follow";
            }
            enum "4" {
              tailf:info
                "Specifies a HIDDEN secret will follow";
            }
            enum "5" {
              tailf:info
                "Specifies an ENCRYPTED secret will follow";
            }
            enum "8" {
              tailf:info
                "Specifies a PBKDF2 HASHED secret will follow";
            }
            enum "9" {
              tailf:info
                "Specifies a SCRYPT HASHED secret will follow";
            }
          }
        }
        leaf secret {
          tailf:cli-drop-node-name;
          tailf:cli-full-command;
          tailf:cli-disallow-value "0|4|5|8|9|key-chain";
          tailf:meta-data "secret-password";
          type string {
            tailf:info
              "LINE;;The UNENCRYPTED (cleartext) 'enable' secret";
          }
        }
      }
      container secret-conf {
        tailf:cli-drop-node-name;
        container secret {
          tailf:info
            "Assign the privileged level secret";
          list level {
            tailf:info
              "Set exec level password";
            tailf:cli-suppress-mode;
            tailf:cli-delete-when-empty;
            tailf:cli-compact-syntax;
            tailf:cli-sequence-commands {
              tailf:cli-reset-siblings;
            }
            tailf:cli-incomplete-command;
            key "level";
            leaf level {
              tailf:cli-suppress-range;
              type uint8 {
                tailf:info
                  "<1-15>;;Level number";
                range "1..15";
              }
            }
            leaf type {
              tailf:cli-drop-node-name;
              tailf:cli-optional-in-sequence;
              tailf:cli-incomplete-command;
              type enumeration {
                enum "0" {
                  tailf:info
                    "Specifies an UNENCRYPTED password will follow";
                }
                enum "4" {
                  tailf:info
                    "Specifies a HIDDEN secret will follow";
                }
                enum "5" {
                  tailf:info
                    "Specifies an ENCRYPTED secret will follow";
                }
                enum "8" {
                  tailf:info
                    "Specifies a PBKDF2 HASHED secret will follow";
                }
                enum "9" {
                  tailf:info
                    "Specifies a SCRYPT HASHED secret will follow";
                }
              }
            }
            leaf secret {
              tailf:cli-drop-node-name;
              tailf:cli-full-command;
              tailf:cli-disallow-value "0|4|5|8|9|key-chain";
              tailf:meta-data "secret-password" {
                tailf:meta-value "enable secret level <level> <PASSWORD>";
              }
              type string {
                tailf:info
                  "LINE;;The UNENCRYPTED (cleartext) 'enable' secret";
              }
            }
          }
        }
      }
      leaf use-tacacs {
        tailf:info
          "Use TACACS to check enable passwords";
        tailf:cli-full-command;
        type empty;
      }
    }
    container aaa {
      tailf:ncs-device-type "cli-ned";
      tailf:display-when "not(../../ncs:module) or ../../ncs:module[ncs:name='tailf-ned-cisco-ios']";
      tailf:info
        "Authentication, Authorization and Accounting.";
      tailf:cli-incomplete-command;
      leaf new-model {
        tailf:info
          "Enable NEW access control commands and functions.(Disables OLD commands.)";
        type empty;
      }
      container group {
        tailf:info
          "AAA group definitions";
        tailf:cli-diff-dependency "../new-model" {
          tailf:xpath-root 3;
        }
        container server {
          tailf:info
            "AAA Server group definitions";
          list radius {
            tailf:info
              "Radius server-group definition";
            tailf:cli-mode-name "config-sg-radius";
            key "name";
            leaf name {
              type string {
                tailf:info
                  "WORD;;Server-group name";
              }
            }
            container server {
              tailf:info
                "Specify a RADIUS server";
              list name {
                tailf:info
                  "Name of radius server";
                tailf:cli-suppress-mode;
                key "name";
                leaf name {
                  tailf:non-strict-leafref {
                    path "../../../name";
                  }
                  type string {
                    tailf:info
                      "WORD;;Name";
                  }
                }
              }
              list direct {
                tailf:cli-drop-node-name;
                tailf:cli-compact-syntax;
                tailf:cli-suppress-mode;
                key "name";
                leaf name {
                  tailf:cli-disallow-value "name";
                  type inet:host {
                    tailf:info
                      "Hostname or A.B.C.D;;IP address of RADIUS server";
                  }
                }
                leaf auth-port {
                  tailf:info
                    "UDP port for RADIUS authentication server (default is 1645)";
                  type uint16 {
                    tailf:info
                      "<0-65535>;;Port number";
                    range "0..65535";
                  }
                }
                leaf acct-port {
                  tailf:info
                    "UDP port for RADIUS accounting server (default is 1646)";
                  type uint16 {
                    tailf:info
                      "<0-65535>;;Port number";
                    range "0..65535";
                  }
                }
              }
            }
            list server-private {
              tailf:info
                "Define a private RADIUS server (per group)";
              tailf:cli-suppress-mode;
              tailf:cli-delete-when-empty;
              tailf:cli-compact-syntax;
              key "name";
              leaf name {
                type inet:host {
                  tailf:info
                    "WORD;;Hostname or X:X:X:X::X or A.B.C.D address of RADIUS server";
                }
              }
              uses radius-server-grouping;
            }
            container backoff {
              tailf:info
                "Retry backoff pattern (Default is retransmits with constant delay)";
              container exponential {
                tailf:info
                  "Exponential retransmit backoff";
                tailf:cli-delete-when-empty;
                presence "true";
                leaf max-delay {
                  tailf:info
                    "Max delay between retransmits(default is 3 min)";
                  type uint8 {
                    tailf:info
                      "<1-120>;;Max time (in minutes) to delay between retransmits";
                    range "1..120";
                  }
                  default "3";
                }
                leaf backoff-retry {
                  tailf:info
                    "Exponential backoff retry number(default is 8)";
                  type uint8 {
                    tailf:info
                      "<1-50>;;Number of retransmits in the exponential backoff mode";
                    range "1..50";
                  }
                  default "8";
                }
              }
            }
            container ip {
              tailf:info
                "Internet Protocol config commands";
              container vrf {
                tailf:info
                  "Set VPN Routing Forwarding to use with the servers";
                leaf forwarding {
                  tailf:info
                    "Configure forwarding table";
                  tailf:cli-diff-dependency "../../../../../../../ip/vrf" {
                    tailf:xpath-root 3;
                  }
                  tailf:non-strict-leafref {
                    path "../../../../../../../ip/vrf/name";
                  }
                  type string {
                    tailf:info
                      "WORD;;VRF name";
                  }
                }
              }
              container radius {
                tailf:info
                  "RADIUS configuration commands";
                container source-interface {
                  tailf:info
                    "Specify interface for source address in RADIUS packets";
                  uses interface-name-grouping;
                }
              }
            }
            leaf deadtime {
              tailf:info
                "Specify time in minutes to ignore an unresponsive server";
              type uint16 {
                tailf:info
                  "<0-1440>;;Dead-time in minutes for this server group";
                range "0..1440";
              }
            }
          }
          list tacacs-plus {
            tailf:alt-name "tacacs+";
            tailf:info
              "Tacacs+ server-group definition";
            tailf:cli-mode-name "config-sg-tacacs+";
            tailf:cli-full-command;
            key "name";
            leaf name {
              type string {
                tailf:info
                  "WORD;;Server-group name";
              }
            }
            container server {
              tailf:info
                "Specify a TACACS server";
              list name {
                tailf:cli-suppress-mode;
                tailf:cli-delete-when-empty;
                key "name";
                leaf name {
                  type string {
                    tailf:info
                      "WORD;;Tacacs server name";
                  }
                }
              }
              list server-list {
                tailf:cli-drop-node-name;
                tailf:cli-suppress-mode;
                tailf:cli-delete-when-empty;
                key "name";
                leaf name {
                  tailf:cli-disallow-value "name";
                  type inet:host {
                    tailf:info
                      "Hostname or A.B.C.D;;IP address of TACACS server";
                  }
                }
              }
            }
            list server-private {
              tailf:info
                "Define a private TACACS server (per group)";
              tailf:cli-suppress-mode;
              tailf:cli-delete-when-empty;
              tailf:cli-compact-syntax;
              tailf:cli-sequence-commands {
                tailf:cli-reset-siblings;
              }
              key "name";
              leaf name {
                type inet:host {
                  tailf:info
                    "Hostname or A.B.C.D;;IP address of TACACS server";
                }
              }
              leaf timeout {
                tailf:info
                  "Time to wait for this TACACS server to reply (overrides default)";
                tailf:cli-optional-in-sequence;
                type uint16 {
                  tailf:info
                    "<1-1000>;;Timeout value in seconds to wait for server to reply";
                  range "1..1000";
                }
              }
              container key {
                tailf:info
                  "per-server encryption key (overrides default)";
                tailf:cli-flatten-container;
                tailf:cli-compact-syntax;
                tailf:cli-sequence-commands;
                uses password-grouping;
              }
            }
            container ip {
              tailf:info
                "Internet Protocol config commands";
              container vrf {
                tailf:info
                  "Set VPN Routing Forwarding to use with the servers";
                leaf forwarding {
                  tailf:info
                    "Configure forwarding table";
                  tailf:cli-diff-dependency "../../../../../../../ip/vrf" {
                    tailf:xpath-root 3;
                  }
                  tailf:non-strict-leafref {
                    path "../../../../../../../ip/vrf/name";
                  }
                  type string {
                    tailf:info
                      "WORD;;VRF name";
                  }
                }
              }
              container tacacs {
                tailf:info
                  "TACACS configuration commands";
                container source-interface {
                  tailf:info
                    "Specify interface for source address in TACACS packets";
                  uses interface-name-grouping;
                }
              }
            }
          }
        }
      }
      container authentication {
        tailf:info
          "Authentication configurations parameters.";
        tailf:cli-diff-dependency "../new-model" {
          tailf:xpath-root 3;
        }
        container attempts {
          tailf:info
            "Set the maximum number of authentication attempts";
          leaf login {
            tailf:info
              "Set the max. number of attempts for login service";
            type uint8 {
              tailf:info
                "<1-25>;;Specify value for the number of attempts";
            }
            default "3";
          }
        }
        leaf username-prompt {
          tailf:info
            "Text to use when prompting for a username";
          type string {
            tailf:info
              "WORD;;Text of prompt";
          }
        }
        list dot1x {
          tailf:info
            "Set authentication lists for IEEE 802.1x.";
          tailf:cli-suppress-mode;
          tailf:cli-delete-when-empty;
          tailf:cli-compact-syntax;
          tailf:cli-incomplete-command;
          key "name";
          leaf name {
            type aaa-authentication-name-type;
          }
          leaf cache {
            tailf:info
              "Use Cached-group";
            type aaa-group-type;
          }
          leaf group {
            tailf:info
              "Use Server-group";
            type aaa-group-type;
          }
        }
        list login {
          tailf:info
            "Set authentication lists for logins.";
          tailf:cli-suppress-mode;
          tailf:cli-delete-when-empty;
          tailf:cli-compact-syntax;
          tailf:cli-reset-container;
          tailf:cli-incomplete-command;
          key "name";
          leaf name {
            type aaa-authentication-name-type;
          }
          uses aaa-authentication-method-grouping;
        }
        container enable {
          tailf:info
            "Set authentication list for enable.";
          container default {
            tailf:info
              "The default authentication list.";
            tailf:cli-compact-syntax;
            uses aaa-authentication-method-grouping;
          }
        }
        list ppp {
          tailf:info
            "Set authentication lists for ppp.";
          tailf:cli-suppress-mode;
          tailf:cli-delete-when-empty;
          tailf:cli-compact-syntax;
          tailf:cli-reset-container;
          tailf:cli-incomplete-command;
          key "name";
          leaf name {
            type aaa-authentication-name-type;
          }
          uses aaa-authentication-method-grouping;
        }
      }
      container authorization {
        tailf:info
          "Authorization configurations parameters.";
        tailf:cli-incomplete-command;
        tailf:cli-diff-dependency "../new-model" {
          tailf:xpath-root 3;
        }
        leaf console {
          tailf:info
            "For enabling console authorization";
          type empty;
        }
        leaf config-commands {
          tailf:info
            "For configuration mode commands.";
          type empty;
        }
        list exec {
          tailf:info
            "For starting an exec (shell).";
          tailf:cli-suppress-mode;
          tailf:cli-delete-when-empty;
          tailf:cli-compact-syntax;
          tailf:cli-incomplete-command;
          tailf:cli-reset-container;
          key "name";
          leaf name {
            type aaa-authorization-name-type;
          }
          uses aaa-authorization-method-grouping;
        }
        list commands {
          tailf:info
            "For exec (shell) commands.";
          tailf:cli-suppress-mode;
          tailf:cli-delete-when-empty;
          tailf:cli-compact-syntax;
          tailf:cli-incomplete-command;
          tailf:cli-reset-container;
          key "level name";
          leaf level {
            type uint8 {
              tailf:info
                "<0-15>;;Enable level";
              range "0..15";
            }
          }
          leaf name {
            type aaa-authorization-name-type;
          }
          uses aaa-authorization-method-grouping;
        }
        list eventmanager {
          tailf:info
            "For starting an exec (shell).";
          tailf:cli-suppress-mode;
          tailf:cli-delete-when-empty;
          tailf:cli-compact-syntax;
          tailf:cli-incomplete-command;
          key "name";
          leaf name {
            type aaa-authorization-name-type;
          }
          uses aaa-authorization-method-grouping;
        }
        list network {
          tailf:info
            "For network services. (PPP, SLIP, ARAP)";
          tailf:cli-suppress-mode;
          tailf:cli-delete-when-empty;
          tailf:cli-compact-syntax;
          tailf:cli-incomplete-command;
          key "name";
          leaf name {
            type aaa-authorization-name-type;
          }
          uses aaa-authorization-method-grouping;
        }
        list auth-proxy {
          tailf:cli-suppress-mode;
          tailf:cli-delete-when-empty;
          tailf:cli-compact-syntax;
          tailf:cli-incomplete-command;
          key "name";
          leaf name {
            type aaa-authorization-name-type;
          }
          uses aaa-authorization-method-grouping;
        }
      }
      container accounting {
        tailf:info
          "Accounting configurations parameters.";
        tailf:cli-incomplete-command;
        tailf:cli-diff-dependency "../new-model" {
          tailf:xpath-root 3;
        }
        container send {
          tailf:info
            "Send records to accounting server.";
          container stop-record {
            tailf:info
              "Generate STOP records for a specified event.";
            container authentication {
              tailf:info
                "Generate STOP records for authentication failures.";
              leaf failure {
                tailf:info
                  "Generate STOP records for authentication failures.";
                type empty;
              }
              container failure-vrf {
                tailf:cli-drop-node-name;
                container failure {
                  tailf:info
                    "Generate STOP records for authentication failures.";
                  tailf:cli-incomplete-command;
                  tailf:cli-incomplete-no;
                  list vrf {
                    tailf:info
                      "VPN Routing/Forwarding parameters";
                    tailf:cli-suppress-mode;
                    tailf:cli-delete-when-empty;
                    key "name";
                    leaf name {
                      tailf:cli-diff-dependency "../../../../../../../../../ip/vrf" {
                        tailf:xpath-root 3;
                      }
                      tailf:cli-diff-dependency "../../../../../../../../../vrf/definition" {
                        tailf:xpath-root 3;
                      }
                      type string {
                        tailf:info
                          "WORD;;VRF name";
                      }
                    }
                  }
                }
              }
            }
          }
        }
        container nested {
          tailf:info
            "When starting PPP from EXEC, generate NETWORK records before EXEC-STOP record.";
          tailf:cli-delete-when-empty;
          presence "true";
          container suppress {
            tailf:info
              "Exec accounting records suppression options";
            leaf stop {
              tailf:info
                "Suppress stop record for exec if network start record sent";
              type empty;
            }
          }
        }
        list commands {
          tailf:info
            "For exec (shell) commands.";
          tailf:cli-suppress-mode;
          tailf:cli-delete-when-empty;
          tailf:cli-compact-syntax;
          key "level name";
          leaf level {
            type uint8 {
              tailf:info
                "<0-15>;;Enable level";
              range "0..15";
            }
          }
          leaf name {
            type aaa-accounting-name-type;
          }
          uses aaa-accounting-method-grouping;
        }
        list exec {
          tailf:info
            "For starting an exec (shell).";
          tailf:cli-suppress-mode;
          tailf:cli-delete-when-empty;
          tailf:cli-compact-syntax;
          key "name";
          leaf name {
            type aaa-accounting-name-type;
          }
          uses aaa-accounting-method-grouping;
        }
        list network {
          tailf:info
            "For network services. (PPP, SLIP, ARAP)";
          tailf:cli-suppress-mode;
          tailf:cli-delete-when-empty;
          tailf:cli-compact-syntax;
          key "name";
          leaf name {
            type aaa-accounting-name-type;
          }
          uses aaa-accounting-method-grouping;
        }
        list auth-proxy {
          tailf:info
            "For authentication proxy events.";
          tailf:cli-suppress-mode;
          tailf:cli-delete-when-empty;
          tailf:cli-compact-syntax;
          key "name";
          leaf name {
            type aaa-accounting-name-type;
          }
          uses aaa-accounting-method-grouping;
        }
        list connection {
          tailf:info
            "For outbound connections. (telnet, rlogin)";
          tailf:cli-suppress-mode;
          tailf:cli-delete-when-empty;
          tailf:cli-compact-syntax;
          key "name";
          leaf name {
            type aaa-accounting-name-type;
          }
          uses aaa-accounting-method-grouping;
        }
        list dot1x {
          tailf:info
            "For dot1x sessions.";
          tailf:cli-suppress-mode;
          tailf:cli-delete-when-empty;
          tailf:cli-compact-syntax;
          key "name";
          leaf name {
            type aaa-accounting-name-type;
          }
          uses aaa-accounting-method-grouping;
        }
        container system {
          tailf:info
            "For system events.";
          container default {
            tailf:cli-compact-syntax;
            tailf:cli-delete-when-empty;
            presence "true";
            uses aaa-accounting-method-grouping;
          }
        }
        container suppress {
          tailf:info
            "Do not generate accounting records for a specific type of user.";
          leaf null-username {
            tailf:info
              "Do not generate accounting records for users with a null-username";
            type empty;
          }
        }
        container update {
          tailf:info
            "Enable accounting update records.";
          tailf:cli-compact-syntax;
          leaf newinfo {
            tailf:info
              "Only send accounting update records when we have new acct info.";
            type empty;
          }
          leaf periodic {
            tailf:info
              "Send accounting update records at regular intervals.";
            type uint32 {
              tailf:info
                "<1-71582>;;Periodic intervals to send accounting update records(in minutes)";
              range "1..71582";
            }
          }
        }
        container delay-start {
          tailf:info
            "Delay PPP Network start record until peer IP address is known.";
          presence "true";
          leaf all {
            tailf:info
              "Delay start records for all vrf and non-vrf users.";
            type empty;
          }
        }
      }
      leaf session-id {
        tailf:info
          "AAA Session ID";
        tailf:cli-diff-dependency "../new-model" {
          tailf:xpath-root 3;
        }
        tailf:meta-data "suppress-no-command";
        type enumeration {
          enum "common" {
            tailf:info
              "Common Session ID";
          }
          enum "unique" {
            tailf:info
              "Unique Session ID for different accounting types";
          }
        }
      }
      container attribute {
        tailf:info
          "AAA attribute definitions";
        tailf:cli-diff-dependency "../new-model" {
          tailf:xpath-root 3;
        }
        list list {
          tailf:info
            "AAA attribute list definition";
          tailf:cli-mode-name "config-attr-list";
          key "name";
          leaf name {
            type string {
              tailf:info
                "WORD;;name";
            }
          }
          container attribute {
            tailf:info
              "Specify an AAA attribute";
            container type {
              tailf:info
                "Specify an AAA attribute type";
              leaf interface-config {
                tailf:info
                  "Configuration commands for an interface";
                type string {
                  tailf:info
                    "WORD;;string";
                }
              }
            }
          }
        }
      }
      container server {
        tailf:info
          "Local AAA server";
        tailf:cli-diff-dependency "../new-model" {
          tailf:xpath-root 3;
        }
        container radius {
          tailf:info
            "Profile for local radius server";
          container dynamic-author {
            tailf:info
              "Local server profile for RFC 3576 support";
            tailf:cli-add-mode;
            tailf:cli-mode-name "config-locsvr-da-radius";
            list client {
              tailf:info
                "Specify a RADIUS client";
              tailf:cli-suppress-mode;
              tailf:cli-delete-when-empty;
              key "address";
              leaf address {
                type inet:host {
                  tailf:info
                    "Hostname or A.B.C.D;;IP address of RADIUS client";
                }
              }
              container server-key {
                tailf:info
                  "Specify a RADIUS client server-key";
                tailf:cli-flatten-container;
                tailf:cli-compact-syntax;
                tailf:cli-sequence-commands;
                uses password-grouping {
                  refine "secret" {
                    tailf:meta-data "secret-password" {
                      tailf:meta-value "aaa server radius dynamic-author<NL><*> :: client <client> server-key <PASSWORD>";
                    }
                  }
                }
              }
            }
          }
        }
      }
    }
    list switch {
      tailf:ncs-device-type "cli-ned";
      tailf:display-when "not(../ncs:module) or ../ncs:module[ncs:name='tailf-ned-cisco-ios']";
      tailf:info
        "Config commands for the switches in the stack";
      tailf:cli-suppress-mode;
      tailf:cli-delete-when-empty;
      tailf:cli-incomplete-command;
      key "id";
      leaf id {
        type uint8 {
          tailf:info
            "<1-9>;;Switch Number";
          range "1..9";
        }
      }
      leaf provision {
        tailf:info
          "Configure Switch provision / offline config";
        tailf:cli-full-command;
        type string {
          tailf:info
            "WORD;;provision a XXX switch with YYY";
        }
      }
    }
    container resource {
      tailf:ncs-device-type "cli-ned";
      tailf:display-when "not(../../ncs:module) or ../../ncs:module[ncs:name='tailf-ned-cisco-ios']";
      tailf:info
        "Configure Embedded Resource Manager (ERM)";
      container policy {
        tailf:info
          "policy  Configure Embedded Resource Manager (ERM)";
        tailf:cli-add-mode;
        tailf:cli-mode-name "config-erm";
        tailf:cli-full-command;
        presence "true";
        list policy {
          tailf:info
            "Configure Resource Policy";
          tailf:cli-mode-name "config-erm-policy";
          key "name";
          leaf name {
            type string {
              tailf:info
                "WORD;;Resource Policy Name";
            }
          }
          leaf global {
            tailf:info
              "Configure a Global Policy";
            tailf:cli-hide-in-submode;
            type empty;
          }
          leaf system {
            tailf:info
              "Configure System Level Resource Owners";
            type empty;
          }
        }
      }
    }
    container cns {
      tailf:ncs-device-type "cli-ned";
      tailf:display-when "not(../../ncs:module) or ../../ncs:module[ncs:name='tailf-ned-cisco-ios']";
      tailf:info
        "CNS agents";
      list trusted-server {
        tailf:info
          "Trusted Server Configuration";
        tailf:cli-suppress-mode;
        tailf:cli-delete-when-empty;
        key "agent name";
        leaf agent {
          type enumeration {
            enum "all-agents" {
              tailf:info
                "trusted  for all agents";
            }
            enum "config" {
              tailf:info
                "trusted for config agent";
            }
            enum "event" {
              tailf:info
                "trusted for event agent";
            }
            enum "exec" {
              tailf:info
                "trusted for exec agent";
            }
            enum "image" {
              tailf:info
                "trusted for image agent";
            }
          }
        }
        leaf name {
          type string {
            tailf:info
              "WORD;;Host name or address of trusted-server";
          }
        }
      }
      container id {
        tailf:info
          "Get CNS ID for CNS agents";
        leaf string {
          tailf:info
            "Use an arbitrary string as the unique ID";
          tailf:cli-full-command;
          type string {
            tailf:info
              "WORD;;e.g. hostname";
          }
        }
        container id-services-list {
          tailf:cli-drop-node-name;
          list string {
            tailf:info
              "Use an arbitrary string as the unique ID";
            tailf:cli-suppress-mode;
            tailf:cli-delete-when-empty;
            tailf:cli-sequence-commands;
            tailf:cli-compact-syntax;
            key "service";
            leaf string {
              tailf:cli-prefix-key;
              tailf:cli-drop-node-name;
              type string {
                tailf:info
                  "WORD;;e.g. hostname";
              }
            }
            leaf service {
              type enumeration {
                enum "event" {
                  tailf:info
                    "Set this ID as the event ID";
                }
                enum "image" {
                  tailf:info
                    "Set this ID as the image ID";
                }
              }
            }
          }
        }
      }
      list event {
        tailf:info
          "Event Agent";
        tailf:cli-suppress-mode;
        tailf:cli-delete-when-empty;
        tailf:cli-compact-syntax;
        key "name";
        leaf name {
          type string {
            tailf:info
              "WORD;;Host name or ip address of event gateway";
          }
        }
        leaf port-number {
          tailf:cli-drop-node-name;
          type uint16 {
            tailf:info
              "<0-65535>;;Event Gateway port number, default is 11011";
            range "0..65535";
          }
        }
        container source {
          tailf:info
            "bind socket to a source ip";
          tailf:cli-flatten-container;
          tailf:cli-compact-syntax;
          uses interface-name-grouping;
        }
        container keepalive {
          tailf:info
            "Keepalive timeout retry_count";
          tailf:cli-flatten-container;
          tailf:cli-compact-syntax;
          tailf:cli-sequence-commands;
          leaf seconds {
            tailf:cli-drop-node-name;
            tailf:cli-incomplete-command;
            type uint16 {
              tailf:info
                "<0-65535>;;timeout in seconds , default is 0";
            }
          }
          leaf retry-count {
            tailf:cli-drop-node-name;
            type uint16 {
              tailf:info
                "<0-65535>;;retry count , default is 0";
            }
          }
        }
      }
      container image {
        tailf:info
          "CNS Image Agent";
        container server {
          tailf:info
            "CNS Image Agent management server";
          tailf:cli-compact-syntax;
          tailf:cli-sequence-commands {
            tailf:cli-reset-siblings;
          }
          leaf server-url {
            tailf:cli-drop-node-name;
            tailf:cli-remove-before-change;
            type string {
              tailf:info
                "WORD;;URL to POST to for the management server";
            }
          }
          leaf status {
            tailf:info
              "CNS Image Agent status server";
            type string {
              tailf:info
                "WORD;;URL to POST status messages to";
            }
          }
        }
      }
      container config {
        tailf:info
          "Configuration Agent";
        container notify {
          tailf:info
            "Configuration change notification";
          tailf:cli-compact-syntax;
          tailf:cli-sequence-commands {
            tailf:cli-reset-siblings;
          }
          leaf capture {
            tailf:cli-drop-node-name;
            type enumeration {
              enum "all" {
                tailf:info
                  "notify all config commands";
              }
              enum "diff" {
                tailf:info
                  "notify config changes only";
              }
            }
          }
          leaf interval {
            tailf:info
              "send config change event if nothing entered in config mode for this many minutes";
            type uint16 {
              tailf:info
                "<0-35791>;;number in minutes, default is 5";
              range "0..35791";
            }
          }
        }
        container partial {
          tailf:info
            "Partial Configuration";
          tailf:cli-compact-syntax;
          tailf:cli-sequence-commands {
            tailf:cli-reset-siblings;
          }
          leaf host {
            tailf:cli-drop-node-name;
            type inet:host {
              tailf:info
                "WORD;;Host name or address of configuration server";
            }
          }
          leaf port-number {
            tailf:cli-drop-node-name;
            type uint16 {
              tailf:info
                "<0-65535>;;the port number of the config service. default is 80";
            }
          }
        }
      }
      list exec {
        tailf:info
          "Exec Agent";
        tailf:cli-suppress-mode;
        tailf:cli-delete-when-empty;
        tailf:cli-compact-syntax;
        tailf:cli-sequence-commands {
          tailf:cli-reset-siblings;
        }
        max-elements 1;
        key "port-number";
        leaf encrypt {
          tailf:info
            "Use an encrypted link to the server";
          tailf:cli-prefix-key;
          tailf:cli-optional-in-sequence;
          type empty;
        }
        leaf port-number {
          type uint16 {
            tailf:info
              "<1-65535>;;port number of plaintext exec service.";
            range "1..65535";
          }
        }
        container source {
          tailf:info
            "bind socket to a source ip";
          tailf:cli-flatten-container;
          tailf:cli-compact-syntax;
          uses interface-name-grouping;
        }
      }
      leaf dhcp {
        tailf:info
          "Allow DHCP option 43 message to pass in config commands";
        type empty;
      }
    }
    container epm {
      tailf:ncs-device-type "cli-ned";
      tailf:display-when "not(../../ncs:module) or ../../ncs:module[ncs:name='tailf-ned-cisco-ios']";
      tailf:info
        "EPM Global Configuration Commands";
      leaf logging {
        tailf:info
          "Enable EPM logging";
        type empty;
      }
    }
    container clock {
      tailf:ncs-device-type "cli-ned";
      tailf:display-when "not(../../ncs:module) or ../../ncs:module[ncs:name='tailf-ned-cisco-ios']";
      tailf:info
        "Configure time-of-day clock";
      container timezone {
        tailf:info
          "Configure time zone";
        tailf:cli-compact-syntax;
        tailf:cli-sequence-commands {
          tailf:cli-reset-siblings;
        }
        leaf zone {
          tailf:cli-drop-node-name;
          tailf:cli-incomplete-command;
          type string {
            tailf:info
              "WORD;;name of time zone";
          }
        }
        leaf offset {
          tailf:cli-drop-node-name;
          tailf:cli-optional-in-sequence;
          tailf:cli-incomplete-command;
          type enumeration {
            enum "+";
            enum "-";
          }
        }
        leaf hours {
          tailf:cli-drop-node-name;
          type int8 {
            tailf:info
              "<-23 - 23>;;Hours offset from UTC";
            range "-23..23";
          }
        }
        leaf minutes {
          tailf:cli-drop-node-name;
          type int8 {
            tailf:info
              "<0-59>;;Minutes ofset from UTC";
            range "0..59";
          }
        }
      }
      container summer-time {
        tailf:info
          "Configure summer (daylight savings) time";
        tailf:cli-compact-syntax;
        tailf:cli-sequence-commands {
          tailf:cli-reset-siblings;
        }
        leaf zone {
          tailf:cli-drop-node-name;
          tailf:cli-incomplete-command;
          tailf:cli-disallow-value "date|recurring";
          type string {
            tailf:info
              "WORD;;name of time zone in summer";
          }
        }
        choice summer-choice {
          case date-case {
            leaf date {
              tailf:info
                "Configure absolute summer time";
              type empty;
            }
            leaf date-start-month {
              tailf:cli-drop-node-name;
              tailf:cli-incomplete-command;
              type month-type {
                tailf:info
                  "MONTH;;Month to start";
              }
            }
            leaf date-start-date {
              tailf:cli-drop-node-name;
              tailf:cli-incomplete-command;
              type uint8 {
                tailf:info
                  "<1-31>;;Date to start";
                range "1..31";
              }
            }
            leaf date-start-year {
              tailf:cli-drop-node-name;
              tailf:cli-incomplete-command;
              type uint16 {
                tailf:info
                  "<1993-2035>;;Year to start";
                range "1993..2035";
              }
            }
            leaf date-start-time {
              tailf:cli-drop-node-name;
              tailf:cli-incomplete-command;
              type hhmm-type {
                tailf:info
                  "hh:mm;;Time to start (hh:mm)";
              }
            }
            leaf date-end-month {
              tailf:cli-drop-node-name;
              tailf:cli-incomplete-command;
              type month-type {
                tailf:info
                  "MONTH;;Month to end";
              }
            }
            leaf date-end-date {
              tailf:cli-drop-node-name;
              tailf:cli-incomplete-command;
              type uint8 {
                tailf:info
                  "<1-31>;;Date to end";
                range "1..31";
              }
            }
            leaf date-end-year {
              tailf:cli-drop-node-name;
              tailf:cli-incomplete-command;
              type uint16 {
                tailf:info
                  "<1993-2035>;;Year to end";
                range "1993..2035";
              }
            }
            leaf date-end-time {
              tailf:cli-drop-node-name;
              type hhmm-type {
                tailf:info
                  "hh:mm;;Time to end (hh:mm)";
              }
            }
            leaf date-offset {
              tailf:cli-drop-node-name;
              type uint16 {
                tailf:info
                  "<1-1440>;;Offset to add in minutes";
                range "1..1440";
              }
            }
          }
          case recurring-case {
            leaf recurring {
              tailf:info
                "Configure recurring summer time";
              type empty;
            }
            leaf start {
              tailf:cli-drop-node-name;
              tailf:cli-incomplete-command;
              type union {
                type uint8 {
                  tailf:info
                    "<1-4>;;Week number to start";
                  range "1..4";
                }
                type enumeration {
                  enum "first" {
                    tailf:info
                      "First week of the month";
                  }
                  enum "last" {
                    tailf:info
                      "Last week of the month";
                  }
                }
              }
            }
            leaf start-day {
              tailf:cli-drop-node-name;
              tailf:cli-incomplete-command;
              type weekday-type {
                tailf:info
                  "DAY;;Weekday to start";
              }
            }
            leaf start-month {
              tailf:cli-drop-node-name;
              tailf:cli-incomplete-command;
              type month-type {
                tailf:info
                  "MONTH;;Month to start";
              }
            }
            leaf start-time {
              tailf:cli-drop-node-name;
              tailf:cli-incomplete-command;
              type hhmm-type {
                tailf:info
                  "hh:mm;;Time to start (hh:mm)";
              }
            }
            leaf end {
              tailf:cli-drop-node-name;
              tailf:cli-incomplete-command;
              type union {
                type uint8 {
                  tailf:info
                    "<1-4>;;Week number to end";
                  range "1..4";
                }
                type enumeration {
                  enum "first" {
                    tailf:info
                      "First week of the month";
                  }
                  enum "last" {
                    tailf:info
                      "Last week of the month";
                  }
                }
              }
            }
            leaf end-day {
              tailf:cli-drop-node-name;
              tailf:cli-incomplete-command;
              type weekday-type {
                tailf:info
                  "DAY;;Weekday to end";
              }
            }
            leaf end-month {
              tailf:cli-drop-node-name;
              tailf:cli-incomplete-command;
              type month-type {
                tailf:info
                  "MONTH;;Month to end";
              }
            }
            leaf end-time {
              tailf:cli-drop-node-name;
              type hhmm-type {
                tailf:info
                  "hh:mm;;Time to end (hh:mm)";
              }
            }
            leaf offset {
              tailf:cli-drop-node-name;
              type uint16 {
                tailf:info
                  "<1-1440>;;Offset to add in minutes";
                range "1..1440";
              }
            }
          }
        }
      }
      container calendar-valid {
        tailf:info
          "Calendar time is authoritative";
        presence "true";
      }
    }
    container device-sensor {
      tailf:ncs-device-type "cli-ned";
      tailf:display-when "not(../../ncs:module) or ../../ncs:module[ncs:name='tailf-ned-cisco-ios']";
      tailf:info
        "IOS Sensor Commands";
      leaf accounting {
        tailf:info
          "Trigger accounting updates with sensor TLVs/Options";
        type empty;
      }
      leaf notify {
        type enumeration {
          enum "all-changes" {
            tailf:info
              "Trigger identity update when TLVs are added/modified/removed";
          }
          enum "new-tlvs" {
            tailf:info
              "Trigger identity update only when TLVs are added";
          }
        }
        default "new-tlvs";
      }
    }
    container call-home {
      tailf:ncs-device-type "cli-ned";
      tailf:display-when "not(../../ncs:module) or ../../ncs:module[ncs:name='tailf-ned-cisco-ios']";
      tailf:info
        "Enter call-home configuration mode";
      tailf:cli-add-mode;
      tailf:cli-mode-name "cfg-call-home";
      leaf contact-email-addr {
        tailf:info
          "System Contact's email address";
        tailf:cli-full-command;
        type string {
          tailf:info
            "WORD;;Contact person's email address";
        }
      }
      container source-interface {
        tailf:info
          "Specify source interface";
        uses interface-name-grouping;
      }
      leaf vrf {
        tailf:info
          "VPN Routing/Forwarding instance name";
        tailf:cli-diff-dependency "../../ip/vrf" {
          tailf:xpath-root 3;
        }
        tailf:cli-diff-dependency "../../vrf/definition" {
          tailf:xpath-root 3;
        }
        type string {
          tailf:info
            "WORD;;VRF instance name";
        }
      }
      container http-proxy {
        tailf:info
          "Specify proxy server for http request";
        tailf:cli-compact-syntax;
        tailf:cli-sequence-commands {
          tailf:cli-reset-siblings;
        }
        leaf server {
          tailf:cli-drop-node-name;
          tailf:cli-incomplete-command;
          type string {
            tailf:info
              "WORD;;Http proxy server";
          }
        }
        leaf port {
          tailf:info
            "proxy server port number";
          type uint16 {
            tailf:info
              "<1-65535>;;http proxy server port number";
            range "1..65535";
          }
        }
      }
      list profile {
        tailf:info
          "Enter call-home profile configuration mode";
        tailf:cli-mode-name "cfg-call-home-profile";
        tailf:cli-full-command;
        tailf:cli-recursive-delete;
        key "name";
        leaf name {
          type string {
            tailf:info
              "WORD;;Profile name";
          }
        }
        leaf anonymous-reporting-only {
          tailf:info
            "Enable call-home anonymous reporting only";
          type empty;
        }
        leaf active {
          tailf:info
            "Activate the current profile";
          tailf:cli-boolean-no;
          tailf:cli-full-command;
          type boolean;
          default "true";
        }
        container destination {
          tailf:info
            "Message destination related configuration";
          container transport-method {
            tailf:info
              "To specify transport method for this profile";
            leaf http {
              tailf:info
                "Enable http as transport method";
              type empty;
            }
            leaf email {
              tailf:info
                "Enable email as transport method";
              tailf:cli-boolean-no;
              tailf:cli-full-command;
              type boolean;
              default "true";
            }
          }
          container address {
            tailf:info
              "To add destination address to this profile";
            leaf http {
              tailf:info
                "To add http address to this profile";
              tailf:cli-full-command;
              type string {
                tailf:info
                  "WORD;;HTTP url (1-200) characters";
              }
            }
            leaf email {
              tailf:info
                "To add email address to this profile";
              tailf:cli-full-command;
              type string {
                tailf:info
                  "WORD;;HTTP url (1-200) characters";
              }
            }
          }
        }
      }
    }
    container facility-alarm {
      tailf:ncs-device-type "cli-ned";
      tailf:display-when "not(../../ncs:module) or ../../ncs:module[ncs:name='tailf-ned-cisco-ios']";
      tailf:info
        "Alarm thresholds configuration";
      container core-temperature {
        tailf:info
          "Threshold for processor module temperature";
        uses facility-alarm-grouping;
      }
      container outlet-temperature {
        tailf:info
          "Threshold for air outlet temperature";
        uses facility-alarm-grouping;
      }
      container intake-temperature {
        tailf:info
          "Threshold for air inlet temperature";
        uses facility-alarm-grouping;
      }
      container critical {
        tailf:info
          "Behavior on critical threshold exceed";
        leaf exceed-action {
          tailf:info
            "Behavior on critical threshold exceed";
          type enumeration {
            enum "shutdown" {
              tailf:info
                "Behavior on critical threshold exceed";
            }
          }
        }
      }
    }
    container cef {
      tailf:ncs-device-type "cli-ned";
      tailf:display-when "not(../../ncs:module) or ../../ncs:module[ncs:name='tailf-ned-cisco-ios']";
      tailf:info
        "Cisco Express Forwarding";
      container table {
        tailf:info
          "Set CEF forwarding table characteristics";
        container output-chain {
          tailf:info
            "Set table output chain characteristics";
          container build {
            tailf:info
              "Set table output chain building characteristics";
            leaf favor {
              tailf:info
                "Set which table output chain building characteristics to favor";
              type enumeration {
                enum "convergence-speed" {
                  tailf:info
                    "Favor faster convergence";
                }
                enum "memory-utilization" {
                  tailf:info
                    "Favor smaller memory utilization";
                }
              }
            }
          }
        }
      }
    }
    container ipdr {
      tailf:ncs-device-type "cli-ned";
      tailf:display-when "not(../../ncs:module) or ../../ncs:module[ncs:name='tailf-ned-cisco-ios']";
      tailf:info
        "IPDR Configuration";
      list session {
        tailf:info
          "IPDR session";
        tailf:cli-suppress-mode;
        tailf:cli-delete-when-empty;
        tailf:cli-compact-syntax;
        tailf:cli-sequence-commands {
          tailf:cli-reset-siblings;
        }
        tailf:cli-incomplete-command;
        key "session-id";
        leaf session-id {
          type uint8 {
            tailf:info
              "<1-255>;;IPDR session id";
            range "1..255";
          }
        }
        leaf session-name {
          tailf:cli-drop-node-name;
          tailf:cli-incomplete-command;
          type string {
            tailf:info
              "WORD;;IPDR session name";
          }
        }
        leaf session-descr {
          tailf:cli-drop-node-name;
          tailf:cli-multi-value;
          type string {
            tailf:info
              "LINE;;IPDR session description";
          }
        }
      }
      list type {
        tailf:info
          "IPDR session type";
        tailf:cli-suppress-mode;
        tailf:cli-delete-when-empty;
        tailf:cli-compact-syntax;
        tailf:cli-incomplete-command;
        key "session-id";
        leaf session-id {
          type uint8 {
            tailf:info
              "<1-255>;;IPDR session id";
            range "1..255";
          }
        }
        choice type-choice {
          leaf ad-hoc {
            tailf:info
              "Ad-hoc type session";
            type empty;
          }
          leaf event {
            tailf:info
              "Event type session";
            type empty;
          }
          leaf time-interval {
            tailf:info
              "Time interval type session";
            type uint16 {
              tailf:info
                "<15-1440>;;Interval in minute";
            }
          }
        }
      }
      list collector {
        tailf:info
          "IPDR collector";
        tailf:cli-suppress-mode;
        tailf:cli-delete-when-empty;
        tailf:cli-compact-syntax;
        tailf:cli-sequence-commands {
          tailf:cli-reset-siblings;
        }
        tailf:cli-incomplete-command;
        key "name";
        leaf name {
          type string {
            tailf:info
              "WORD;;IPDR collector name string";
          }
        }
        leaf ip-addr {
          tailf:cli-drop-node-name;
          type inet:ipv4-address {
            tailf:info
              "A.B.C.D;;IPDR collector ip address";
          }
        }
        leaf port {
          tailf:cli-drop-node-name;
          type uint16 {
            tailf:info
              "<1-65535>;;IPDR collector port";
            range "1..65535";
          }
        }
      }
      list associate {
        tailf:info
          "IPDR collector to session association";
        tailf:cli-suppress-mode;
        tailf:cli-delete-when-empty;
        tailf:cli-compact-syntax;
        tailf:cli-sequence-commands {
          tailf:cli-reset-siblings;
        }
        tailf:cli-incomplete-command;
        key "session-id";
        leaf session-id {
          type uint8 {
            tailf:info
              "<1-255>;;IPDR session id";
            range "1..255";
          }
        }
        leaf collector-name {
          tailf:cli-drop-node-name;
          tailf:cli-incomplete-command;
          type string {
            tailf:info
              "WORD;;IPDR collector name";
          }
        }
        leaf priority {
          tailf:cli-drop-node-name;
          type uint8 {
            tailf:info
              "<1-10>;;Priority of the collector in session, lower number is higher priority";
            range "1..10";
          }
        }
      }
      list template {
        tailf:info
          "IPDR template";
        tailf:cli-suppress-mode;
        tailf:cli-delete-when-empty;
        tailf:cli-compact-syntax;
        tailf:cli-sequence-commands {
          tailf:cli-reset-siblings;
        }
        tailf:cli-incomplete-command;
        key "session-id";
        leaf session-id {
          type uint8 {
            tailf:info
              "<1-255>;;IPDR session id";
            range "1..255";
          }
        }
        leaf template-name {
          tailf:cli-drop-node-name;
          type string {
            tailf:info
              "WORD;;Template name";
          }
        }
      }
      container exporter {
        tailf:info
          "IPDR exporter";
        leaf start {
          tailf:info
            "start IPDR exporter";
          type empty;
        }
      }
    }
    container qos-conf {
      tailf:ncs-device-type "cli-ned";
      tailf:display-when "not(../../ncs:module) or ../../ncs:module[ncs:name='tailf-ned-cisco-ios']";
      tailf:cli-drop-node-name;
      leaf qos {
        tailf:info
          "Global QoS configuration subcommands";
        type empty;
      }
    }
    container qos {
      tailf:ncs-device-type "cli-ned";
      tailf:display-when "not(../../ncs:module) or ../../ncs:module[ncs:name='tailf-ned-cisco-ios']";
      tailf:info
        "Global QoS configuration subcommands";
      tailf:cli-incomplete-command;
      tailf:cli-incomplete-no;
      container dbl {
        tailf:info
          "Global DBL configuration";
        tailf:cli-display-separated;
        presence "true";
        container exceed-action {
          tailf:info
            "mark the packets when dbl limit is exceeded";
          leaf ecn {
            tailf:info
              "use explicit congestion notification";
            type empty;
          }
          leaf probability {
            tailf:info
              "specify marking probability";
            type uint8 {
              tailf:info
                "<0-100>;;probability";
              range "0..100";
            }
          }
        }
      }
      container map {
        tailf:info
          "QoS mapping tables";
        container dscp {
          tailf:info
            "Configure DSCP mapping tables";
          list dscp-to-tq-queue {
            tailf:cli-drop-node-name;
            tailf:cli-suppress-mode;
            tailf:cli-delete-when-empty;
            tailf:cli-compact-syntax;
            tailf:cli-sequence-commands;
            key "to tx-queue";
            leaf to {
              type enumeration {
                enum "to" {
                  tailf:info
                    "Map DSCP to";
                }
              }
            }
            leaf tx-queue {
              tailf:info
                "Map DSCP to transmit queue";
              tailf:cli-expose-key-name;
              type uint8 {
                tailf:info
                  "<1-4>;;Transmit queue number";
                range "1..4";
              }
            }
            uses dscp-value-0-7-grouping;
          }
          list dscp-to-cos {
            tailf:cli-drop-node-name;
            tailf:cli-suppress-mode;
            tailf:cli-delete-when-empty;
            tailf:cli-compact-syntax;
            tailf:cli-sequence-commands;
            key "to cos";
            leaf to {
              type enumeration {
                enum "to" {
                  tailf:info
                    "Map DSCP to";
                }
              }
            }
            leaf cos {
              tailf:info
                "Map DSCP to CoS";
              tailf:cli-expose-key-name;
              type uint8 {
                tailf:info
                  "<0-7>;;Mapped CoS value";
                range "0..7";
              }
            }
            uses dscp-value-0-7-grouping;
          }
        }
        container cos {
          tailf:info
            "Configure CoS mapping tables";
          list cos-to-dscp {
            tailf:cli-drop-node-name;
            tailf:cli-suppress-mode;
            tailf:cli-delete-when-empty;
            tailf:cli-compact-syntax;
            tailf:cli-sequence-commands;
            key "to dscp";
            leaf to {
              type enumeration {
                enum "to" {
                  tailf:info
                    "Map CoS to";
                }
              }
            }
            leaf dscp {
              tailf:info
                "Map CoS to DSCP";
              tailf:cli-expose-key-name;
              type uint8 {
                tailf:info
                  "<0-63>;;Mapped DSCP value";
                range "0..63";
              }
            }
            uses cos-value-0-7-grouping;
          }
        }
      }
      container account {
        tailf:info
          "Additional lengths to be accounted by QoS Features";
        container layer2 {
          tailf:info
            "Accounting Layer 2 headers";
          container encapsulation {
            tailf:info
              "Account Layer 2 Encapsulation when applying QoS features";
            leaf length {
              tailf:info
                "Layer2 Encapsulation length in bytes";
              type uint8 {
                tailf:info
                  "<0-64>;;Layer2 Encapsulation length in bytes";
                range "0..64";
              }
            }
          }
        }
      }
      container rewrite {
        tailf:info
          "QoS Rewrite Configuration";
        container ip {
          tailf:info
            "QoS IP Rewrite Configuration";
          leaf dscp {
            tailf:info
              "Rewrite DSCP bits in the ToS Byte of IP Header";
            tailf:cli-boolean-no;
            type boolean;
            default "true";
          }
        }
      }
      list aggregate-policer {
        tailf:info
          "Named aggregate policer";
        tailf:cli-suppress-mode;
        tailf:cli-delete-when-empty;
        tailf:cli-compact-syntax;
        tailf:cli-sequence-commands {
          tailf:cli-reset-all-siblings;
        }
        key "name";
        leaf name {
          type string {
            tailf:info
              "WORD;;Aggregate policer name";
          }
        }
        leaf rate {
          tailf:cli-drop-node-name;
          type uint64 {
            tailf:info
              "<32000-32000000000>;;Rate in bits per second (postfix k, m, g optional; decimal point allowed)";
            range "32000..32000000000";
          }
        }
        leaf xps {
          tailf:cli-drop-node-name;
          tailf:cli-optional-in-sequence;
          type enumeration {
            enum "pps" {
              tailf:info
                "Treat 'rate' value in packets-per-second";
            }
            enum "bps" {
              tailf:info
                "Treat 'rate' value in bytes-per-second";
            }
          }
        }
        leaf burst {
          tailf:cli-drop-node-name;
          type uint32 {
            tailf:info
              "<1000-512000000>;;Normal burst bytes";
            range "1000..512000000";
          }
        }
        leaf burst-type {
          tailf:cli-drop-node-name;
          tailf:cli-optional-in-sequence;
          type enumeration {
            enum "byte" {
              tailf:info
                "Treat 'burst' value as bytes";
            }
          }
        }
        container conform-action {
          tailf:info
            "action when rate is not exceeded";
          tailf:cli-optional-in-sequence;
          tailf:cli-flatten-container;
          tailf:cli-compact-syntax;
          choice action-choice {
            leaf drop {
              tailf:info
                "drop packet";
              type empty;
            }
            leaf transmit {
              tailf:info
                "transmit packet";
              type empty;
            }
          }
        }
        leaf exceed-action {
          tailf:info
            "action when rate is exceeded";
          tailf:cli-optional-in-sequence;
          type enumeration {
            enum "drop" {
              tailf:info
                "drop packet";
            }
            enum "policed-dscp-transmit" {
              tailf:info
                "change dscp per policed-dscp map and send it";
            }
            enum "transmit" {
              tailf:info
                "transmit packet";
            }
          }
        }
      }
    }
    container card {
      tailf:ncs-device-type "cli-ned";
      tailf:display-when "not(../../ncs:module) or ../../ncs:module[ncs:name='tailf-ned-cisco-ios']";
      tailf:info
        "Configure card type";
      list card-slot {
        tailf:cli-drop-node-name;
        tailf:cli-suppress-mode;
        tailf:cli-delete-when-empty;
        tailf:cli-compact-syntax;
        key "slot card-type";
        leaf slot {
          type uint8 {
            tailf:info
              "<1-3>;;Enter odd slot";
            range "1|3";
          }
        }
        leaf card-type {
          type enumeration {
            enum "4jacket-1" {
              tailf:info
                "create a 4jacket-1 cardtype";
            }
          }
        }
      }
      list card-slot-subslot {
        tailf:cli-drop-node-name;
        tailf:cli-suppress-mode;
        tailf:cli-delete-when-empty;
        tailf:cli-compact-syntax;
        tailf:cli-sequence-commands {
          tailf:cli-reset-all-siblings;
        }
        key "slot-subslot card-type";
        leaf slot-subslot {
          type string {
            tailf:info
              "<0-9>/<0-3>;;Enter slot/subslot (subslot 2 and 3 is for SPA only)";
            pattern '[0-9]/[0-3]';
          }
        }
        leaf card-type {
          type enumeration {
            enum "24rfchannel-spa-1" {
              tailf:info
                "create a Wideband DOCSIS SPA";
            }
            enum "2cable-dtcc" {
              tailf:info
                "Utility Card w/DTI (EightBells)";
            }
            enum "2cable-tccplus" {
              tailf:info
                "Utility Card";
            }
            enum "SPA-1XTENGE-XFP-V2" {
              tailf:info
                "create a 10GE SPA 1 PORT cardtype";
            }
            enum "SPA-2X1GE-V2" {
              tailf:info
                "create a GE SPA 2 PORT cardtype";
            }
            enum "SPA-5X1GE-V2" {
              tailf:info
                "create a GE SPA 5 PORT cardtype";
            }
            enum "SPA-8X1GE-V2" {
              tailf:info
                "create a GE SPA 8 PORT cardtype";
            }
            enum "SPA-DOCSIS-HD-V1" {
              tailf:info
                "create a High Density DOCSIS SPA";
            }
            enum "ubr10k-clc-3g60" {
              tailf:info
                "create a uBR10000 line card with MC3Gx60";
            }
            enum "ubr10k-clc-mc2020v" {
              tailf:info
                "create a uBR10000 line card with MC20x20";
            }
            enum "1gigethernet-1" {
              tailf:info
                "create a GE_1_PORT cardtype";
            }
            enum "1gigethernet-hh-1" {
              tailf:info
                "create a GE1H_1_PORT cardtype";
            }
            enum "cBR-CCAP-LC-40G" {
              tailf:info
                "create a cBR line card with CCAP-LC-40G";
            }
            enum "sup-pic-8x10g" {
              tailf:info
                "create a sup-pic 8x10G card";
            }
          }
        }
        leaf SPA-DOCSIS-HD-V1-port {
          when "../card-type = 'SPA-DOCSIS-HD-V1'" {
            tailf:xpath-root 3;
            tailf:dependency "../card-type";
          }
          tailf:cli-drop-node-name;
          type enumeration {
            enum "1x10GE" {
              tailf:info
                "using 1x10GE port";
            }
            enum "3x1GE" {
              tailf:info
                "using 3x1GE port";
            }
          }
        }
        leaf license {
          tailf:info
            "create a license for the line card";
          type string {
            tailf:info
              "WORD;;License string";
          }
        }
      }
      container type {
        tailf:info
          "Configure card type";
        list t1 {
          tailf:info
            "T1";
          tailf:cli-suppress-mode;
          tailf:cli-delete-when-empty;
          tailf:cli-compact-syntax;
          key "slot";
          leaf slot {
            type uint8;
          }
        }
        container t1-bay {
          tailf:cli-drop-node-name;
          list t1 {
            tailf:cli-suppress-mode;
            tailf:cli-delete-when-empty;
            tailf:cli-compact-syntax;
            key "slot bay";
            leaf slot {
              type uint8 {
                tailf:info
                  "<0-2>;;Card slot number (always 0 for 1800 series & 2801 routers)";
              }
            }
            leaf bay {
              type uint8 {
                tailf:info
                  "<0-3>;;WIC slot number (0:WIC, 1:Onboard for NM-HDV2)";
              }
            }
          }
        }
        list t3 {
          tailf:info
            "T3";
          tailf:cli-suppress-mode;
          tailf:cli-delete-when-empty;
          key "slot subslot";
          leaf slot {
            type uint8 {
              tailf:info
                "<0-6>;;Card slot number";
            }
          }
          leaf subslot {
            type uint8 {
              tailf:info
                "<0-6>;;Card subslot number";
            }
          }
        }
        list e1 {
          tailf:info
            "E1";
          tailf:cli-suppress-mode;
          tailf:cli-delete-when-empty;
          key "slot bay";
          leaf slot {
            type uint8 {
              tailf:info
                "<0-x>;;Card slot number";
            }
          }
          leaf bay {
            type uint8 {
              tailf:info
                "<0-x>;;WIC slot number";
            }
          }
        }
        list e3 {
          tailf:info
            "E3";
          tailf:cli-suppress-mode;
          tailf:cli-delete-when-empty;
          key "slot subslot";
          leaf slot {
            type uint8 {
              tailf:info
                "<0-6>;;Card slot number";
            }
          }
          leaf subslot {
            type uint8 {
              tailf:info
                "<0-6>;;Card subslot number";
            }
          }
        }
      }
    }
    container hw-module {
      tailf:ncs-device-type "cli-ned";
      tailf:display-when "not(../../ncs:module) or ../../ncs:module[ncs:name='tailf-ned-cisco-ios']";
      tailf:info
        "Slot/subslot/port level commands";
      list bay {
        tailf:info
          "Bay level commands";
        tailf:cli-suppress-mode;
        tailf:cli-delete-when-empty;
        tailf:cli-compact-syntax;
        tailf:cli-sequence-commands {
          tailf:cli-reset-siblings;
        }
        tailf:cli-incomplete-command;
        key "name";
        leaf name {
          type string {
            tailf:info
              "WORD;;<1-3>/<0-3>";
          }
        }
        leaf shutdown {
          tailf:info
            "Shutdown the target subslot";
          type empty;
        }
        choice power-choice {
          leaf powered {
            tailf:info
              "Hold the target subslot in reset";
            type empty;
          }
          leaf unpowered {
            tailf:info
              "Power-off the target subslot";
            type empty;
          }
        }
      }
      list ism {
        tailf:cli-suppress-mode;
        tailf:cli-delete-when-empty;
        key "name";
        leaf name {
          type string {
            tailf:info
              "<0-1>;;Service module slot number";
          }
        }
      }
      list slot {
        tailf:cli-suppress-mode;
        tailf:cli-delete-when-empty;
        key "name";
        leaf name {
          type uint32 {
            tailf:info
              "<1-6>;;slot number of line card";
          }
        }
        leaf process-max-time {
          tailf:info
            "Maximum time for process to run before voluntarily relinquishing processor";
          type uint16 {
            tailf:info
              "<20-200>;;The number of millisecs before voluntary suspend";
            range "20..200";
          }
        }
      }
      container module {
        tailf:info
          "Specify a linecard slot for the hw-module command";
        list module-list {
          tailf:cli-drop-node-name;
          tailf:cli-suppress-mode;
          tailf:cli-delete-when-empty;
          tailf:cli-compact-syntax;
          tailf:cli-incomplete-command;
          key "name port-group";
          leaf name {
            type uint8 {
              tailf:info
                "<1-7>;;module slot number";
            }
          }
          leaf port-group {
            tailf:info
              "onfigure port-group";
            tailf:cli-expose-key-name;
            type uint8 {
              tailf:info
                "<1-4>;;port-group number";
            }
          }
          leaf select {
            tailf:info
              "Select a port-group interface type";
            type enumeration {
              enum "gigabitethernet" {
                tailf:info
                  "Select this port-group's gigabit interfaces";
              }
              enum "tengigabitethernet" {
                tailf:info
                  "Select this port-group's 10G interfaces";
              }
            }
          }
        }
      }
    }
    container cable {
      tailf:ncs-device-type "cli-ned";
      tailf:display-when "not(../../ncs:module) or ../../ncs:module[ncs:name='tailf-ned-cisco-ios']";
      tailf:info
        "Global cable configuration";
      container profile {
        tailf:info
          "Global profile configuration";
        list mac-domain {
          tailf:info
            "Select a mac-domain common profile to configure";
          tailf:cli-mode-name "config-profile-md";
          key "name";
          leaf name {
            type string {
              tailf:info
                "WORD;;mac-domain common profile name";
            }
          }
          container cable {
            tailf:info
              "Cable interface subcommands";
            container dynamic-secret {
              tailf:info
                "Enable dynamic secret for CM config files";
              container reject {
                tailf:info
                  "Reject registration request from modems violating dynamic secret";
                tailf:cli-delete-when-empty;
                presence "true";
                leaf nocrypt {
                  tailf:info
                    "Do not encrypt modem config file name";
                  type empty;
                }
              }
            }
            container privacy {
              tailf:info
                "Cable Privacy";
              leaf bpi-plus-policy {
                tailf:info
                  "Privacy requires BPI+";
                type enumeration {
                  enum "capable-enforcement" {
                    tailf:info
                      "BPI+ required for all capable modems with BPI+ enabled (policy 1)";
                  }
                  enum "d11-enabled-enforcement" {
                    tailf:info
                      "BPI+ required for all D1.1 and later modems with BPI+ enabled (policy 2)";
                  }
                  enum "d11-enforcement" {
                    tailf:info
                      "BPI+ required for all D1.1 and later modems (policy 3)";
                  }
                  enum "total-enforcement" {
                    tailf:info
                      "BPI+ required for all modems (policy 4)";
                  }
                }
              }
            }
          }
        }
        list wideband-interface {
          tailf:info
            "Select a wideband interface common profile to configure";
          tailf:cli-mode-name "config-profile-wb";
          key "name";
          leaf name {
            type string {
              tailf:info
                "WORD;;wideband interface common profile name";
            }
          }
          container cable {
            tailf:info
              "Wideband-Cable interface subcommands";
            container downstream {
              tailf:info
                "Downstream parameter configuration";
              leaf attribute-mask {
                tailf:info
                  "Downstream channel provisioned Attribute Mask";
                type string {
                  tailf:info
                    "<0-FFFFFFFF>;;The attribute bitmap in hex";
                }
              }
            }
          }
        }
        list downstream {
          tailf:info
            "Select a downstream interface common profile to configure";
          tailf:cli-mode-name "config-profile-ds";
          key "name";
          leaf name {
            type string {
              tailf:info
                "WORD;;downstream interface common profile name";
            }
          }
          container cable {
            tailf:info
              "Integrated-Cable interface subcommands";
            container rf-bandwidth-percent {
              tailf:info
                "% of reserved RF channel bandwidth";
              leaf percent-value {
                tailf:cli-drop-node-name;
                type uint8 {
                  tailf:info
                    "<1-100>;;% bandwidth";
                  range "1..100";
                }
              }
            }
            leaf attribute-mask {
              tailf:info
                "Downstream channel provisioned Attribute Mask";
              type string {
                tailf:info
                  "<0-FFFFFFFF>;;The attribute bitmap in hex";
              }
            }
          }
        }
        list service-group {
          tailf:info
            "Create fiber-node service group profile";
          tailf:cli-mode-name "config-profile-sg";
          key "name";
          leaf name {
            type string {
              tailf:info
                "WORD;;fiber-node service group profile name";
            }
          }
          container cable {
            tailf:info
              "cable subcommand";
            leaf bundle {
              tailf:info
                "Bundle number for bundling of cable interfaces";
              type uint8 {
                tailf:info
                  "<1-255>;;Bundle number";
                range "1..255";
              }
            }
          }
          list mac-domain {
            tailf:info
              "Cable Mac Domain";
            tailf:cli-mode-name "config-profile-sg-md";
            tailf:cli-sequence-commands;
            key "id";
            leaf id {
              tailf:cli-incomplete-command;
              type uint8 {
                tailf:info
                  "<0-15>;;mac-domain id";
                range "0..15";
              }
            }
            leaf profile {
              tailf:info
                "mac-domain profile";
              tailf:cli-hide-in-submode;
              tailf:cli-full-command;
              tailf:non-strict-leafref {
                path "../../../mac-domain/name";
              }
              type string {
                tailf:info
                  "WORD;;mac-domain profile name";
              }
            }
            container downstream {
              tailf:cli-break-sequence-commands;
              tailf:info
                "Add a ds service group channel to a MD";
              tailf:cli-compact-syntax;
              tailf:cli-sequence-commands;
              list sg-channel {
                tailf:info
                  "ds service group channel";
                tailf:cli-suppress-mode;
                tailf:cli-delete-when-empty;
                tailf:cli-compact-syntax;
                tailf:cli-sequence-commands;
                key "profile";
                leaf profile {
                  tailf:info
                    "IC interface profile";
                  tailf:cli-expose-key-name;
                  tailf:cli-suppress-range;
                  type string {
                    tailf:info
                      "WORD;;IC interface profile name";
                  }
                }
                leaf-list id {
                  tailf:cli-drop-node-name;
                  tailf:cli-prefix-key;
                  tailf:cli-range-list-syntax;
                  tailf:cli-incomplete-command;
                  tailf:cli-incomplete-no;
                  type uint8 {
                    tailf:info
                      "<grouplist>;;List of Ranges for sg-channels <0-254>";
                    range "0..254";
                  }
                }
                leaf upstream {
                  tailf:info
                    "Upstream sg-channels serving these downstream sg-channels";
                  type string {
                    tailf:info
                      "<grouplist>;;List of Ranges for upstream sg-channels <0-7>";
                  }
                }
              }
            }
            list upstream {
              tailf:info
                "Add a us service group channel to a MD";
              tailf:cli-suppress-mode;
              tailf:cli-delete-when-empty;
              tailf:cli-incomplete-command;
              key "id";
              leaf id {
                type uint16 {
                  tailf:info
                    "<0-15>;;US channel index in MD";
                  range "0..15";
                }
              }
              leaf sg-channel {
                tailf:info
                  "us service group channel";
                type uint8 {
                  tailf:info
                    "<0-254>;;US sg-channel index";
                  range "0..254";
                }
              }
            }
            list us-bonding-group {
              tailf:info
                "Configure upstream bonding group";
              tailf:cli-mode-name "config-profile-sg-md-usb";
              key "id";
              leaf id {
                type uint16 {
                  tailf:info
                    "<1-65535>;;bonding group id";
                  range "1..65535";
                }
              }
              container admission-control {
                tailf:info
                  "Configure Cable Admission Control";
                leaf max-reserved-bandwidth {
                  tailf:info
                    "Configure maximum AC reserved bandwidth for this bonding group.";
                  type uint32 {
                    tailf:info
                      "NUM;;Maximum AC reserved bandwidth Value in kbps";
                  }
                }
              }
              list upstream {
                tailf:info
                  "Add an upstream to this bonding group";
                tailf:cli-suppress-mode;
                tailf:cli-delete-when-empty;
                key "id";
                leaf id {
                  type uint8 {
                    tailf:info
                      "<0-15>;;upstream to add";
                    range "0..15";
                  }
                }
              }
            }
          }
          list wideband-interface {
            tailf:info
              "Downstream bonding group";
            tailf:cli-mode-name "config-profile-sg-bg";
            key "id";
            leaf id {
              type uint8 {
                tailf:info
                  "<0-63>;;downstream bonding group id";
                range "0..63";
              }
            }
            leaf profile {
              tailf:info
                "wideband interface profile";
              tailf:cli-hide-in-submode;
              tailf:non-strict-leafref {
                path "../../../wideband-interface/name";
              }
              type string {
                tailf:info
                  "WORD;;wideband interface profile name";
              }
            }
            container downstream {
              tailf:info
                "Add a ds service group channel to a BG";
              list sg-channel {
                tailf:info
                  "ds service group channel";
                tailf:cli-suppress-mode;
                tailf:cli-delete-when-empty;
                tailf:cli-incomplete-command;
                key "id";
                leaf id {
                  tailf:cli-multi-value;
                  tailf:cli-suppress-range;
                  type string {
                    tailf:info
                      "<grouplist>;;List of Ranges for sg-channels <0-254>";
                  }
                }
                leaf rf-bandwidth-percent {
                  tailf:info
                    "ds service group channel";
                  type uint8 {
                    tailf:info
                      "<1-100>;;bandwidth";
                    range "1..100";
                  }
                }
              }
            }
          }
        }
      }
      container downstream {
        tailf:info
          "configure at chassis level";
        list freq-profile {
          tailf:info
            "configure chassis level freq profile";
          tailf:cli-mode-name "config-freq-prof";
          key "name";
          leaf name {
            type string {
              tailf:info
                "WORD;;RFGW Frequency profile ID or Name";
            }
          }
          list lane {
            tailf:info
              "lane configurations";
            tailf:cli-mode-name "config-freq-prof-lane";
            tailf:cli-incomplete-command;
            key "id";
            leaf id {
              type uint8 {
                tailf:info
                  "<1-4>;;lane id ";
                range "1..4";
              }
            }
            leaf start-freq {
              tailf:info
                "starting freq keyword for the lane";
              tailf:cli-hide-in-submode;
              type uint32 {
                tailf:info
                  "<48000000-995000000>;;lane start frequency";
                range "48000000..995000000";
              }
            }
            list block {
              tailf:info
                "block configurations";
              tailf:cli-suppress-mode;
              tailf:cli-delete-when-empty;
              tailf:cli-incomplete-command;
              key "id";
              leaf id {
                type uint8 {
                  tailf:info
                    "<1-4>;;block id ";
                  range "1..4";
                }
              }
              leaf start-freq {
                tailf:info
                  "starting freq keyword for the block";
                type uint32 {
                  tailf:info
                    "<48000000-995000000>;;block start frequency";
                }
              }
            }
          }
        }
        list rf-profile {
          tailf:info
            "configure chassis level rf profile";
          tailf:cli-mode-name "config-rf-prof";
          key "name";
          leaf name {
            type string {
              tailf:info
                "WORD;;RFGW RF profile ID or Name";
            }
          }
          container cable {
            tailf:info
              "cable keyword under rf profile config mode";
            container downstream {
              tailf:info
                "downstream configurations for the rf profile";
              leaf annex {
                tailf:info
                  "MPEG framing format, annex A|B|C";
                tailf:cli-full-command;
                type enumeration {
                  enum "A" {
                    tailf:info
                      "annex A, European Standard";
                  }
                  enum "B" {
                    tailf:info
                      "annex B, North American Standard";
                  }
                  enum "C" {
                    tailf:info
                      "annex C, Japan Standard";
                  }
                }
              }
              leaf modulation {
                tailf:info
                  "set QAM modulation format";
                tailf:cli-full-command;
                type enumeration {
                  enum "256" {
                    tailf:info
                      "256QAM";
                  }
                  enum "64" {
                    tailf:info
                      "64QAM ";
                  }
                }
              }
              container interleaver-depth {
                tailf:info
                  "Interleaver Depth, allows 2 options";
                tailf:cli-compact-syntax;
                tailf:cli-sequence-commands {
                  tailf:cli-reset-siblings;
                }
                leaf option1 {
                  tailf:info
                    "Interleaver Depth option 1";
                  tailf:cli-incomplete-command;
                  type cable-downstream-interleaver-depth-option;
                }
                leaf option2 {
                  tailf:info
                    "Interleaver Depth option 2";
                  type cable-downstream-interleaver-depth-option;
                }
              }
              leaf symbol-rate {
                tailf:info
                  "set the symbol rate";
                tailf:cli-full-command;
                type uint32 {
                  tailf:info
                    "<3500000-7000000>;;symbols per second";
                }
              }
            }
          }
        }
        list qam-profile {
          tailf:info
            "configure chassis level qam profile";
          tailf:cli-mode-name "config-qam-prof";
          key "name";
          leaf name {
            type string {
              tailf:info
                "<0-31>;;Qam Profile ID (<0-3> system defined, <4-31> user defined)";
            }
          }
          leaf annex {
            tailf:info
              "MPEG framing format, annex A|B|C";
            type enumeration {
              enum "A" {
                tailf:info
                  "annex A, European Standard";
              }
              enum "B" {
                tailf:info
                  "annex B, North American Standard";
              }
              enum "C" {
                tailf:info
                  "annex C, Japan Standard";
              }
            }
          }
          leaf modulation {
            tailf:info
              "set QAM modulation format";
            type enumeration {
              enum "256" {
                tailf:info
                  "256QAM";
              }
              enum "64" {
                tailf:info
                  "64QAM ";
              }
            }
          }
          leaf interleaver-depth {
            tailf:info
              "Interleaver Depth";
            type enumeration {
              enum "I12-J17" {
                tailf:info
                  "INTERLEAVER-I-12-J-17 for Annex A or C";
              }
              enum "I128-J1" {
                tailf:info
                  "INTERLEAVER-I-128-J-1 for Annex B";
              }
              enum "I128-J2" {
                tailf:info
                  "INTERLEAVER-I-128-J-2 for Annex B";
              }
              enum "I128-J3" {
                tailf:info
                  "INTERLEAVER-I-128-J-3 for Annex B";
              }
              enum "I128-J4" {
                tailf:info
                  "INTERLEAVER-I-128-J-4 for Annex B";
              }
              enum "I128-J5" {
                tailf:info
                  "INTERLEAVER-I-128-J-5 for Annex B";
              }
              enum "I128-J6" {
                tailf:info
                  "INTERLEAVER-I-128-J-6 for Annex B";
              }
              enum "I128-J7" {
                tailf:info
                  "INTERLEAVER-I-128-J-7 for Annex B";
              }
              enum "I128-J8" {
                tailf:info
                  "INTERLEAVER-I-128-J-8 for Annex B";
              }
              enum "I16-J8" {
                tailf:info
                  "INTERLEAVER-I-16-J-8 for Annex B ";
              }
              enum "I32-J4" {
                tailf:info
                  "INTERLEAVER-I-32-J-4 for Annex B ";
              }
              enum "I64-J2" {
                tailf:info
                  "INTERLEAVER-I-64-J-2 for Annex B ";
              }
              enum "I8-J16" {
                tailf:info
                  "INTERLEAVER-I-8-J-16 for Annex B ";
              }
            }
          }
          leaf symbol-rate {
            tailf:info
              "set the symbol rate";
            type uint32 {
              tailf:info
                "<NUM>;;set symbol rate value in kilo-symbol/sec";
            }
          }
          leaf spectrum-inversion {
            tailf:info
              "set spectrum inversion";
            type enumeration {
              enum "off" {
                tailf:info
                  "spectrum-inversion off ";
              }
              enum "on" {
                tailf:info
                  "spectrum-inversion on";
              }
            }
          }
          uses description-grouping;
        }
        list controller-profile {
          tailf:info
            "configure downstream controller profile mode";
          tailf:cli-mode-name "config-controller-profile";
          key "id";
          leaf id {
            type uint8 {
              tailf:info
                "<0-255>;;Downstream controller-profile ID";
            }
          }
          leaf shutdown {
            tailf:info
              "Shutdown RF Port";
            type empty;
          }
          uses description-grouping;
          leaf max-carrier {
            tailf:info
              "Max Carrier of a RF Port";
            type uint8 {
              tailf:info
                "<1-158>;;RF Port Max Carrier Value";
              range "1..158";
            }
          }
          leaf base-channel-power {
            tailf:info
              "set base channel power level";
            type uint8 {
              tailf:info
                "<35-44>;;Base Channel Power Value in dBmV";
            }
          }
          container rf-chan {
            tailf:info
              "Configure RF Channel";
            list rf-chan {
              tailf:cli-drop-node-name;
              tailf:cli-mode-name "config-prof-rf-chan";
              key "start";
              leaf start {
                type uint8 {
                  tailf:info
                    "<0-162>;;Starting Qam ID";
                }
              }
              leaf end {
                tailf:cli-drop-node-name;
                tailf:cli-hide-in-submode;
                type uint8 {
                  tailf:info
                    "<1-162>;;Ending QAM ID";
                  range "1..162";
                }
              }
              uses controller-integrated-cable-rf-chan-grouping;
            }
          }
        }
      }
      container upstream {
        tailf:info
          "global upstream parameters";
        container rate-adapt {
          tailf:info
            "rate adapt";
          tailf:cli-compact-syntax;
          leaf priority {
            tailf:info
              "Configure priority to enable rate-adapt";
            type uint8 {
              tailf:info
                "<0-7>;;priority at or above enables rate-adapt.";
              range "0..7";
            }
          }
          leaf rate {
            tailf:info
              "Configure rate to enable rate-adapt";
            type uint32 {
              tailf:info
                "<0-30000000>;;rate at or above enables rate-adapt.";
              range "0..30000000";
            }
          }
          leaf local {
            tailf:info
              "Enable rate-adapt locally per upstream";
            type empty;
          }
        }
        list controller-profile {
          tailf:info
            "configure upstream controller profile mode";
          tailf:cli-mode-name "config-controller-profile";
          key "name";
          leaf name {
            type uint16 {
              tailf:info
                "<0-511>;;upstream controller-profile number";
            }
          }
          uses description-grouping;
          uses us-channel-grouping;
        }
      }
      list linecard {
        tailf:info
          "Linecard related configuration";
        tailf:cli-suppress-mode;
        tailf:cli-delete-when-empty;
        tailf:cli-compact-syntax;
        tailf:cli-sequence-commands;
        tailf:cli-incomplete-command;
        key "id";
        leaf id {
          type uint8 {
            tailf:info
              "<3-12>;;linecard slot number";
            range "3..12";
          }
        }
        leaf encryption {
          tailf:info
            "encryption options are pkey or dvb or or pme or clear";
          type enumeration {
            enum "clear" {
              tailf:info
                "Encryption type is CLEAR";
            }
            enum "dual-crypt" {
              tailf:info
                "Encryption type is dual-crypt";
            }
            enum "dvb" {
              tailf:info
                "Encryption type is DVB";
            }
            enum "pkey" {
              tailf:info
                "Encryption type is PowerKEY";
            }
            enum "pme" {
              tailf:info
                "Encryption type is PME";
            }
          }
        }
        leaf scrambler {
          tailf:info
            "scrambler options are des or csa or none";
          type enumeration {
            enum "none" {
              tailf:info
                "Scrambling algorithm is NONE";
            }
            enum "csa" {
              tailf:info
                "Scrambling algorithm is CSA";
            }
            enum "des" {
              tailf:info
                "Scrambling algorithm is DES";
            }
          }
        }
      }
      container admission-control {
        tailf:info
          "Configure Cable Admission Control";
        container preempt {
          tailf:info
            "Reason for preemption";
          leaf priority-voice {
            tailf:info
              "Priority Voice call can preempt normal";
            tailf:cli-show-no;
            type empty;
          }
        }
      }
      container flap-list {
        tailf:info
          "Cable flap-list configuration";
        leaf aging {
          tailf:info
            "Flap-list aging";
          type uint32 {
            tailf:info
              "<1-86400>;;Maximum number of minutes the cable modem is kept in the flap-list";
            range "1..86400";
          }
        }
      }
      container source-verify {
        tailf:info
          "Source verify";
        container leasequery-filter {
          tailf:info
            "Source verify Lease query filter";
          container downstream {
            tailf:info
              "Source verify Lease query filter for downstream pkts";
            tailf:cli-compact-syntax;
            tailf:cli-sequence-commands;
            leaf threshold {
              tailf:cli-drop-node-name;
              tailf:cli-incomplete-command;
              type uint8 {
                tailf:info
                  "<0-255>;;Number of lease queries for unknown sid";
                range "0..255";
              }
            }
            leaf interval {
              tailf:cli-drop-node-name;
              type uint8 {
                tailf:info
                  "<1-10>;;size of time window in seconds";
                range "1..10";
              }
            }
          }
        }
      }
      container modem {
        tailf:info
          "Modem polling using SNMP query";
        container remote-query {
          tailf:info
            "Modem polling using SNMP query";
          container gather {
            tailf:cli-drop-node-name;
            tailf:cli-compact-syntax;
            tailf:cli-sequence-commands;
            leaf polling-interval {
              tailf:cli-drop-node-name;
              tailf:cli-incomplete-command;
              type uint32 {
                tailf:info
                  "<1-86400>;;Periodic polling interval in seconds";
                range "1..86400";
              }
            }
            leaf community-string {
              tailf:cli-drop-node-name;
              type string {
                tailf:info
                  "WORD;;Community string ";
              }
            }
          }
          leaf src-ip {
            tailf:info
              "source IP address";
            type inet:ipv4-address {
              tailf:info
                "A.B.C.D;;Source IP addr";
            }
          }
        }
        leaf max-cpe {
          tailf:info
            "Max CPE override";
          type union {
            type uint8 {
              tailf:info
                "<1-255>;;Number";
            }
            type enumeration {
              enum "unlimited" {
                tailf:info
                  "Max CPE not enforced";
              }
            }
          }
        }
        leaf v6-max-cpe-prefix {
          tailf:info
            "Max CPE override";
          type uint16 {
            tailf:info
              "<0-1023>;;Number";
            range "0..1023";
          }
        }
        list vendor {
          tailf:info
            "Cable modem vendor information";
          tailf:cli-suppress-mode;
          tailf:cli-delete-when-empty;
          key "oui";
          leaf oui {
            type string {
              tailf:info
                "WORD;;OUI of the vendor in the format xx.xx.xx or xx:xx:xx";
            }
          }
          leaf vendor-name {
            tailf:cli-drop-node-name;
            type string {
              tailf:info
                "WORD;Vendor name";
            }
          }
        }
      }
      container modulation-profile {
        tailf:info
          "Modulation profile";
        list modulation-profile-list {
          tailf:cli-drop-node-name;
          tailf:cli-suppress-mode;
          tailf:cli-delete-when-empty;
          tailf:cli-incomplete-command;
          key "profile";
          leaf profile {
            type string {
              tailf:info
                "WORD;;Modulation Profile Group";
            }
          }
          container atdma {
            tailf:info
              "DOCSIS2.0 atdma mode";
            uses cable-modulation-profile-list-grouping;
          }
          container tdma {
            tailf:info
              "DOCSIS1.x tdma mode";
            uses cable-modulation-profile-list-grouping;
          }
          container mixed {
            tailf:info
              "DOCSIS1.x/2.0 tdma-atdma mixed mode";
            uses cable-modulation-profile-list-grouping;
          }
          uses cable-modulation-profile-list-grouping;
        }
      }
      list tag {
        tailf:info
          "cable tag";
        tailf:cli-mode-name "config-cmts-tag";
        key "id";
        leaf id {
          type uint16 {
            tailf:info
              "<1-1000>;;The id of the tag";
            range "1..1000";
          }
        }
        leaf name {
          tailf:info
            "Name of the tag";
          type string {
            tailf:info
              "WORD;;Globally unique name string of the tag";
          }
        }
        leaf service-type-id {
          tailf:info
            "Set the match rule for service type id";
          type string {
            tailf:info
              "WORD;;Service Type ID";
          }
        }
        leaf docsis-version {
          tailf:info
            "Set the match rule for DOCSIS version";
          type enumeration {
            enum "docsis10" {
              tailf:info
                "Match docsis 1.0 modems";
            }
            enum "docsis11" {
              tailf:info
                "Match docsis 1.1 modems";
            }
            enum "docsis20" {
              tailf:info
                "Match docsis 2.0 modems";
            }
            enum "docsis30" {
              tailf:info
                "Match docsis 3.0 modems";
            }
          }
        }
        leaf service-class {
          tailf:info
            "Set the match rule for service class name";
          type string {
            tailf:info
              "WORD;;Service class name";
          }
        }
      }
      container service {
        tailf:info
          "Service flow/class setting";
        list class {
          tailf:info
            "Service class settings";
          tailf:cli-suppress-mode;
          tailf:cli-delete-when-empty;
          tailf:cli-incomplete-command;
          key "class-index";
          leaf class-index {
            type uint16 {
              tailf:info
                "<1-1023>;;Class Index";
              range "1..1023";
            }
          }
          leaf name {
            tailf:cli-full-command;
            type string {
              tailf:info
                "WORD;;The ascii string identifier for this Service Class";
            }
          }
          choice direction-choice {
            leaf downstream {
              tailf:info
                "Service Class is downstream";
              tailf:cli-full-command;
              tailf:cli-diff-dependency "../name" {
                tailf:xpath-root 3;
              }
              tailf:meta-data "suppress-delete-error-invalid";
              type empty;
            }
            leaf upstream {
              tailf:info
                "Service Class is upstream";
              tailf:cli-full-command;
              tailf:cli-diff-dependency "../name" {
                tailf:xpath-root 3;
              }
              tailf:meta-data "suppress-delete-error-invalid";
              type empty;
            }
          }
          leaf peak-rate {
            tailf:info
              "Peak Rate within maximum traffic burst";
            tailf:cli-diff-dependency "../name" {
              tailf:xpath-root 3;
            }
            type uint32 {
              tailf:info
                "<0-4294967295>;;Enter Peak Rate (bps";
            }
          }
          leaf max-concat-burst {
            tailf:info
              "Max Concat Burst";
            tailf:cli-diff-dependency "../name" {
              tailf:xpath-root 3;
            }
            type uint16 {
              tailf:info
                "<0-65535>;;Enter Max Concat Burst (bytes)";
            }
          }
          container tos-overwrite {
            tailf:info
              "Overwrite TOS byte by setting mask bits to value";
            tailf:cli-compact-syntax;
            tailf:cli-sequence-commands;
            tailf:cli-diff-dependency "../name" {
              tailf:xpath-root 3;
            }
            leaf and-mask {
              tailf:cli-drop-node-name;
              tailf:cli-incomplete-command;
              type string {
                tailf:info
                  "<0x0-0xFF>;,TOS-overwrite-mask-and byte in hex";
              }
            }
            leaf or-mask {
              tailf:cli-drop-node-name;
              type string {
                tailf:info
                  "<0x0-0xFF>;;TOS-overwrite-mask-or byte in hex";
              }
            }
          }
          leaf req-trans-policy {
            tailf:info
              "Request Transmission Policy Bit Field";
            tailf:cli-full-command;
            tailf:cli-diff-dependency "../name" {
              tailf:xpath-root 3;
            }
            type string {
              tailf:info
                "<0x0-0xFFFFFFFF>;;Enter Request Transmission Policy Bit Field in hex";
            }
          }
          leaf max-rate {
            tailf:info
              "Max Rate";
            tailf:cli-diff-dependency "../name" {
              tailf:xpath-root 3;
            }
            type uint32 {
              tailf:info
                "<0-4294967295>;;Enter Max Rate (bps)";
            }
          }
          leaf max-burst {
            tailf:info
              "Max Tx Burst";
            tailf:cli-diff-dependency "../name" {
              tailf:xpath-root 3;
            }
            type uint32 {
              tailf:info
                "<1522-4294967295>;;Enter Max Tx Burst (bytes)";
              range "1522..4294967295";
            }
          }
          leaf min-rate {
            tailf:info
              "Min Rate";
            tailf:cli-diff-dependency "../name" {
              tailf:xpath-root 3;
            }
            type uint32 {
              tailf:info
                "<0-4294967295>;;Enter Min Resv Rate (bps)";
            }
          }
          leaf min-packet-size {
            tailf:info
              "Min Packet Size for Reserved Rate";
            tailf:cli-diff-dependency "../name" {
              tailf:xpath-root 3;
            }
            type uint16 {
              tailf:info
                "<0-65535>;;Enter Min Packet Size for Reserved Rate(bytes)";
            }
          }
          leaf max-latency {
            tailf:info
              "Max Latency";
            tailf:cli-diff-dependency "../name" {
              tailf:xpath-root 3;
            }
            type uint32 {
              tailf:info
                "<0-4294967295>;;Enter Max Latency(usecs)";
            }
          }
          leaf req-attr-mask {
            tailf:info
              "Required Attribute Mask";
            tailf:cli-full-command;
            tailf:cli-diff-dependency "../name" {
              tailf:xpath-root 3;
            }
            type string {
              tailf:info
                "<0-FFFFFFFF>;;The attribute bitmap in hex";
            }
          }
          leaf admission-timeout {
            tailf:info
              "Admitted QoS Param Set Timeout";
            tailf:cli-diff-dependency "../name" {
              tailf:xpath-root 3;
            }
            type uint16 {
              tailf:info
                "<0-65535>;;Enter Admitted QoS Param Set Timeout";
            }
          }
          leaf activity-timeout {
            tailf:info
              "QoS Param Set Activity Timeout";
            tailf:cli-diff-dependency "../name" {
              tailf:xpath-root 3;
            }
            type uint16 {
              tailf:info
                "<0-65535>;;Enter QoS Param Set Activity Timeout";
            }
          }
          leaf priority {
            tailf:info
              "Priority";
            tailf:cli-diff-dependency "../name" {
              tailf:xpath-root 3;
            }
            type uint8 {
              tailf:info
                "<0-7>;;Enter Priority";
              range "0..7";
            }
          }
          leaf sched-type {
            tailf:info
              "Service Class Schedule Type";
            tailf:cli-diff-dependency "../name" {
              tailf:xpath-root 3;
            }
            type enumeration {
              enum "2" {
                tailf:info
                  "Best Effort Schedule Type";
              }
              enum "3" {
                tailf:info
                  "Non Real-Time Polling Service Schedule Type";
              }
              enum "4" {
                tailf:info
                  "Real-Time Polling Service Schedule Type";
              }
              enum "5" {
                tailf:info
                  "Unsolicited Grant Service with Activity Detection Schedule Type";
              }
              enum "6" {
                tailf:info
                  "Unsolicited Grant Service Schedule Type";
              }
            }
          }
        }
        list type {
          tailf:info
            "service type";
          tailf:cli-suppress-mode;
          tailf:cli-delete-when-empty;
          tailf:cli-incomplete-command;
          key "id";
          leaf id {
            tailf:cli-suppress-range;
            type string {
              tailf:info
                "WORD;;Service Type Id";
            }
          }
          leaf ds-frequency {
            tailf:info
              "downstream frequency";
            type uint32 {
              tailf:info
                "<55000000-858000000>;;Frequency - Hz";
              range "55000000..858000000";
            }
          }
        }
        container attribute {
          tailf:info
            "Service attribute settings";
          container ds-bonded {
            tailf:info
              "Downstream Bonding Settings";
            container downstream-type {
              tailf:info
                "Bonding downstream-type settings";
              container bonding-enabled {
                tailf:info
                  "Channel Bonding only supported on Bonding-capable interfaces";
                tailf:cli-delete-when-empty;
                presence "true";
                leaf enforce {
                  tailf:info
                    "Enforce Bonding-capable interface selection";
                  type empty;
                }
              }
            }
          }
          container withhold-tlvs {
            tailf:info
              "Withhold D3.0 TLVs from pre-D3.0 modems";
            leaf peak-rate {
              tailf:info
                "Peak Traffic Rate TLV 24/25.27";
              type empty;
            }
          }
        }
        container flow {
          tailf:info
            "Service flow settings";
          leaf activity-timeout {
            tailf:info
              "Default value for Service flow activity timeout";
            type uint16 {
              tailf:info
                "<0-65535>;;Seconds";
            }
          }
        }
      }
      container qos {
        tailf:info
          "Cable Quality of Service";
        container permission {
          tailf:info
            "Permission for Creating Cable Quality of Service Profile";
          leaf create {
            tailf:info
              "Allow create by management";
            tailf:cli-show-no;
            type empty;
          }
          leaf update {
            tailf:info
              "Allow update by management";
            tailf:cli-show-no;
            type empty;
          }
          leaf modems {
            tailf:info
              "Allow create by modems";
            tailf:cli-show-no;
            type empty;
          }
        }
      }
      container multicast {
        tailf:info
          "Cable Multicast";
        container mdf-disable {
          tailf:info
            "Disable Multicast DSID Forwarding mode";
          leaf WB-Incapable-CM {
            tailf:info
              "Wideband Incapable modems only";
            type empty;
          }
        }
      }
      container filter {
        tailf:info
          "CMTS packet filter settings";
        list group {
          tailf:info
            "CMTS packet filter group settings";
          tailf:cli-suppress-mode;
          tailf:cli-delete-when-empty;
          tailf:cli-compact-syntax;
          key "group-id";
          leaf group-id {
            type uint8 {
              tailf:info
                "<1-254>;;Group ID";
              range "1..254";
            }
          }
          list index {
            tailf:info
              "CMTS packet filter index settings";
            tailf:cli-suppress-mode;
            tailf:cli-delete-when-empty;
            key "index-num";
            leaf index-num {
              type uint8 {
                tailf:info
                  "<1-255>;;Filter Index";
              }
            }
            leaf src-ip {
              tailf:info
                "IP source address";
              type inet:ipv4-address {
                tailf:info
                  "A.B.C.D;;Enter IP source address";
              }
            }
            leaf src-mask {
              tailf:info
                "IP source address mask";
              type inet:ipv4-address {
                tailf:info
                  "A.B.C.D;;Enter IP source address mask";
              }
            }
            leaf dest-ip {
              tailf:info
                "IP destination address";
              type inet:ipv4-address {
                tailf:info
                  "A.B.C.D;;Enter IP destination address";
              }
            }
            leaf dest-mask {
              tailf:info
                "IP destination address mask";
              type inet:ipv4-address {
                tailf:info
                  "A.B.C.D;;Enter IP destination address mask";
              }
            }
            leaf v6-src-address {
              tailf:info
                "IPv6 source address";
              type inet:ipv6-address {
                tailf:info
                  "X:X:X:X::X;;Enter IPv6 source address";
              }
            }
            leaf v6-src-pfxlen {
              tailf:info
                "IPv6 source address prefix length";
              type uint8 {
                tailf:info
                  "<0-128>;;Enter Source Address Prefix Length";
                range "0..128";
              }
            }
            leaf v6-dest-address {
              tailf:info
                "IPv6 destination address";
              type inet:ipv6-address {
                tailf:info
                  "X:X:X:X::X;;Enter IPv6 destination address";
              }
            }
            leaf v6-dest-pfxlen {
              tailf:info
                "IPv6 destination address prefix length";
              type uint8 {
                tailf:info
                  "<0-128>;;Enter Destination Address Prefix Length";
                range "0..128";
              }
            }
            leaf v6-flow-label {
              tailf:info
                "IPv6 flow label";
              type uint32 {
                tailf:info
                  "<0-1048575>;;Enter IPv6 flow label";
                range "0..1048575";
              }
            }
            leaf ip-proto {
              tailf:info
                "IP protocol";
              type uint16 {
                tailf:info
                  "<0-256>;;Enter IP protocol type";
                range "0..256";
              }
            }
            container ip-tos {
              tailf:info
                "IP TOS byte settings";
              tailf:cli-compact-syntax;
              tailf:cli-sequence-commands;
              leaf tos-mask {
                tailf:cli-drop-node-name;
                tailf:cli-incomplete-command;
                type string {
                  tailf:info
                    "<0x0-0xFF>;;Enter mask against TOS value, byte in hex";
                }
              }
              leaf tos-value {
                tailf:cli-drop-node-name;
                type string {
                  tailf:info
                    "<0x0-0xFF>;;Enter TOS value, byte in hex";
                }
              }
            }
            leaf src-port {
              tailf:info
                "TCP/UDP source port";
              type uint16 {
                tailf:info
                  "<0-65535>;;Enter TCP/UDP Source Port";
              }
            }
            leaf dest-port {
              tailf:info
                "TCP/UDP destination port";
              type uint16 {
                tailf:info
                  "<0-65535>;;Enter TCP/UDP Destination Port";
              }
            }
            leaf ip-version {
              tailf:info
                "IP version of filter";
              type enumeration {
                enum "IPv4" {
                  tailf:info
                    "Filter is for IPv4 (default)";
                }
                enum "IPv6" {
                  tailf:info
                    "Filter is for IPv6";
                }
              }
              default "IPv4";
            }
            container tcp-flags {
              tailf:info
                "TCP flags settings";
              tailf:cli-compact-syntax;
              tailf:cli-sequence-commands;
              leaf flags-mask {
                tailf:cli-drop-node-name;
                tailf:cli-incomplete-command;
                type string {
                  tailf:info
                    "<0x0-0x3F;;Enter TCP Flags Mask in Hex";
                }
              }
              leaf flags-value {
                tailf:cli-drop-node-name;
                type string {
                  tailf:info
                    "<0x0-0x3F>;;Enter TCP Flags Value in Hex";
                }
              }
            }
            leaf match-action {
              tailf:info
                "Filter Match action processing";
              type enumeration {
                enum "accept" {
                  tailf:info
                    "Accept Packet on Match";
                }
                enum "drop" {
                  tailf:info
                    "Drop Packet on Match";
                }
              }
            }
            leaf status {
              tailf:info
                "Status of filter";
              type enumeration {
                enum "active" {
                  tailf:info
                    "Filter is active";
                }
                enum "inactive" {
                  tailf:info
                    "Filter is inactive";
                }
              }
              default "active";
            }
          }
        }
      }
      container submgmt {
        tailf:info
          "CMTS Subscriber Management Objects";
        container default {
          tailf:info
            "Defaults";
          container filter-group {
            tailf:info
              "Configure Filter Group";
            container cm {
              tailf:info
                "CM Group Defaults";
              uses cable-submgmt-default-filter-group-grouping;
            }
            container cpe {
              tailf:info
                "CPE Group Defaults";
              uses cable-submgmt-default-filter-group-grouping;
            }
            container mta {
              tailf:info
                "MTA Group Defaults";
              uses cable-submgmt-default-filter-group-grouping;
            }
            container stb {
              tailf:info
                "STB Group Defaults";
              uses cable-submgmt-default-filter-group-grouping;
            }
            container ps {
              tailf:info
                "PS Group Defaults";
              uses cable-submgmt-default-filter-group-grouping;
            }
          }
          leaf active {
            tailf:info
              "CPE Control for Subscriber Management Filtering";
            type empty;
          }
        }
      }
      container logging {
        tailf:info
          "Logs specific cable messages";
        container badipsource {
          tailf:info
            "cable BADIPSOURCE messages";
          tailf:cli-delete-when-empty;
          presence "true";
          leaf buffer-size {
            tailf:cli-drop-node-name;
            type uint32 {
              tailf:info
                "<4096-4121440>;;Buffer size";
            }
          }
        }
        container layer2events {
          tailf:info
            "cable layer 2 messages";
          tailf:cli-delete-when-empty;
          presence "true";
          leaf buffer-size {
            tailf:cli-drop-node-name;
            type uint32 {
              tailf:info
                "<4096-4121440>;;Buffer size";
            }
          }
        }
        container overlapip {
          tailf:info
            "cable OVERLAPIP messages";
          tailf:cli-delete-when-empty;
          presence "true";
          leaf buffer-size {
            tailf:cli-drop-node-name;
            type uint32 {
              tailf:info
                "<4096-4121440>;;Buffer size";
            }
          }
        }
        container ironbus {
          tailf:info
            "cable IRONBUS messages";
          tailf:cli-delete-when-empty;
          presence "true";
          leaf buffer-size {
            tailf:cli-drop-node-name;
            type uint32 {
              tailf:info
                "<4096-4121440>;;Buffer size";
            }
          }
        }
        container downstream-index {
          tailf:info
            "cable downstream index messages";
          tailf:cli-delete-when-empty;
          presence "true";
          leaf buffer-size {
            tailf:cli-drop-node-name;
            type uint32 {
              tailf:info
                "<4096-4121440>;;Buffer size";
            }
          }
        }
      }
      container default-tos-qos10 {
        tailf:info
          "Default DOCSIS 1.0 ToS Overwrite";
        container tos-overwrite {
          tailf:info
            "Overwrite ToS byte by setting mask bits to value";
          tailf:cli-compact-syntax;
          tailf:cli-sequence-commands;
          leaf tos-and {
            tailf:cli-drop-node-name;
            tailf:cli-incomplete-command;
            type string {
              tailf:info
                "<0x0-0xFF>;;ToS-overwrite-mask-and byte in hex";
            }
          }
          leaf tos-or {
            tailf:cli-drop-node-name;
            type string {
              tailf:info
                "<0x0-0xFF>;;ToS-overwrite-mask-or byte in hex";
            }
          }
        }
      }
      container primary-sflow-qos11 {
        tailf:info
          "Keep the primary service flows after CM in QoS DOCSIS11 mode offline";
        leaf keep {
          tailf:info
            "Keep the primary service flows after CM in QoS DOCSIS11 mode offline";
          type enumeration {
            enum "all" {
              tailf:info
                "Keep CLI and SNMP counters after CM in QoS DOCSIS11 mode offline";
            }
            enum "snmp-only" {
              tailf:info
                "Keep SNMP counters only after CM in QoS DOCSIS11 mode offline";
            }
          }
        }
      }
      container sflog {
        tailf:info
          "CMTS Service Flow Logging Configuration";
        tailf:cli-compact-syntax;
        tailf:cli-sequence-commands;
        leaf max-entry {
          tailf:info
            "Max. number of entries in service flow log.";
          tailf:cli-incomplete-command;
          type uint16 {
            tailf:info
              "<30000-59999>;;Max. number of entries in the service flow log.";
            range "30000..59999";
          }
        }
        leaf entry-duration {
          tailf:info
            "Service flow log entry duration in second";
          type uint32 {
            tailf:info
              "<3600-86400>;;Service flow log entry duration in second.";
            range "3600..86400";
          }
        }
      }
      list trust {
        tailf:cli-suppress-mode;
        tailf:cli-delete-when-empty;
        key "address";
        leaf address {
          type string {
            tailf:info
              "H.H.H;;MAC address of the trusted host";
          }
        }
      }
      container dynamic-secret {
        tailf:info
          "Cable dynamic secret";
        container exclude {
          tailf:info
            "Exclude single modem";
          leaf modem {
            tailf:info
              "Exclude single modem";
            type string {
              tailf:info
                "H.H.H;;MAC address of the modem to exclude";
            }
          }
          leaf oui {
            tailf:info
              "Exclude group of modems based on OUI";
            type string {
              tailf:info
                "WORD;;OUI to exclude";
            }
          }
        }
        container tftp {
          tailf:info
            "TFTP Proxy Options";
          leaf insert-upgrade-server {
            tailf:info
              "Automatically insert upgrade server TLV into the DOCSIS configuration file";
            type empty;
          }
        }
      }
      container docsis30-voice {
        tailf:info
          "Docsis 3.0 voice default configurations";
        container downstream {
          tailf:info
            "Downstream Service parameters";
          tailf:cli-compact-syntax;
          tailf:cli-sequence-commands;
          leaf req-attr-mask {
            tailf:info
              "SF Required Attribute Mask";
            tailf:cli-incomplete-command;
            type string {
              tailf:info
                "<0-FFFFFFFF>;;The attribute bitmap in hex";
            }
          }
          leaf forb-attr-mask {
            tailf:info
              "SF Forbidden Attribute Mask";
            type string {
              tailf:info
                "<0-FFFFFFFF>;;The attribute bitmap in hex";
            }
          }
        }
      }
      leaf util-interval {
        tailf:info
          "Set channel utilization interval";
        type uint32 {
          tailf:info
            "<1-86400>;;The time interval in seconds";
          range "1..86400";
        }
      }
      container clock {
        tailf:info
          "Clock card";
        leaf dti {
          tailf:info
            "set DTI clock reference mode";
          type empty;
        }
        leaf dti-server-type {
          tailf:info
            "Server type configuration (Polylink/Symmetricom)";
          type enumeration {
            enum "polylink" {
              tailf:info
                "DTI server type - Polylink";
            }
            enum "symmetricom" {
              tailf:info
                "DTI server type - Symmetricom";
            }
          }
        }
      }
      container bgsync {
        tailf:info
          "switch snmp sync state";
        leaf active {
          tailf:info
            "set background sync status";
          tailf:cli-boolean-no;
          tailf:cli-full-command;
          type boolean;
          default "true";
        }
        leaf ptime {
          tailf:info
            "set how long(unit second) a p packet sent";
          type uint32 {
            tailf:info
              "<5-86400>;;in second";
            range "5..86400";
          }
          default "5";
        }
        leaf itime {
          tailf:info
            "set how long(unit second) a i packet sent";
          type uint32 {
            tailf:info
              "<5-31536000>;;in second";
            range "5..31536000";
          }
          default "86400";
        }
      }
      container privacy {
        tailf:info
          "Cable Privacy";
        leaf encrypt-alg-priority {
          tailf:info
            "Encryption algorithm priority";
          type enumeration {
            enum "aes128-des40-des56" {
              tailf:info
                "Priority AES128, DES40, DES56";
            }
            enum "aes128-des56-des40" {
              tailf:info
                "Priority AES128, DES56, DES40";
            }
            enum "des40-aes128-des56" {
              tailf:info
                "Priority DES40, AES128, DES56";
            }
            enum "des40-des56-aes128" {
              tailf:info
                "Priority DES40, DES56, AES128";
            }
            enum "des56-aes128-des40" {
              tailf:info
                "Priority DES56, AES128, DES40";
            }
            enum "des56-des40-aes128" {
              tailf:info
                "Priority DES56, DES40, AES128";
            }
          }
        }
      }
      container dsg {
        tailf:info
          "Set DSG advance mode global parameters";
        list client-list {
          tailf:info
            "DSG client list settings";
          tailf:cli-suppress-mode;
          tailf:cli-delete-when-empty;
          tailf:cli-compact-syntax;
          tailf:cli-incomplete-command;
          key "client-list-id";
          leaf client-list-id {
            type uint16 {
              tailf:info
                "<1-65535>;;DSG client list ID";
              range "1..65535";
            }
          }
          list id-index {
            tailf:info
              "DSG Client ID settings";
            tailf:cli-suppress-mode;
            tailf:cli-delete-when-empty;
            tailf:cli-incomplete-command;
            key "id";
            leaf id {
              type uint16 {
                tailf:info
                  "<1-65535>;;DSG client ID index for the client list";
                range "1..65535";
              }
            }
            choice parameter-choice {
              leaf application-id {
                tailf:info
                  "DSG Client type Application ID";
                type string {
                  tailf:info
                    "<1-FFFF>;;Hex value of DSG Client type Application ID";
                }
              }
              leaf broadcast {
                tailf:info
                  "DSG Client type broadcast";
                type uint16 {
                  tailf:info
                    "<1--65535>;;DSG Broadcast client";
                  range "1..65535";
                }
              }
              leaf ca-system-id {
                tailf:info
                  "DSG Client type CA system ID";
                type string {
                  tailf:info
                    "<1-FFFF>;;Hex value of DSG Client type CA system ID";
                }
              }
              leaf mac-addr {
                tailf:info
                  "DSG Client type Mac address";
                type string {
                  tailf:info
                    "H.H.H;;DSG Client MAC address";
                }
              }
            }
          }
        }
        list tg {
          tailf:cli-suppress-mode;
          tailf:cli-delete-when-empty;
          key "group-id";
          leaf group-id {
            type uint16 {
              tailf:info
                "<1-65535>;;DSG Tunnel Group ID";
              range "1..65535";
            }
          }
          list channel {
            tailf:info
              "DSG Channel";
            tailf:cli-suppress-mode;
            tailf:cli-delete-when-empty;
            tailf:cli-compact-syntax;
            key "channel-id";
            leaf channel-id {
              type uint16 {
                tailf:info
                  "<1-65535>;;DSG Channel ID";
                range "1..65535";
              }
            }
            leaf priority {
              tailf:info
                "DSG Rule priority";
              type uint8 {
                tailf:info
                  "<0-255>;;DSG Rule priority";
              }
            }
            leaf status {
              tailf:cli-drop-node-name;
              type enumeration {
                enum "disable" {
                  tailf:info
                    "Disable DSG tunnel group";
                }
                enum "enable" {
                  tailf:info
                    "Enable DSG tunnel group";
                }
              }
              default "enable";
            }
          }
        }
        list tunnel {
          tailf:info
            "DSG tunnel";
          tailf:cli-suppress-mode;
          tailf:cli-delete-when-empty;
          tailf:cli-compact-syntax;
          tailf:cli-sequence-commands;
          key "tunnel-id";
          leaf tunnel-id {
            type uint16 {
              tailf:info
                "<1-65535>;;Tunnel id";
              range "1..65535";
            }
          }
          leaf mac-addr {
            tailf:info
              "destination MAC address";
            tailf:cli-incomplete-command;
            type string {
              tailf:info
                "H.H.H;;Multicast group MAC address";
            }
          }
          leaf tg {
            tailf:info
              "tunnel group id";
            tailf:cli-incomplete-command;
            type uint16 {
              tailf:info
                "<1-65535>;;tunnel group id";
              range "1..65535";
            }
          }
          leaf clients {
            tailf:info
              "DSG Clients";
            type uint16 {
              tailf:info
                "<1-65535>;;DSG Clients";
              range "1..65535";
            }
          }
          leaf status {
            tailf:cli-drop-node-name;
            type enumeration {
              enum "disable" {
                tailf:info
                  "disable tunnel";
              }
              enum "enable" {
                tailf:info
                  "enable tunnel";
              }
            }
            default "enable";
          }
        }
        list cfr {
          tailf:info
            "DSG classifier";
          tailf:cli-suppress-mode;
          tailf:cli-delete-when-empty;
          tailf:cli-compact-syntax;
          tailf:cli-sequence-commands;
          key "index";
          leaf index {
            type uint16 {
              tailf:info
                "<1-65535>;;Classifier index";
              range "1..65535";
            }
          }
          leaf dest-ip {
            tailf:info
              "destination IP address";
            type string {
              tailf:info
                "WORD;;Multicast group IP address or hostname";
            }
          }
          leaf tunnel {
            tailf:cli-break-sequence-commands;
            tailf:info
              "tunnel index";
            type uint16 {
              tailf:info
                "<1-65535>;;tunnel index";
              range "1..65535";
            }
          }
          leaf priority {
            tailf:info
              "Classifier priority";
            type uint8 {
              tailf:info
                "<0-255>;;Classifier priority";
            }
          }
          leaf src-ip {
            tailf:info
              "source IP address";
            type string {
              tailf:info
                "WORD;;source IP address or hostname";
            }
          }
          leaf in-dcd {
            tailf:info
              "classifier is included in DCD or not";
            type enumeration {
              enum "ignore" {
                tailf:info
                  "classifier is not included in DCD regardless of tunnel MAC address";
              }
              enum "no" {
                tailf:info
                  "classifier is not included in DCD";
              }
              enum "yes" {
                tailf:info
                  "classifier is included in DCD";
              }
            }
          }
        }
        list timer {
          tailf:info
            "DSG Timer settings";
          tailf:cli-suppress-mode;
          tailf:cli-delete-when-empty;
          tailf:cli-compact-syntax;
          key "index";
          leaf index {
            type uint16 {
              tailf:info
                "<1-65535>;;DSG Timer index";
              range "1..65535";
            }
          }
          leaf Tdsg1 {
            tailf:info
              "DSG Initialization Timeout (Tdsg1) setting";
            type uint16 {
              tailf:info
                "<1-65535>;;DSG Initialization Timeout (Tdsg1) value";
              range "1..65535";
            }
          }
          leaf Tdsg2 {
            tailf:info
              "DSG Operational Timeout (Tdsg2) setting";
            type uint16 {
              tailf:info
                "<1-65535>;;DSG Initialization Timeout (Tdsg2) value";
              range "1..65535";
            }
          }
          leaf Tdsg3 {
            tailf:info
              "DSG Two-Way Retry Timer (Tdsg3) setting";
            type uint16 {
              tailf:info
                "<0-65535>;;DSG Initialization Timeout (Tdsg3) value";
            }
          }
          leaf Tdsg4 {
            tailf:info
              "DSG One-Way Retry Timer (Tdsg4) setting";
            type uint16 {
              tailf:info
                "<0-65535>;;DSG Initialization Timeout (Tdsg4) value";
            }
          }
        }
        list chan-list {
          tailf:cli-suppress-mode;
          tailf:cli-delete-when-empty;
          tailf:cli-compact-syntax;
          tailf:cli-sequence-commands {
            tailf:cli-reset-siblings;
          }
          tailf:cli-incomplete-command;
          key "id index";
          leaf id {
            type uint16 {
              tailf:info
                "<1-65535>;;DSG Channel List index";
              range "1..65535";
            }
          }
          leaf index {
            tailf:info
              "DSG channel frequency entry setting";
            tailf:cli-expose-key-name;
            type uint16 {
              tailf:info
                "<1-65535>;;DSG channel frequency entry index";
              range "1..65535";
            }
          }
          leaf freq {
            tailf:info
              "DSG Channel Frequency setting";
            type uint32 {
              tailf:info
                "<47000000-862000000>;;Center frequency of the downstream channel in Hz";
            }
          }
        }
      }
      container load-balance {
        tailf:info
          "DOCSIS load balancing";
        leaf docsis-enable {
          tailf:info
            "Enable docsis 2.0 load balancing";
          type empty;
        }
        container docsis30-enable {
          tailf:info
            "Enable docsis 3.0 load balancing";
          tailf:cli-delete-when-empty;
          presence "true";
          leaf downstream-only {
            type empty;
          }
        }
        container modem {
          tailf:info
            "Modem settings";
          leaf max-failures {
            tailf:info
              "Set the time of failed movements before modem is removed from dynamic LB";
            type uint8 {
              tailf:info
                "<0-100>;;Maximum failures before modem is removed from dynamic LB";
              range "0..100";
            }
          }
        }
        list rule {
          tailf:info
            "Enter docsis load balance rule";
          tailf:cli-suppress-mode;
          tailf:cli-delete-when-empty;
          tailf:cli-compact-syntax;
          tailf:cli-sequence-commands;
          tailf:cli-incomplete-command;
          key "rule-id";
          leaf rule-id {
            type uint32 {
              tailf:info
                "<1-4294967295>;;DOCSIS load balance rule ID";
              range "1..4294967295";
            }
          }
          choice status-choice {
            container ds {
              tailf:cli-drop-node-name;
              container disable-throughput-lowerbound {
                tailf:info
                  "load balance is disabled if CM throughput is lower than a threshold";
                leaf ds {
                  tailf:info
                    "Specify DS throughput lowerbound";
                  type uint32 {
                    tailf:info
                      "<0-1000000>;;Throughput lowerbound in kbps";
                    range "0..1000000";
                  }
                }
              }
            }
            container us {
              tailf:cli-drop-node-name;
              container disable-throughput-lowerbound {
                tailf:info
                  "load balance is disabled if CM throughput is lower than a threshold";
                leaf us {
                  tailf:info
                    "Specify US throughput lowerbound";
                  type uint32 {
                    tailf:info
                      "<0-1000000>;;Throughput lowerbound in kbps";
                    range "0..1000000";
                  }
                }
              }
            }
            leaf disabled {
              tailf:info
                "load balance is always disabled";
              type empty;
            }
            leaf enabled {
              tailf:info
                "load balance is always enabled";
              type empty;
            }
          }
        }
        list docsis-policy {
          tailf:info
            "Enter docsis load balance policy";
          tailf:cli-suppress-mode;
          tailf:cli-delete-when-empty;
          key "policy-id";
          leaf policy-id {
            type uint32 {
              tailf:info
                "<1-4294967295>;;DOCSIS load balance policy ID";
              range "1..4294967295";
            }
          }
          list rule {
            tailf:info
              "Enter docsis load balance rule";
            tailf:cli-suppress-mode;
            tailf:cli-delete-when-empty;
            key "rule-id";
            leaf rule-id {
              type uint32 {
                tailf:info
                  "<1-4294967295>;;DOCSIS load balance rule ID";
              }
            }
          }
          leaf tag {
            tailf:info
              "Tag name";
            type string {
              tailf:info
                "WORD;;Tag name";
            }
          }
          leaf override {
            tailf:info
              "Override the default";
            type empty;
          }
        }
        container d20-ggrp-default {
          tailf:info
            "Set DOCSIS 2.0 general group default value ";
          leaf init-tech-list {
            tailf:info
              "Set DOCSIS GGRP DCC/DBC init tech as default";
            type uint32 {
              tailf:info
                "<grouplist>;;Set DCC/DBC Initialization technique list as default";
            }
          }
          container method {
            tailf:info
              "Set default load balancing type/method";
            container utilization {
              tailf:info
                "Interface utilization";
              presence "true";
            }
          }
          container policy {
            tailf:info
              "Set default load balancing policy";
            leaf pure-ds-load {
              tailf:info
                "Do not count US load when calculating DS utilization";
              type empty;
            }
          }
          container threshold {
            tailf:info
              "Set default load balancing threshold in %";
            container load {
              tailf:info
                "Set default interface load threshold setting";
              leaf value {
                tailf:cli-drop-node-name;
                type uint8 {
                  tailf:info
                    "<1-100>;;Set threshold value in % as default";
                  range "1..100";
                }
              }
            }
          }
        }
        container d30-ggrp-default {
          tailf:info
            "Set DOCSIS 3.0 general group default value";
          leaf disable {
            tailf:info
              "Set disable DOCSIS GGRP as default";
            type empty;
          }
          leaf init-tech-list {
            tailf:info
              "Set DOCSIS GGRP DCC/DBC init tech as default";
            type string {
              tailf:info
                "<grouplist>;;Set DCC/DBC Initialization technique list as default";
            }
          }
          leaf docsis-policy {
            tailf:info
              "Set DOCSIS GGRP policy ID as default";
            type uint32 {
              tailf:info
                "<0-4294967295>;;Set DOCSIS load balance policy ID as default";
            }
          }
          leaf policy {
            tailf:info
              "Set default load balancing policy";
            type enumeration {
              enum "pcmm" {
                tailf:info
                  "Enable balancing of modems with active PCMM service flows";
              }
              enum "pure-ds-load" {
                tailf:info
                  "Do not count US load when calculating DS utilization";
              }
              enum "ugs" {
                tailf:info
                  "Enable balancing of modems with active UGS service flows";
              }
              enum "us-across-ds" {
                tailf:info
                  "Load balancing on US groups across DS, DS method will be ignored";
              }
            }
          }
          container threshold {
            tailf:info
              "Set default load balancing threshold in %";
            container load {
              tailf:info
                "Set default interface load threshold setting";
              leaf load-value {
                tailf:cli-drop-node-name;
                type uint8 {
                  tailf:info
                    "<1-100>;;Set threshold value in % as default";
                  range "1..100";
                }
              }
              leaf minimum {
                tailf:info
                  "Set minimum number of modems/flows difference before loadbalancing starts as default";
                type uint8 {
                  tailf:info
                    "<1-100>;;Set minimum number of modems/flows as default";
                  range "1..100";
                }
              }
            }
          }
        }
        container docsis-group {
          tailf:info
            "DOCSIS group";
          list FN {
            tailf:cli-mode-name "config-lb-group";
            key "fn-id";
            leaf fn-id {
              type uint16 {
                tailf:info
                  "<1-256>;;cable fiber-node ID";
                range "1..256";
              }
            }
            container MD {
              tailf:info
                "Enter MAC-domain interface";
              tailf:cli-hide-in-submode;
              tailf:cli-flatten-container;
              leaf Cable {
                tailf:info
                  "Cable;;CMTS interface";
                tailf:cli-allow-join-with-value {
                  tailf:cli-display-joined;
                }
                tailf:cli-hide-in-submode;
                tailf:non-strict-leafref {
                  path "../../../../../../interface/Cable/name";
                }
                type string {
                  pattern '[0-9]+.*';
                }
              }
            }
            uses cable-load-balance-docsis-group-grouping;
          }
          list docsis-group-list {
            tailf:cli-drop-node-name;
            tailf:cli-mode-name "config-lb-group";
            key "docsis-group-id";
            leaf docsis-group-id {
              type uint32 {
                tailf:info
                  "<1-2147483647>;;DOCSIS load balance group number";
                range "1..2147483647";
              }
            }
            uses cable-load-balance-docsis-group-grouping;
          }
        }
        list group {
          tailf:cli-suppress-mode;
          tailf:cli-delete-when-empty;
          tailf:cli-compact-syntax;
          key "id";
          leaf id {
            type uint16 {
              tailf:info
                "<1-256>;;Load balance group number";
              range "1..256";
            }
          }
        }
        container exclude {
          tailf:info
            "Exclude modems from load balancing";
          list oui {
            tailf:cli-suppress-mode;
            tailf:cli-delete-when-empty;
            tailf:cli-compact-syntax;
            tailf:cli-reset-container;
            key "word";
            leaf word {
              type string {
                tailf:info
                  "WORD;;OUI of exclude modem in the formatxx.xx.xx or xx:xx:xx";
              }
            }
            leaf assignment {
              tailf:info
                "Exclude modem at assigning phase";
              tailf:cli-full-command;
              type empty;
            }
            leaf enforce {
              tailf:info
                "Exclude only for enforced load balancing";
              tailf:cli-full-command;
              type empty;
            }
            leaf static {
              tailf:info
                "Exclude only for static load balancing";
              type empty;
            }
            leaf strict {
              tailf:info
                "Exclude all forms of load balancing";
              tailf:cli-full-command;
              type empty;
            }
          }
        }
      }
      container metering {
        tailf:info
          "CMTS Metering Configuration";
        choice cable-metering-choice {
          container destination {
            tailf:info
              "Cable Metering Collector IP address";
            tailf:cli-compact-syntax;
            tailf:cli-sequence-commands {
              tailf:cli-reset-siblings;
            }
            leaf ip-address {
              tailf:cli-drop-node-name;
              tailf:cli-incomplete-command;
              tailf:cli-remove-before-change;
              type inet:ipv4-address {
                tailf:info
                  "A.B.C.D;;Enter IP address of primary";
              }
            }
            leaf port {
              tailf:cli-drop-node-name;
              tailf:cli-incomplete-command;
              type uint16 {
                tailf:info
                  "<1-65535>;;Enter Port Number of primary";
                range "1..65535";
              }
            }
            leaf ip-address2 {
              tailf:cli-drop-node-name;
              tailf:cli-optional-in-sequence;
              tailf:cli-incomplete-command;
              type inet:ipv4-address {
                tailf:info
                  "A.B.C.D;;Enter IP address of secondary";
              }
            }
            leaf port2 {
              when "../ip-address2" {
                tailf:xpath-root 3;
                tailf:dependency "../ip-address2";
              }
              tailf:cli-drop-node-name;
              tailf:cli-incomplete-command;
              type uint16 {
                tailf:info
                  "<1-65535>;;Enter Port Number of secondary";
                range "1..65535";
              }
            }
            leaf retries {
              tailf:cli-drop-node-name;
              tailf:cli-incomplete-command;
              type uint8 {
                tailf:info
                  "<0-5>;;Enter number of retries ";
                range "0..5";
              }
            }
            leaf minutes {
              tailf:cli-drop-node-name;
              tailf:cli-incomplete-command;
              type uint16 {
                tailf:info
                  "<2-1440>;;Enter metering data collection interval in minutes";
                range "2..1440";
              }
            }
            leaf security {
              tailf:cli-drop-node-name;
              type enumeration {
                enum "non-secure" {
                  tailf:info
                    "Non secure streaming";
                }
                enum "secure" {
                  tailf:info
                    "Secure streaming";
                }
              }
            }
            leaf flow-aggregate {
              tailf:cli-break-sequence-commands;
              tailf:info
                "Only aggregate service flow information";
              type empty;
            }
            leaf cpe-list-suppress {
              tailf:info
                "Suppress cpe information";
              type empty;
            }
            leaf full-records {
              tailf:info
                "Full service flow (active and idle) records";
              type empty;
            }
          }
          container ipdr-d3 {
            tailf:info
              "Cable Metering Exporter through IPDR D3.0";
            container session {
              tailf:info
                "IPDR D3 session";
              tailf:cli-compact-syntax;
              tailf:cli-sequence-commands {
                tailf:cli-reset-siblings;
              }
              leaf session-id {
                tailf:cli-drop-node-name;
                tailf:cli-incomplete-command;
                type uint8 {
                  tailf:info
                    "<1-255>;;Enter metering ipdr D3 session id";
                  range "1..255";
                }
              }
              leaf type {
                tailf:info
                  "IPDR D3 Service Definition Type of Metering";
                type uint8 {
                  tailf:info
                    "<1-2>;;Enter metering IPDR D3 Service Definition Type";
                  range "1..2";
                }
              }
              leaf flow-aggregate {
                tailf:info
                  "Only aggregate service flow information";
                tailf:cli-optional-in-sequence;
                type empty;
              }
              leaf full-records {
                tailf:info
                  "Full service flow (active and idle) records";
                type empty;
              }
            }
          }
        }
        container ipdr {
          tailf:cli-compact-syntax;
          tailf:cli-sequence-commands {
            tailf:cli-reset-siblings;
          }
          leaf interval {
            tailf:cli-drop-node-name;
            tailf:cli-incomplete-command;
            type uint16 {
              tailf:info
                "<2-1440>;;Enter metering data streaming interval in minutes";
              range "2..1440";
            }
          }
          leaf session {
            tailf:info
              "IPDR session";
            type uint8 {
              tailf:info
                "<1-255>;;Enter metering ipdr session id";
              range "1..255";
            }
          }
          leaf flow-aggregate {
            tailf:info
              "Only aggregate service flow information";
            tailf:cli-optional-in-sequence;
            type empty;
          }
          leaf full-records {
            tailf:info
              "Full service flow (active and idle) records";
            type empty;
          }
        }
        container source-interface {
          tailf:info
            "source-interface for the billing packets";
          uses interface-name-grouping;
        }
        container data-per-session {
          tailf:info
            "Number of flows per session";
          tailf:cli-compact-syntax;
          tailf:cli-sequence-commands;
          leaf data-per-session {
            tailf:cli-drop-node-name;
            type uint8 {
              tailf:info
                "<3-30>;;Enter # of data flows per session";
              range "3..30";
            }
          }
          leaf timer {
            tailf:info
              "CLC timer to wake up ";
            type uint16 {
              tailf:info
                "<8-500>;;Enter timer wake up interval in msec";
              range "8..500";
            }
          }
        }
      }
      container rf-change-trigger {
        tailf:info
          "NP RF status change trigger";
        tailf:cli-compact-syntax;
        leaf percent {
          tailf:info
            "% of CM report NP RF status change";
          type uint8 {
            tailf:info
              "<1-100>;;% of CM report NP RF status change";
            range "1..100";
          }
        }
        leaf count {
          tailf:info
            "#of CM report NP RF status change";
          type uint16 {
            tailf:info
              "<1-65535>;;#of CM report NP RF status change";
            range "1..65535";
          }
        }
        leaf secondary {
          tailf:info
            "move secondary service flows";
          type empty;
        }
      }
      leaf rf-change-dampen-time {
        tailf:info
          "NP RF status change dampen time";
        type uint16 {
          tailf:info
            "<1-65535>;;#of seconds NP RF status change must persist";
          range "1..65535";
        }
      }
      container resiliency {
        tailf:info
          "Resiliency functionality";
        leaf ds-bonding {
          tailf:info
            "Downstream resiliency bonding groups";
          type empty;
        }
      }
      container throttle-modem {
        tailf:info
          "Manage CM initialization/registration throttling on large systems";
        tailf:cli-compact-syntax;
        tailf:cli-sequence-commands {
          tailf:cli-reset-siblings;
        }
        leaf init-rate {
          tailf:info
            "Maximum number of modems pass the initialization step per second";
          tailf:cli-incomplete-command;
          type uint16 {
            tailf:info
              "<1-1000>;;Default value is 32 CM/Sec";
            range "1..1000";
          }
        }
        leaf holdoff-time {
          tailf:info
            "Maximum number of seconds a modem waiting in throttling queue";
          tailf:cli-incomplete-command;
          type uint8 {
            tailf:info
              "<5-100>;;Default value is 45 Seconds";
            range "5..100";
          }
        }
        leaf flush-rate {
          tailf:info
            "Maximum number of modems flushing from throttling queue once holdoff time is expired";
          type uint16 {
            tailf:info
              "<100-1000>;;Default value is 300 CM/Sec";
            range "100..1000";
          }
        }
      }
      container ds-max-burst {
        tailf:info
          "Enable maximum traffic burst";
        tailf:cli-delete-when-empty;
        presence "true";
        choice optional {
          leaf burst-threshold {
            tailf:info
              "Threshold to enable maximum traffic burst";
            type uint32 {
              tailf:info
                "<64-1000000>;;Burst Threshold in Kbytes (default = 1000)";
              range "64..1000000";
            }
            default "1000";
          }
          leaf peak-rate {
            tailf:info
              "Peak rate within the maximum traffic burst";
            type uint32 {
              tailf:info
                "<0-1000000>;;Peak Rate in Kbps (default is unshaped)";
              range "0..1000000";
            }
          }
        }
      }
      container acfe {
        tailf:info
          "Configure Fairness across DOCSIS interfaces";
        leaf enable {
          tailf:info
            "Enable Fairness across DOCSIS interfaces (Adaptive CIR Fair EIR)";
          type empty;
        }
        leaf period {
          tailf:info
            "Set EIR rebalance period";
          type uint8 {
            tailf:info
              "<5-60>;;seconds";
            range "5..60";
          }
        }
      }
      container l2-vpn-service {
        tailf:info
          "Use Layer-2 Tunnels for CPE traffic behind certain CMs";
        container xconnect {
          tailf:info
            "Tunnel traffic to L2VPN circuit";
          container nsi {
            tailf:info
              "Network System Interface";
            container dot1q {
              tailf:info
                "Tunnel traffic to DOT1Q L2VPN";
              tailf:cli-display-separated;
              presence "true";
              container interface {
                tailf:info
                  "Default Ethernet NSI interface";
                uses interface-name-grouping;
              }
            }
            container mpls {
              tailf:info
                "Tunnel traffic to ATOM/MPLS PW";
              presence "true";
            }
          }
        }
      }
      list dot1q-vc-map {
        tailf:info
          "Map a CM to an Ethernet VLAN";
        tailf:cli-suppress-mode;
        tailf:cli-delete-when-empty;
        tailf:cli-compact-syntax;
        tailf:cli-sequence-commands;
        tailf:cli-incomplete-command;
        key "mac-address";
        leaf mac-address {
          type string {
            tailf:info
              "H.H.H;;Modem MAC address";
          }
        }
        container ethernet-interface {
          tailf:cli-drop-node-name;
          tailf:cli-flatten-container;
          tailf:cli-compact-syntax;
          tailf:cli-incomplete-command;
          uses interface-name-grouping;
        }
        leaf vlan-id {
          tailf:cli-drop-node-name;
          type uint16 {
            tailf:info
              "<2-4095>;;IEEE 802.1Q VLAN ID";
            range "2..4095";
          }
        }
        leaf cust-name {
          tailf:cli-drop-node-name;
          type string {
            tailf:info
              "WORD;;Customer Name";
          }
        }
      }
      list l2vpn {
        tailf:info
          "Cable Modem Ethernet L2VPN Service";
        tailf:cli-mode-name "config-l2vpn";
        tailf:cli-sequence-commands;
        key "mac-address";
        leaf mac-address {
          type string {
            tailf:info
              "H.H.H;;Modem MAC address";
          }
        }
        leaf customer-name {
          tailf:cli-drop-node-name;
          tailf:cli-hide-in-submode;
          type string {
            tailf:info
              "WORD;;Customer Name";
          }
        }
        container service {
          tailf:cli-break-sequence-commands;
          tailf:info
            "Ethernet service";
          list instance {
            tailf:info
              "Ethernet service Instance";
            tailf:cli-mode-name "config-ethsrv";
            tailf:cli-sequence-commands;
            tailf:cli-incomplete-command;
            max-elements 1;
            key "id";
            leaf id {
              type uint16 {
                tailf:info
                  "<1-8000>;;Ethernet service Instance id";
              }
            }
            leaf ethernet {
              tailf:info
                "Service Type  - Ethernet";
              tailf:cli-hide-in-submode;
              tailf:cli-full-command;
              type empty;
            }
            container xconnect {
              tailf:cli-break-sequence-commands;
              tailf:info
                "Xconnect service";
              tailf:cli-add-mode;
              tailf:cli-mode-name "config-xconn";
              tailf:cli-compact-syntax;
              tailf:cli-sequence-commands;
              tailf:cli-incomplete-command;
              leaf address {
                tailf:cli-drop-node-name;
                tailf:cli-incomplete-command;
                tailf:cli-hide-in-submode;
                type inet:ipv4-address {
                  tailf:info
                    "A.B.C.D;;Pseudo-wire Peer IP address";
                }
              }
              leaf vcid {
                tailf:cli-drop-node-name;
                tailf:cli-incomplete-command;
                tailf:cli-hide-in-submode;
                type uint32 {
                  tailf:info
                    "<1-4294967295>;;Pseudo Wire VCID";
                  range "1..4294967295";
                }
              }
              leaf encapsulation {
                tailf:info
                  "Data encapsulation method";
                tailf:cli-hide-in-submode;
                type enumeration {
                  enum "mpls" {
                    tailf:info
                      "Use MPLS encapsulation";
                  }
                }
              }
              leaf pw-type {
                tailf:info
                  "MPLS Pseudo-wire Type";
                tailf:cli-optional-in-sequence;
                tailf:cli-hide-in-submode;
                type uint8 {
                  tailf:info
                    "<4-5>;;Type-5 : Ethernet Port, Type-4 : Ethernet VLAN";
                  range "4..5";
                }
              }
              container backup {
                tailf:cli-break-sequence-commands;
                tailf:info
                  "Xconnect backup configuration commands";
                list peer {
                  tailf:info
                    "Backup pseudowire";
                  tailf:cli-suppress-mode;
                  tailf:cli-delete-when-empty;
                  tailf:cli-compact-syntax;
                  max-elements 3;
                  key "peer-router-ip-addr vcid";
                  leaf peer-router-ip-addr {
                    type inet:ipv4-address {
                      tailf:info
                        "A.B.C.D;;IP address of peer";
                    }
                  }
                  leaf vcid {
                    type uint32 {
                      tailf:info
                        "<1-4294967295>;;Enter VC ID value";
                      range "1..4294967295";
                    }
                  }
                  leaf priority {
                    tailf:info
                      "Optional priority to use for backup pseudowire.";
                    type uint8 {
                      tailf:info
                        "Peer priority";
                      range "1..10";
                    }
                  }
                }
                container delay {
                  tailf:info
                    "Backup delay";
                  tailf:cli-compact-syntax;
                  tailf:cli-sequence-commands;
                  leaf enable-delay {
                    tailf:cli-drop-node-name;
                    tailf:cli-incomplete-command;
                    type uint8 {
                      tailf:info
                        "<0-180>;;Enable delay";
                      range "0..180";
                    }
                    default "0";
                  }
                  leaf disable-delay {
                    tailf:cli-drop-node-name;
                    type union {
                      type uint8 {
                        tailf:info
                          "<0-180>;;Disable delay";
                        range "0..180";
                      }
                      type enumeration {
                        enum "never" {
                          tailf:info
                            "Disallow disable";
                        }
                      }
                    }
                    default "0";
                  }
                }
              }
            }
            container cable {
              tailf:info
                "Cable Specific commands";
              container set {
                tailf:info
                  "Set parameters";
                leaf mpls-experimental {
                  tailf:info
                    "Set MPLS Pseudo-wire Experimental bits";
                  type uint8 {
                    tailf:info
                      "<0-7>;;MPLS Experimental Bits Value";
                  }
                }
              }
            }
          }
        }
      }
      container wideband {
        tailf:info
          "Wideband Configuration";
        leaf auto-reset {
          tailf:info
            "Reset WCMs reg'd traditional-DOCSIS";
          type empty;
        }
      }
      list rcc-template {
        tailf:info
          "Create Cable RCC-Template";
        tailf:cli-mode-name "config-rcc-template";
        key "index";
        leaf index {
          type uint8 {
            tailf:info
              "<1-255>;;cable rcc-template id";
            range "1..255";
          }
        }
        leaf rcp-id {
          tailf:info
            "Receive Channel Profile ID";
          tailf:cli-multi-value;
          tailf:cli-full-command;
          type string {
            tailf:info
              "<0x0-0xFF>;;RCP ID in hex";
          }
        }
        list receive-module {
          tailf:info
            "Receive Module entry";
          tailf:cli-suppress-mode;
          tailf:cli-delete-when-empty;
          tailf:cli-compact-syntax;
          tailf:cli-sequence-commands;
          tailf:cli-incomplete-command;
          key "index";
          leaf index {
            type uint8 {
              tailf:info
                "<1-10>;;Receive Module index";
              range "1..10";
            }
          }
          leaf first-center-frequency {
            tailf:info
              "Module Center frequency";
            type uint32 {
              tailf:info
                "<55000000-1050000000>;;Center Frequency - Hz";
              range "55000000..1050000000";
            }
          }
          leaf connected-receive-module {
            tailf:info
              "Receive Modules";
            type uint8 {
              tailf:info
                "<1-10>;;Connected Receive Module index";
              range "1..10";
            }
          }
        }
        list receive-channel {
          tailf:info
            "Receive Channel entry";
          tailf:cli-suppress-mode;
          tailf:cli-delete-when-empty;
          tailf:cli-compact-syntax;
          tailf:cli-sequence-commands;
          tailf:cli-incomplete-command;
          key "index";
          leaf index {
            type uint8 {
              tailf:info
                "<1-24>;;Receive Channel index";
              range "1..24";
            }
          }
          leaf center-frequency {
            tailf:info
              "Channel Center frequency";
            tailf:cli-incomplete-command;
            type uint32 {
              tailf:info
                "<55000000-1050000000>;;Center Frequency - Hz";
              range "55000000..1050000000";
            }
          }
          leaf connected-receive-module {
            tailf:info
              "Receive Modules";
            type uint8 {
              tailf:info
                "<1-10>;;Connected Receive Module index";
              range "1..10";
            }
          }
          leaf primary {
            tailf:info
              "Receive Channel Primary indicator";
            type empty;
          }
        }
      }
      container video {
        tailf:info
          "Cable video config commands";
        presence "true";
      }
      list fiber-node {
        tailf:info
          "Create Cable fiber-node";
        tailf:cli-mode-name "config-fiber-node";
        key "fiber-node-id";
        leaf fiber-node-id {
          type uint16 {
            tailf:info
              "<1-256>;;cable fiber-node id";
            range "1..256";
          }
        }
        leaf description {
          tailf:info
            "Fiber node name/description";
          tailf:cli-multi-value;
          tailf:cli-preformatted;
          tailf:cli-full-command;
          type string {
            tailf:info
              "LINE;;Description of this fiber node that will be truncated to 80 characters.";
          }
        }
        container downstream {
          tailf:info
            "Set downstream RF channels";
          list Downstream-Cable {
            tailf:info
              "Downstream-Cable controller";
            tailf:cli-allow-join-with-key;
            tailf:cli-suppress-mode;
            tailf:cli-delete-when-empty;
            key "name";
            leaf name {
              type string {
                tailf:info
                  "<slot>/<card>/<port>;;Enter slot/subslot/bay";
              }
            }
            leaf rf-channel {
              tailf:info
                "RF channel";
              type string {
                tailf:info
                  "<grouplist>;;List of port numbers and number ranges";
              }
            }
          }
          list Modular-Cable {
            tailf:info
              "Modular cable";
            tailf:cli-allow-join-with-key;
            tailf:cli-suppress-mode;
            tailf:cli-delete-when-empty;
            key "name";
            leaf name {
              type string {
                tailf:info
                  "<slot>/<card>/<port>;;Enter slot/subslot/bay";
              }
            }
            leaf rf-channel {
              tailf:info
                "RF channel";
              type string {
                tailf:info
                  "<grouplist>;;List of port numbers and number ranges";
              }
            }
          }
          list Integrated-Cable {
            tailf:info
              "Integrated cable";
            tailf:cli-allow-join-with-key;
            tailf:cli-suppress-mode;
            tailf:cli-delete-when-empty;
            key "name";
            leaf name {
              type string {
                tailf:info
                  "<slot>/<card>/<port>;;Enter slot/subslot/bay";
              }
            }
            leaf rf-channel {
              tailf:info
                "RF channel";
              type string {
                tailf:info
                  "<grouplist>;;List of port numbers and number ranges";
              }
            }
          }
          list sg-channel {
            tailf:info
              "Associate/Remove DS-SG channels into this FN";
            tailf:cli-suppress-mode;
            tailf:cli-delete-when-empty;
            tailf:cli-compact-syntax;
            tailf:cli-sequence-commands;
            key "low";
            leaf low {
              type uint8 {
                tailf:info
                  "<0-254>;;Low DS SG channel";
                range "0..254";
              }
            }
            leaf high {
              tailf:cli-drop-node-name;
              tailf:cli-optional-in-sequence;
              tailf:cli-incomplete-command;
              type uint8 {
                tailf:info
                  "<0-254>;;High DS SG channel";
                range "0..254";
              }
            }
            choice cable-choice {
              leaf downstream-Cable {
                tailf:info
                  "Downstream-Cable controller";
                tailf:cli-incomplete-command;
                type string {
                  tailf:info
                    "WORD;;Controller number";
                }
              }
              leaf integrated-Cable {
                tailf:info
                  "Integrated-Cable controller";
                tailf:cli-incomplete-command;
                type string {
                  tailf:info
                    "WORD;;Controller number";
                }
              }
            }
            leaf rf-channel {
              tailf:info
                "Associate/Remove Downstream channels into this FN";
              type uint8 {
                tailf:info
                  "<0-162>;;Low Downstream rf-channel";
                range "0..162";
              }
            }
            leaf rf-channel-high {
              tailf:cli-drop-node-name;
              type uint8 {
                tailf:info
                  "<1-162>;;High Downstream rf-channel";
                range "1..162";
              }
            }
          }
        }
        container upstream {
          tailf:info
            "Cable upstream channel";
          list Upstream-Cable {
            tailf:info
              "Upstream cable";
            tailf:cli-allow-join-with-key;
            tailf:cli-suppress-mode;
            tailf:cli-delete-when-empty;
            key "name";
            leaf name {
              type string {
                tailf:info
                  "<slot>/<card>/<port>;;Enter slot/subslot/bay";
              }
            }
            leaf connector {
              tailf:info
                "Physical upstream port connector on LC";
              type string {
                tailf:info
                  "<grouplist>;;List of port numbers and number ranges";
              }
            }
          }
          list Cable {
            tailf:cli-allow-join-with-key;
            tailf:cli-suppress-mode;
            tailf:cli-delete-when-empty;
            key "name";
            leaf name {
              type string {
                tailf:info
                  "<slot>/<card>/<port>;;Enter slot/subslot/bay";
              }
            }
            leaf connector {
              tailf:info
                "Physical upstream port connector on LC";
              type string {
                tailf:info
                  "<grouplist>;;List of port numbers and number ranges";
              }
            }
          }
          list sg-channel {
            tailf:info
              "Associate/Remove US-SG channels into this FN";
            tailf:cli-suppress-mode;
            tailf:cli-delete-when-empty;
            tailf:cli-compact-syntax;
            tailf:cli-sequence-commands;
            key "low";
            leaf low {
              type uint8 {
                tailf:info
                  "<0-254>;;Low US SG channel";
                range "0..254";
              }
            }
            leaf high {
              tailf:cli-drop-node-name;
              tailf:cli-optional-in-sequence;
              tailf:cli-incomplete-command;
              type uint8 {
                tailf:info
                  "<0-254>;;High US SG channel";
                range "0..254";
              }
            }
            leaf Upstream-Cable {
              tailf:info
                "Upstream-Cable controller";
              tailf:cli-incomplete-command;
              type string {
                tailf:info
                  "WORD;;Controller number";
              }
            }
            leaf us-channel {
              tailf:info
                "Associate/Remove Upstream channels into this FN";
              type uint8 {
                tailf:info
                  "<0-15>;;Low Upstream us-channel";
                range "0..15";
              }
            }
            leaf us-channel-high {
              tailf:cli-drop-node-name;
              type uint8 {
                tailf:info
                  "<0-15>;;High Upstream us-channel";
                range "0..15";
              }
            }
          }
        }
        container service-group {
          tailf:info
            "Fiber node service group profile association";
          leaf profile {
            tailf:info
              "Fiber node service group profile";
            tailf:cli-remove-before-change;
            type string {
              tailf:info
                "LINE;;Fiber Node(Service Group) Profile name will be truncated to 16 characters.";
            }
          }
        }
      }
      list rpd {
        tailf:info
          "Create Cable RPD";
        tailf:cli-mode-name "config-rpd";
        key "name";
        leaf name {
          type string {
            tailf:info
              "WORD;;Unique RPD Name";
          }
        }
        uses description-grouping;
        leaf identifier {
          tailf:info
            "Identifier";
          tailf:cli-full-command;
          type string {
            tailf:info
              "H.H.H;;MAC Address of This RPD";
          }
        }
        container core-interface {
          tailf:info
            "Core-interface configuration";
          list Te {
            tailf:info
              "Ten Gigabit Ethernet";
            tailf:cli-allow-join-with-key {
              tailf:cli-display-joined;
            }
            tailf:cli-mode-name "config-rpd-core";
            key "name";
            leaf name {
              type string {
                tailf:info
                  "WORD;;TenGigabitEthernet interface number";
                pattern '[0-9]+.*';
              }
            }
            leaf principal {
              tailf:info
                "Specify the principal core";
              type empty;
            }
            list rpd-ds {
              tailf:info
                "RPD DS port";
              tailf:cli-suppress-mode;
              tailf:cli-delete-when-empty;
              tailf:cli-incomplete-command;
              key "port downstream-cable";
              leaf port {
                tailf:info
                  "<0-0>;;RPD DS port num";
                type uint8 {
                  range "0";
                }
              }
              leaf downstream-cable {
                tailf:cli-expose-key-name;
                tailf:info
                  "Downstream-Cable controller";
                type string {
                  tailf:info
                    "WORD;;Controller number";
                }
              }
              leaf profile {
                tailf:info
                  "DS controller profile";
                type uint8 {
                  tailf:info
                    "<0-255>;;Profile number";
                }
              }
            }
            list rpd-us {
              tailf:info
                "RPD DS port";
              tailf:cli-suppress-mode;
              tailf:cli-delete-when-empty;
              tailf:cli-incomplete-command;
              key "port upstream-cable";
              leaf port {
                tailf:info
                  "<0-0>;;RPD DS port num";
                type uint8 {
                  range "0";
                }
              }
              leaf upstream-cable {
                tailf:cli-expose-key-name;
                tailf:info
                  "Upstream-Cable controller";
                type string {
                  tailf:info
                    "WORD;;Controller number";
                }
              }
              leaf profile {
                tailf:info
                  "DS controller profile";
                type uint8 {
                  tailf:info
                    "<0-255>;;Profile number";
                }
              }
            }
          }
        }
        leaf r-dti {
          tailf:info
            "R-DTI set";
          type uint8 {
            tailf:info
              "<1-64>;;R-DTI configuration ID";
            range "1..64";
          }
        }
        container rpd-event {
          tailf:info
            "rpd-event profile set";
          leaf profile {
            tailf:info
              "rpd-event profile set";
            type uint8 {
              tailf:info
                "<0-63>;;rpd-event profile ID";
              range "0..63";
            }
          }
        }
        container ptp {
          tailf:info
            "PTP clock set";
          leaf profile {
            tailf:info
              "PTP clock profile set";
            type uint8 {
              tailf:info
                "<0-63>;;PTP Clock Profile ID";
              range "0..63";
            }
          }
        }
      }
      container ipv6 {
        tailf:info
          "Configure CMTS-wide IPv6 commands";
        container pd-route {
          tailf:info
            "Configure PD enclosing route";
          tailf:cli-compact-syntax;
          tailf:cli-sequence-commands;
          leaf prefix {
            tailf:cli-drop-node-name;
            tailf:cli-incomplete-command;
            type ios:ipv6-prefix {
              tailf:info
                "X:X:X:X::X/<0-128>;;IPv6 prefix";
            }
          }
          leaf Bundle {
            tailf:info
              "Virtual Bundle";
            tailf:cli-allow-join-with-value {
              tailf:cli-display-joined;
            }
            type uint8 {
              tailf:info
                "<1-255>;;Bundle interface number";
              range "1..255";
            }
          }
        }
        container source-verify {
          tailf:info
            "IPv6 Source verify";
          container leasequery-filter {
            tailf:info
              "Source verify Lease query filter";
            container downstream {
              tailf:info
                "Source verify IPv6 Lease query filter for downstream pkts";
              tailf:cli-compact-syntax;
              tailf:cli-sequence-commands;
              leaf threshold {
                tailf:cli-drop-node-name;
                tailf:cli-incomplete-command;
                type uint8 {
                  tailf:info
                    "<0-255>;;Number of ipv6 lease queries for unknown sid";
                  range "0..255";
                }
              }
              leaf interval {
                tailf:cli-drop-node-name;
                type uint8 {
                  tailf:info
                    "<1-10>;;size of time window in seconds";
                  range "1..10";
                }
              }
            }
          }
        }
      }
    }
    list l2tp-class {
      tailf:ncs-device-type "cli-ned";
      tailf:display-when "not(../ncs:module) or ../ncs:module[ncs:name='tailf-ned-cisco-ios']";
      tailf:info
        "l2tp-class configuration";
      tailf:cli-mode-name "config-l2tp-class";
      key "l2tp-class-name";
      leaf l2tp-class-name {
        type string {
          tailf:info
            "WORD;;l2tp-class name";
        }
      }
      leaf authentication {
        tailf:info
          "Authenticate the L2TP control connection";
        tailf:cli-full-command;
        type empty;
      }
      leaf hello {
        tailf:info
          "Set HELLO message interval";
        type uint16 {
          tailf:info
            "<0-1000>;;Seconds, default is 60";
          range "0..1000";
        }
        default "60";
      }
      container password {
        tailf:info
          "Password for control connection authentication, AVP hiding";
        tailf:cli-compact-syntax;
        tailf:cli-sequence-commands;
        uses password-grouping;
      }
      container retransmit {
        tailf:info
          "Control message retransmission parameters";
        leaf retries {
          tailf:info
            "Number of retries before tearing down a control connection";
          type uint16 {
            tailf:info
              "<5-1000>;;Maximum retransmissions";
            range "5..1000";
          }
        }
        container timeout {
          tailf:info
            "Control packet retransmission timeout parameters";
          choice timeout-choice {
            leaf max {
              tailf:info
                "Maximum timeout";
              type uint8 {
                tailf:info
                  "<1-8>;;Seconds";
                range "1..8";
              }
            }
            leaf min {
              tailf:info
                "Minimum timeout";
              type uint8 {
                tailf:info
                  "<1-8>;;Seconds";
                range "1..8";
              }
            }
          }
        }
        container initial {
          tailf:info
            "SCCRQ message retries/timeout settings";
          leaf retries {
            tailf:info
              "Number of initial retries before halting attempts";
            type uint16 {
              tailf:info
                "<1-1000>;;Maximum SCCRQ retransmissions";
              range "1..1000";
            }
          }
        }
      }
    }
    container packetcable {
      tailf:ncs-device-type "cli-ned";
      tailf:display-when "not(../../ncs:module) or ../../ncs:module[ncs:name='tailf-ned-cisco-ios']";
      tailf:info
        "Global packetcable configuration";
      tailf:cli-display-separated;
      presence "true";
      leaf multimedia {
        tailf:info
          "Enable Packetcable Multimedia functionality";
        type empty;
      }
      container authorize {
        tailf:info
          "authorize non-packetcable settings";
        leaf vanilla-docsis-mta {
          tailf:info
            "vanilla docsis mta";
          type empty;
        }
      }
    }
    list depi-class {
      tailf:ncs-device-type "cli-ned";
      tailf:display-when "not(../ncs:module) or ../ncs:module[ncs:name='tailf-ned-cisco-ios']";
      tailf:info
        "depi-class configuration";
      tailf:cli-mode-name "config-depi-class";
      key "depi-class-name";
      leaf depi-class-name {
        type string {
          tailf:info
            "WORD;;depi-class name";
        }
      }
      container mode {
        tailf:info
          "Set DEPI Mode";
        leaf mpt {
          tailf:info
            "MPT Mode";
          type empty;
        }
      }
      leaf l2tp-class {
        tailf:info
          "Set l2tp-class";
        tailf:non-strict-leafref {
          path "../../l2tp-class/l2tp-class-name";
        }
        type string {
          tailf:info
            "WORD;;depi-l2tp-class name";
        }
      }
    }
    list depi-tunnel {
      tailf:ncs-device-type "cli-ned";
      tailf:display-when "not(../ncs:module) or ../ncs:module[ncs:name='tailf-ned-cisco-ios']";
      tailf:info
        "depi-tunnel configuration";
      tailf:cli-mode-name "config-depi-tunnel";
      key "depi-tunnel-name";
      leaf depi-tunnel-name {
        type string {
          tailf:info
            "WORD;depi-tunnel name";
        }
      }
      leaf dest-ip {
        tailf:info
          "Set Destination IP address of Tunnel";
        type inet:ipv4-address {
          tailf:info
            "A.B.C.D;;Peer IP address";
        }
      }
      leaf l2tp-class {
        tailf:info
          "Set l2tp-class to associate depi tunnel with";
        type string {
          tailf:info
            "WORD;;L2TP class with which this depi-tunnel is associated";
        }
      }
      leaf depi-class {
        tailf:info
          "Set depi-class to associate depi tunnel with";
        type string {
          tailf:info
            "WORD;;depi-class with which this depi-tunnel is associated";
        }
      }
      leaf protect-tunnel {
        tailf:info
          "Specify protect depi-tunnel";
        type string {
          tailf:info
            "WORD;;protect depi-tunnel with which this depi-tunnel is associated";
        }
      }
    }
    list chat-script {
      tailf:ncs-device-type "cli-ned";
      tailf:display-when "not(../ncs:module) or ../ncs:module[ncs:name='tailf-ned-cisco-ios']";
      tailf:info
        "Define a modem chat script";
      tailf:cli-suppress-mode;
      tailf:cli-delete-when-empty;
      key "name";
      leaf name {
        type string {
          tailf:info
            "WORD;;Name of chat script";
        }
      }
      leaf line {
        tailf:cli-drop-node-name;
        tailf:cli-multi-value;
        tailf:cli-full-command;
        type string {
          tailf:info
            "LINE;;Chat script in form EXPECT SEND EXPECT SEND ...";
        }
      }
    }
    container autonomic {
      tailf:ncs-device-type "cli-ned";
      tailf:display-when "not(../../ncs:module) or ../../ncs:module[ncs:name='tailf-ned-cisco-ios']";
      tailf:info
        "Autonomic Networking";
      tailf:cli-incomplete-command;
      tailf:cli-incomplete-no;
      container registrar {
        tailf:info
          "Registrar";
        tailf:cli-add-mode;
        tailf:cli-mode-name "config-registrar";
        leaf domain-id {
          tailf:info
            "Autonomic Domain ID";
          type string {
            tailf:info
              "WORD;;Autonomic Domain ID in string format";
          }
        }
        container CA {
          tailf:info
            "Create a Certificate Authority";
          choice CA-choice {
            leaf local {
              tailf:info
                "Create local Certificate Authority";
              type empty;
            }
            leaf url {
              tailf:info
                "url to enroll";
              type string {
                tailf:info
                  "WORD;;HTTP URL";
              }
            }
          }
        }
        leaf whitelist {
          tailf:info
            "File with list of whitelisted devices";
          tailf:cli-full-command;
          type string {
            tailf:info
              "WORD;;File with list of whitelisted devices";
          }
        }
        leaf shut {
          tailf:info
            "Shut the Autonomic Registrar";
          tailf:cli-boolean-no;
          tailf:cli-full-command;
          type boolean;
          default "true";
        }
      }
    }
    container autonomic-enable {
      tailf:ncs-device-type "cli-ned";
      tailf:display-when "not(../../ncs:module) or ../../ncs:module[ncs:name='tailf-ned-cisco-ios']";
      tailf:cli-drop-node-name;
      leaf autonomic {
        tailf:info
          "Autonomic Networking";
        tailf:cli-full-command;
        type empty;
      }
    }
    container controller {
      tailf:ncs-device-type "cli-ned";
      tailf:display-when "not(../../ncs:module) or ../../ncs:module[ncs:name='tailf-ned-cisco-ios']";
      tailf:info
        "Configure controller";
      list controller-tx-ex-list {
        tailf:cli-mode-name "config-controller";
        tailf:cli-drop-node-name;
        key "name number";
        leaf name {
          type enumeration {
            tailf:info
              "Controller name";
            enum "T1" {
              tailf:info
                "T1 controller";
            }
            enum "E1" {
              tailf:info
                "E1 controller";
            }
            enum "T3" {
              tailf:info
                "T3 controller";
            }
          }
        }
        leaf number {
          type string {
            tailf:info
              "WORD;;slot/subslot or port[/:]port";
          }
        }
        leaf framing {
          tailf:info
            "Specify the type of Framing on a DS1 link";
          tailf:cli-full-command;
          type string;
        }
        leaf fdl {
          tailf:info
            "Specify the FDL standard for a DS1 data link";
          tailf:cli-full-command;
          type enumeration {
            enum "ansi" {
              tailf:info
                "ANSI T1.403";
            }
            enum "att" {
              tailf:info
                "AT&T TR54016";
            }
            enum "both" {
              tailf:info
                "ANSI T1.403 and AT&T TR54016";
            }
          }
        }
        list cem-group {
          tailf:info
            "Specify the timeslots to cem-group mapping";
          tailf:cli-suppress-mode;
          tailf:cli-delete-when-empty;
          tailf:cli-compact-syntax;
          key "id";
          leaf id {
            type uint8 {
              tailf:info
                "<0-30>;;Channel number";
              range "0..30";
            }
          }
          leaf unframed {
            tailf:info
              "Unframed in the cem group";
            type empty;
          }
          leaf-list timeslots {
            tailf:info
              "List of timeslots in the cem group";
            tailf:cli-range-list-syntax;
            tailf:cli-remove-before-change;
            type uint8 {
              tailf:info
                "<1-31>;List of timeslots which comprise the channel";
              range "1..31";
            }
          }
        }
        container clock {
          tailf:info
            "Specify the clock source for a DS1 link";
          container source {
            tailf:info
              "Specify the clock source for a DS1 link";
            choice source-choice {
              container line {
                tailf:info
                  "Recovered Clock";
                tailf:cli-delete-when-empty;
                presence "true";
                leaf line-mode {
                  tailf:cli-drop-node-name;
                  tailf:cli-full-command;
                  type enumeration {
                    enum "primary" {
                      tailf:info
                        "Primary Source";
                    }
                    enum "secondary";
                    enum "bits" {
                      tailf:info
                        "Bits Clocking";
                    }
                    enum "independent" {
                      tailf:info
                        "Independent Source";
                    }
                  }
                }
              }
              leaf internal {
                tailf:info
                  "Internal Clock";
                tailf:cli-full-command;
                type empty;
              }
              leaf loop-timed {
                tailf:cli-full-command;
                type empty;
              }
              leaf free-running {
                tailf:info
                  "Free Running Clock";
                tailf:cli-full-command;
                type empty;
              }
            }
          }
        }
        leaf linecode {
          tailf:info
            "Specify the line encoding method for a DS1 link";
          tailf:cli-full-command;
          type enumeration {
            enum "ami" {
              tailf:info
                "AMI encoding";
            }
            enum "b8zs" {
              tailf:info
                "B8ZS encoding";
            }
            enum "hdb3";
          }
        }
        container cablelength {
          tailf:info
            "Specify the cable length for a DS1 link";
          choice cablelength-choice {
            leaf value {
              tailf:cli-drop-node-name;
              tailf:cli-full-command;
              type uint32;
            }
            leaf long {
              tailf:info
                "long cable";
              tailf:cli-full-command;
              type string;
            }
            leaf short {
              tailf:info
                "short cable";
              tailf:cli-full-command;
              type string;
            }
          }
        }
        container pri-group {
          tailf:info
            "Configure the specified timeslots for PRI";
          list timeslots {
            tailf:info
              "List of timeslots in the pri-group";
            tailf:cli-compact-syntax;
            tailf:cli-suppress-mode;
            tailf:cli-delete-when-empty;
            tailf:cli-range-list-syntax;
            key "id";
            leaf id {
              type uint8;
            }
            leaf nfas_d {
              tailf:info
                "Specify the operation of the D-channel timeslot.";
              type enumeration {
                enum "primary";
                enum "backup";
                enum "none";
              }
            }
            leaf nfas_int {
              when "../nfas_d" {
                tailf:xpath-root 3;
                tailf:dependency "../nfas_d";
              }
              tailf:info
                "Specify the provisioned NFAS interface value.";
              type uint32 {
                tailf:info
                  "<0-48>;;The NFAS interface value.";
              }
            }
            leaf nfas_group {
              when "../nfas_int" {
                tailf:xpath-root 3;
                tailf:dependency "../nfas_int";
              }
              tailf:info
                "Specify the NFAS group.";
              type uint8 {
                range "1..24";
              }
            }
            leaf service {
              tailf:info
                "Specify the service type";
              type enumeration {
                enum "mgcp" {
                  tailf:info
                    "Media Gateway Control Protocol service";
                }
              }
            }
          }
        }
        list channel-group {
          tailf:info
            "Specify the timeslots to channel-group mapping for an interface";
          tailf:cli-suppress-mode;
          tailf:cli-delete-when-empty;
          key "number";
          leaf number {
            type uint8 {
              range "0..30";
            }
          }
          leaf-list timeslots {
            tailf:info
              "List of timeslots in the channel group";
            tailf:cli-replace-all;
            tailf:cli-range-list-syntax;
            type uint16 {
              tailf:info
                "<1-31>;;List of timeslots which comprise the channel";
            }
          }
        }
        leaf description {
          tailf:info
            "Controller specific description";
          tailf:cli-multi-value;
          tailf:cli-preformatted;
          tailf:cli-full-command;
          type string {
            tailf:info
              "LINE;;Up to 80 characters describing this interface";
          }
        }
        list t1 {
          tailf:cli-suppress-mode;
          tailf:cli-delete-when-empty;
          tailf:cli-compact-syntax;
          key "id";
          leaf id {
            type uint8;
          }
          leaf channel-group {
            type uint8 {
              range "0..23";
            }
          }
          leaf-list timeslots {
            tailf:cli-range-list-syntax;
            type uint8 {
              range "1..24";
            }
          }
          leaf speed {
            type enumeration {
              enum "56";
              enum "64";
            }
          }
          container clock {
            leaf source {
              type enumeration {
                enum "line" {
                  tailf:info
                    "Recovered Clock";
                }
                enum "internal" {
                  tailf:info
                    "Internal Clock";
                }
              }
            }
          }
        }
        container ima-group {
          tailf:info
            "Configure IMA group";
          tailf:cli-compact-syntax;
          tailf:cli-sequence-commands {
            tailf:cli-reset-siblings;
          }
          leaf group-number {
            tailf:cli-drop-node-name;
            type uint8 {
              tailf:info
                "<0-41>;;IMA group ID";
              range "0..41";
            }
          }
          leaf scrambling-payload {
            type empty;
          }
        }
        leaf shutdown {
          tailf:info
            "Shut down a DS1 link (send Blue Alarm)";
          type empty;
        }
      }
      container BITS {
        tailf:info
          "Configure BITS Interface";
        container input {
          tailf:info
            "Configure BITS input";
          container applique {
            tailf:info
              "Link type E1 or T1";
            container E1 {
              tailf:info
                "E1;;Link type E1";
              tailf:cli-compact-syntax;
              tailf:cli-sequence-commands;
              choice E1-choice {
                case clock-case {
                  leaf clock-if {
                    tailf:cli-drop-node-name;
                    type enumeration {
                      enum "2048KHz" {
                        tailf:info
                          "2048 KHz clock interface";
                      }
                    }
                  }
                }
                case framing-case {
                  leaf framing {
                    tailf:info
                      "BITS framing options for E1";
                    tailf:cli-incomplete-command;
                    type enumeration {
                      enum "fas_crc4" {
                        tailf:info
                          "FASCRC4";
                      }
                      enum "fas_nocrc" {
                        tailf:info
                          "FAS";
                      }
                      enum "mfas_crc4" {
                        tailf:info
                          "MFASCRC4";
                      }
                      enum "mfas_nocrc" {
                        tailf:info
                          "MFAS";
                      }
                    }
                  }
                  leaf linecode {
                    tailf:info
                      "BITS linecode options for E1";
                    type enumeration {
                      enum "ami" {
                        tailf:info
                          "AMI encoding";
                      }
                      enum "hdb3" {
                        tailf:info
                          "HDB3 encoding";
                      }
                    }
                  }
                }
              }
            }
          }
        }
      }
      list Cellular {
        tailf:info
          "3G/4G WWAN Cellular controller";
        tailf:cli-mode-name "config-controller";
        key "id";
        leaf id {
          type string {
            tailf:info
              "WORD;;Controller slot/subslot or port number";
            pattern '[0-9]+.*';
          }
        }
        leaf description {
          tailf:info
            "Controller specific description";
          tailf:cli-multi-value;
          tailf:cli-preformatted;
          tailf:cli-full-command;
          type string {
            tailf:info
              "LINE;;Up to 80 characters describing this interface";
            length "1..80";
          }
        }
        container lte {
          tailf:info
            "LTE type carrier";
          container gps {
            tailf:info
              "GPS configuration";
            leaf enable {
              tailf:info
                "enable GPS feature";
              type empty;
            }
            container mode {
              tailf:info
                "select GPS mode";
              leaf standalone {
                tailf:info
                  "select Standalone mode";
                type empty;
              }
            }
            container nmea {
              tailf:info
                "enable NMEA data";
              choice nmea-choice {
                container ip {
                  tailf:info
                    "NMEA over IP interface";
                  presence "true";
                }
                container serial {
                  tailf:info
                    "NMEA over serial interface";
                  presence "true";
                  leaf streaming {
                    tailf:cli-drop-node-name;
                    type enumeration {
                      enum "38400" {
                        tailf:info
                          "38400 bps, 8 databits, No parity, 1 stopbit";
                      }
                      enum "4800" {
                        tailf:info
                          "4800 bps, 8 databits, No parity, 1 stopbit (default)";
                      }
                      enum "line-config" {
                        tailf:info
                          "Use tty line configuration";
                      }
                    }
                  }
                }
              }
            }
          }
          container modem {
            tailf:info
              "Modem logging configuration";
            container link-recovery {
              tailf:info
                "Cellular Link Recovery";
              leaf enable {
                type empty;
              }
              container rssi {
                tailf:info
                  "RSSI Onset Threshold value";
                leaf onset-threshold {
                  tailf:info
                    "RSSI Onset Threshold";
                  type int8 {
                    tailf:info
                      "<-125 - -90>;;RSSI value in -dbm";
                    range "-125..-90";
                  }
                }
              }
              leaf monitor-timer {
                tailf:info
                  "Monitor Timer";
                type uint8 {
                  tailf:info
                    "<20 - 60>;;Monitor Timer value in seconds";
                  range "20..60";
                }
              }
              leaf wait-timer {
                tailf:info
                  "Wait Timer";
                type uint8 {
                  tailf:info
                    "<5 - 60>;;Wait Timer value in seconds";
                  range "5..60";
                }
              }
              leaf debounce-count {
                tailf:info
                  "Debounce Count";
                type uint8 {
                  tailf:info
                    "<6 - 20>;;Debounce Count value";
                  range "6..20";
                }
              }
            }
          }
        }
      }
      list VDSL {
        tailf:info
          "VDSL2 controller";
        tailf:cli-mode-name "config-controller";
        key "id";
        leaf id {
          type string {
            tailf:info
              "WORD;;Controller slot/subslot or port number";
            pattern '[0-9]+.*';
          }
        }
        leaf description {
          tailf:info
            "Controller specific description";
          tailf:cli-multi-value;
          tailf:cli-preformatted;
          tailf:cli-full-command;
          type string {
            tailf:info
              "LINE;;Up to 80 characters describing this interface";
            length "1..80";
          }
        }
      }
      list Upstream-Cable {
        tailf:info
          "Upstream-Cable controller";
        tailf:cli-mode-name "config-controller";
        key "name";
        leaf name {
          type string {
            tailf:info
              "WORD;;Controller slot/subslot/unit";
          }
        }
        uses description-grouping;
        uses us-channel-grouping;
      }
      list Downstream-Cable {
        tailf:info
          "Downstream-Cable controller";
        tailf:cli-mode-name "config-controller";
        key "name";
        leaf name {
          type string {
            tailf:info
              "WORD;;Controller slot/subslot/unit";
          }
        }
        uses description-grouping;
      }
      list Modular-Cable {
        tailf:info
          "Modular-Cable controller";
        tailf:cli-mode-name "config-controller";
        key "name";
        leaf name {
          type string {
            tailf:info
              "WORD;;Controller slot/subslot/unit";
          }
        }
        uses description-grouping;
        leaf ip-address {
          tailf:info
            "Configure IP address";
          type inet:ipv4-address {
            tailf:info
              "A.B.C.D;;IP address of Blaze";
          }
        }
        container modular-host {
          tailf:info
            "Configure modular host";
          leaf subslot {
            tailf:info
              "Configure slot";
            tailf:cli-remove-before-change;
            type string {
              tailf:info
                "WORD;;slot/subslot";
            }
          }
        }
        uses controller-modular-cable-rf-channel-grouping;
      }
      list Integrated-Cable {
        tailf:info
          "Integrated-Cable controller";
        tailf:cli-mode-name "config-controller";
        key "name";
        leaf name {
          type string {
            tailf:info
              "WORD;;Controller slot/subslot/unit";
          }
        }
        uses description-grouping;
        leaf max-carrier {
          tailf:info
            "Max Carrier of a RF Port";
          type uint8 {
            tailf:info
              "<1-128>;;RF Port Max Carrier Value";
            range "1..128";
          }
        }
        leaf base-channel-power {
          tailf:info
            "set base channel power level";
          type uint8 {
            tailf:info
              "<28-39>;;Base Channel Power Value in dBmV";
          }
        }
        leaf freq-profile {
          tailf:info
            "Frequency Profile of a RF Port";
          type uint8 {
            tailf:info
              "<0-15>;;RF Port Frequency Profile Number";
            range "0..15";
          }
        }
        container rf-chan {
          tailf:info
            "Configure RF Channel";
          list rf-chan {
            tailf:cli-drop-node-name;
            tailf:cli-mode-name "config-rf-chan";
            key "start";
            leaf start {
              type uint8 {
                tailf:info
                  "<0-127>;;Starting Qam ID";
              }
            }
            uses controller-integrated-cable-rf-chan-grouping;
          }
          list rf-chan-range {
            tailf:cli-drop-node-name;
            tailf:cli-mode-name "config-rf-chan";
            key "start end";
            leaf start {
              type uint8 {
                tailf:info
                  "<0-127>;;Starting Qam ID";
              }
            }
            leaf end {
              type uint8 {
                tailf:info
                  "<0-127>;;Ending Qam ID";
              }
            }
            uses controller-integrated-cable-rf-chan-grouping;
          }
        }
      }
      list wanphy {
        tailf:info
          "WANPHY controller";
        tailf:cli-mode-name "config-controller";
        key "name";
        leaf name {
          type string {
            tailf:info
              "WORD;;Controller slot/subslot/unit";
          }
        }
      }
      list dwdm {
        tailf:info
          "DWDM controller";
        tailf:cli-mode-name "config-controller";
        key "name";
        leaf name {
          type string {
            tailf:info
              "WORD;;Controller slot/subslot";
          }
        }
        leaf shutdown {
          tailf:info
            "Shut down the controller";
          type empty;
        }
      }
      list SONET {
        tailf:info
          "Channelized SONET/SDH controller";
        tailf:cli-mode-name "config-controller";
        key "name";
        leaf name {
          type string {
            tailf:info
              "WORD;;Controller slot/subslot/unit";
          }
        }
        leaf description {
          tailf:info
            "Controller specific description";
          tailf:cli-multi-value;
          tailf:cli-preformatted;
          tailf:cli-full-command;
          type string {
            tailf:info
              "LINE;;Up to 240 characters describing this controller";
            length "1..240";
          }
        }
        leaf shutdown {
          tailf:info
            "Shut down the Sonet/SDH controller";
          type empty;
        }
        leaf rate {
          tailf:info
            "Set the SONET/SDH rates";
          tailf:cli-remove-before-change;
          tailf:cli-full-command;
          type string {
            tailf:info
              "OC<X>;;Set the controller to OC<X> rate";
            pattern 'OC.*';
          }
        }
        leaf ais-shut {
          tailf:info
            "Send LAIS when shutdown";
          tailf:cli-boolean-no;
          tailf:cli-full-command;
          type boolean;
        }
        leaf TU-AIS {
          tailf:cli-boolean-no;
          tailf:cli-full-command;
          type boolean;
          default "true";
        }
        leaf alarm-report {
          tailf:info
            "Enable reporting of selected alarms";
          type enumeration {
            enum "all" {
              tailf:info
                "All alarm reports";
            }
          }
        }
        container threshold {
          tailf:info
            "Set BER threshold values";
          leaf sf-ber {
            tailf:info
              "set Signal Fail BER threshold";
            type uint8 {
              tailf:info
                "<3-5>;;Bit error rate (10 to the minus n)";
              range "3..5";
            }
          }
        }
        leaf framing {
          tailf:info
            "Configure to use in Sonet or SDH mode";
          tailf:cli-full-command;
          type enumeration {
            enum "sdh" {
              tailf:info
                "Use SDH Framing";
            }
            enum "sonet" {
              tailf:info
                "Use Sonet Framing";
            }
          }
        }
        container clock {
          tailf:info
            "Specify the clock source for Sonet/SDH port";
          leaf source {
            tailf:info
              "Specify the clock source for Sonet/SDH port";
            tailf:cli-full-command;
            type enumeration {
              enum "line" {
                tailf:info
                  "Recovered Clock";
              }
              enum "internal" {
                tailf:info
                  "Internal Clock";
              }
            }
          }
        }
        container aug {
          tailf:info
            "Specify AU-3 or AU-4 mapping";
          leaf mapping {
            tailf:info
              "Specify AU-3 or AU-4 mapping";
            type enumeration {
              enum "au-3" {
                tailf:info
                  "AU-3";
              }
              enum "au-4" {
                tailf:info
                  "AU-4 (default)";
              }
            }
          }
        }
        container overhead {
          tailf:info
            "Specify overhead settings";
          leaf j0 {
            tailf:info
              "Set the j0 trace byte";
            type uint8 {
              tailf:info
                "<0-255>;;j0 trace byte";
            }
          }
        }
        list au-3 {
          tailf:info
            "Specify au-3 number";
          tailf:cli-mode-name "config-ctrlr-au3";
          key "id";
          leaf id {
            type uint8 {
              tailf:info
                "<1-3>;;au-3 number";
              range "1..3";
            }
          }
          container overhead {
            tailf:info
              "Configure sonet path overhead flags";
            container j1 {
              tailf:info
                "Path trace buffer config";
              tailf:cli-compact-syntax;
              leaf length {
                tailf:info
                  "Path trace buffer length (16 or 64 bytes)";
                type enumeration {
                  enum "16" {
                    tailf:info
                      "Path trace buffer length, 16 bytes";
                  }
                  enum "64" {
                    tailf:info
                      "Path trace buffer length, 64 bytes";
                  }
                }
              }
            }
          }
          leaf mode {
            tailf:info
              "Specify path operation mode";
            tailf:cli-full-command;
            type enumeration {
              enum "c-11" {
                tailf:info
                  "Mode C-11";
              }
            }
          }
          list tug-2 {
            tailf:info
              "Tug-2 configuration";
            tailf:cli-suppress-mode;
            tailf:cli-delete-when-empty;
            tailf:cli-incomplete-command;
            key "tug-2 t1";
            leaf tug-2 {
              type uint8 {
                tailf:info
                  "<1-7>;;Tug-2 number <1-7>";
                range "1..7";
              }
            }
            leaf t1 {
              tailf:info
                "T1 line configuration";
              tailf:cli-expose-key-name;
              type uint8 {
                tailf:info
                  "<1-3>;;E1 line number <1-4>";
                range "1..4";
              }
            }
            container clock {
              tailf:info
                "Specify the clock source for a T1";
              leaf source {
                tailf:info
                  "Specify the clock source for a T1";
                tailf:cli-full-command;
                type enumeration {
                  enum "line" {
                    tailf:info
                      "Line Recovered Clock";
                  }
                  enum "internal" {
                    tailf:info
                      "Internal Clock";
                  }
                }
              }
            }
          }
        }
        list au-4 {
          tailf:info
            "Specify AU-4 number and TUG-3 number";
          tailf:cli-suppress-mode;
          tailf:cli-delete-when-empty;
          tailf:cli-incomplete-command;
          key "id";
          leaf id {
            type uint8 {
              tailf:info
                "<1-4>;;au-4 number";
              range "1..4";
            }
          }
          container threshold {
            tailf:info
              "Set Path BER threshold values";
            leaf b3-tca {
              tailf:info
                "B3 BER threshold crossing alarm";
              type uint8 {
                tailf:info
                  "<3-9>;;Bit error rate (10 to the minus n)";
                range "3..9";
              }
            }
          }
          list tug-3 {
            tailf:info
              "TUG-3 number";
            tailf:cli-mode-name "config-ctrlr-tug3";
            key "id";
            leaf id {
              type uint8 {
                tailf:info
                  "<1-3>;;tug-3 number <1..3>";
                range "1..3";
              }
            }
            leaf mode {
              tailf:info
                "Specify path operation mode";
              tailf:cli-full-command;
              type enumeration {
                enum "c-12" {
                  tailf:info
                    "Mode C-12";
                }
              }
            }
            list tug-2 {
              tailf:info
                "Tug-2 configuration";
              tailf:cli-suppress-mode;
              tailf:cli-delete-when-empty;
              tailf:cli-incomplete-command;
              key "tug-2 e1";
              leaf tug-2 {
                type uint8 {
                  tailf:info
                    "<1-7>;;Tug-2 number <1-7>";
                  range "1..7";
                }
              }
              leaf e1 {
                tailf:info
                  "E1 line configuration";
                tailf:cli-expose-key-name;
                type uint8 {
                  tailf:info
                    "<1-3>;;E1 line number <1-3>";
                  range "1..3";
                }
              }
              container ima-group {
                tailf:info
                  "Configure IMA group";
                leaf group-number {
                  tailf:cli-drop-node-name;
                  type uint8 {
                    tailf:info
                      "<0-41>;;IMA group ID";
                    range "0..41";
                  }
                }
              }
              list channel-group {
                tailf:info
                  "Specify the timeslots to channel-group mapping for an E1 interface";
                tailf:cli-suppress-mode;
                tailf:cli-delete-when-empty;
                key "id";
                leaf id {
                  type uint8 {
                    tailf:info
                      "<0-30>;;Channel group number";
                    range "0..30";
                  }
                }
                leaf-list timeslots {
                  tailf:info
                    "List of timeslots in the channel group";
                  tailf:cli-replace-all;
                  tailf:cli-range-list-syntax;
                  type uint16 {
                    tailf:info
                      "<1-31>;;List of timeslots which comprise the channel";
                    range "1..31";
                  }
                }
              }
              list cem-group {
                tailf:info
                  "Specify the timeslots to cem-group mapping";
                tailf:cli-suppress-mode;
                tailf:cli-delete-when-empty;
                key "id";
                leaf id {
                  type uint8 {
                    tailf:info
                      "<0-64>;;Channel number";
                    range "0..64";
                  }
                }
                leaf unframed {
                  tailf:info
                    "Unframed in the cem group";
                  tailf:cli-full-command;
                  type empty;
                }
                leaf-list timeslots {
                  tailf:info
                    "List of timeslots in the cem group";
                  tailf:cli-range-list-syntax;
                  tailf:cli-remove-before-change;
                  tailf:cli-full-command;
                  type uint8 {
                    tailf:info
                      "<1-31>;List of timeslots which comprise the channel";
                    range "1..31";
                  }
                }
              }
              leaf framing {
                tailf:info
                  "Specify the type of Framing on an E1 line";
                type enumeration {
                  enum "crc4" {
                    tailf:info
                      "E1 with CRC";
                  }
                  enum "no-crc4" {
                    tailf:info
                      "E1 with no CRC";
                  }
                  enum "unframed" {
                    tailf:info
                      "No Framing Format";
                  }
                }
              }
              leaf unframed {
                tailf:info
                  "Unframed E1";
                type empty;
              }
              container clock {
                tailf:info
                  "Specify the clock source for Sonet/SDH port";
                leaf source {
                  tailf:info
                    "Specify the clock source for Sonet/SDH port";
                  tailf:cli-full-command;
                  type enumeration {
                    enum "line" {
                      tailf:info
                        "Recovered Clock";
                    }
                    enum "internal" {
                      tailf:info
                        "Internal Clock";
                    }
                  }
                }
              }
            }
          }
        }
        container sts-3c {
          tailf:cli-drop-node-name;
          list sts-1 {
            tailf:info
              "Specify STS-1 number";
            tailf:cli-mode-name "config-ctrlr-sts3c";
            tailf:cli-incomplete-command;
            key "id";
            leaf id {
              type string {
                tailf:info
                  "<sts-1 start> - <sts-1 end>";
              }
            }
            leaf mode {
              tailf:info
                "mode to configure sts-3c";
              tailf:cli-hide-in-submode;
              type enumeration {
                enum "sts-3c" {
                  tailf:info
                    "to assign set of sts as sts-3c";
                }
              }
            }
            container cem-group {
              tailf:info
                "Specify the timeslots to cem-group mapping";
              tailf:cli-compact-syntax;
              tailf:cli-sequence-commands {
                tailf:cli-reset-siblings;
              }
              leaf id {
                tailf:cli-drop-node-name;
                tailf:cli-remove-before-change;
                tailf:cli-incomplete-command;
                type uint16 {
                  tailf:info
                    "<0-5375>;;Channel number";
                  range "0..5375";
                }
              }
              leaf cep {
                tailf:info
                  "cep configuration";
                type empty;
              }
            }
            container clock {
              tailf:info
                "Specify the clock source for a PATH";
              leaf source {
                tailf:info
                  "Specify the clock source for a PATH";
                type enumeration {
                  enum "line" {
                    tailf:info
                      "Line Recovered Clock";
                  }
                  enum "internal" {
                    tailf:info
                      "Internal Clock";
                  }
                  enum "recovered" {
                    tailf:info
                      "packet recovered Clock";
                  }
                  enum "enhanced" {
                    tailf:info
                      "enhanced Clock";
                  }
                }
              }
            }
          }
        }
        list sts-1 {
          tailf:info
            "Specify STS-1 number";
          tailf:cli-mode-name "config-ctrlr-sts1";
          tailf:cli-full-command;
          key "id";
          leaf id {
            type uint8 {
              tailf:info
                "<1-12>;;sts-1 number";
              range "1..12";
            }
          }
          container clock {
            tailf:info
              "Specify the clock source for a PATH";
            leaf source {
              tailf:info
                "Specify the clock source for a PATH";
              type enumeration {
                enum "line" {
                  tailf:info
                    "Line Recovered Clock";
                }
                enum "internal" {
                  tailf:info
                    "Internal Clock";
                }
                enum "recovered" {
                  tailf:info
                    "packet recovered Clock";
                }
                enum "enhanced" {
                  tailf:info
                    "enhanced Clock";
                }
              }
            }
          }
          container cem-group {
            tailf:info
              "Specify the timeslots to cem-group mapping";
            tailf:cli-compact-syntax;
            tailf:cli-sequence-commands {
              tailf:cli-reset-siblings;
            }
            when "../mode/t3" {
              tailf:xpath-root 3;
              tailf:dependency "../mode/t3";
            }
            leaf id {
              tailf:cli-drop-node-name;
              tailf:cli-remove-before-change;
              tailf:cli-incomplete-command;
              tailf:cli-diff-dependency "../../mode/t3" {
                tailf:xpath-root 3;
              }
              type uint16 {
                tailf:info
                  "<0-5375>;;Channel number";
                range "0..5375";
              }
            }
            leaf unframed {
              tailf:info
                "Unframed in the cem group";
              type empty;
            }
          }
          container t3 {
            tailf:info
              "t3 configuration";
            when "../mode/t3" {
              tailf:xpath-root 3;
              tailf:dependency "../mode/t3";
            }
            tailf:cli-diff-dependency "../mode/t3" {
              tailf:xpath-root 3;
            }
            container clock {
              tailf:info
                "Specify the clock source for a T3 link";
              leaf source {
                tailf:info
                  "Specify the clock source for a T3 link";
                type enumeration {
                  enum "line" {
                    tailf:info
                      "Line Recovered Clock";
                  }
                  enum "internal" {
                    tailf:info
                      "Internal Clock";
                  }
                  enum "recovered" {
                    tailf:info
                      "Recovered Clock";
                  }
                }
              }
            }
          }
          container vtg {
            tailf:info
              "vt-15 configuration";
            when "../mode/vt-15" {
              tailf:xpath-root 3;
              tailf:dependency "../mode/vt-15";
            }
            tailf:cli-diff-dependency "../mode/vt-15" {
              tailf:xpath-root 3;
            }
          }
          container mode {
            tailf:info
              "Specify path operation mode";
            choice mode-choice {
              leaf ct3 {
                tailf:info
                  "Mode CT3";
                type empty;
              }
              leaf ct3-e1 {
                tailf:info
                  "Mode CT3-E1";
                type empty;
              }
              leaf t3 {
                tailf:info
                  "Mode T3";
                type empty;
              }
              leaf unframed {
                tailf:info
                  "Mode UNFRAMED";
                type empty;
              }
              leaf vt-15 {
                tailf:info
                  "Mode VT-15";
                type empty;
              }
              leaf vt-2 {
                tailf:info
                  "MODE VT-2";
                type empty;
              }
            }
          }
        }
      }
      list ISA {
        tailf:info
          "ISA controller";
        tailf:cli-mode-name "config-controller";
        key "name";
        leaf name {
          type string {
            tailf:info
              "WORD;;Controller slot/subslot[/unit]";
          }
        }
      }
      list nid {
        tailf:info
          "NID controller";
        tailf:cli-mode-name "config-controller";
        key "name";
        leaf name {
          type string {
            tailf:info
              "WORD;;Controller slot/subslot[/unit]";
          }
        }
      }
      list MediaType {
        tailf:info
          "Generic MediaType Controller";
        tailf:cli-mode-name "config-controller";
        key "name";
        leaf name {
          type string {
            tailf:info
              "WORD;;Controller slot/subslot[/unit]";
          }
        }
        uses description-grouping;
        leaf mode {
          tailf:info
            "MediaType mode";
          tailf:cli-full-command;
          type enumeration {
            enum "ethernet" {
              tailf:info
                "Ethernet";
            }
            enum "sonet" {
              tailf:info
                "Sonet / SDH";
            }
            enum "t3" {
              tailf:info
                "T3";
            }
          }
        }
      }
    }
    container vc-class {
      tailf:ncs-device-type "cli-ned";
      tailf:display-when "not(../../ncs:module) or ../../ncs:module[ncs:name='tailf-ned-cisco-ios']";
      tailf:info
        "Configure per VC parameters";
      list atm {
        tailf:info
          "Asynchronous transfer mode";
        tailf:cli-mode-name "config-vc-class";
        key "name";
        leaf name {
          type string {
            tailf:info
              "WORD;;VC-Class name";
          }
        }
        container vbr-nrt {
          tailf:info
            "Enter Variable Bit Rate (pcr)(scr)(bcs)";
          tailf:cli-compact-syntax;
          tailf:cli-sequence-commands {
            tailf:cli-reset-siblings;
          }
          leaf pcr {
            tailf:cli-drop-node-name;
            tailf:cli-incomplete-command;
            type uint16 {
              tailf:info
                "<16-4608>;;Peak Cell Rate(PCR) in Kbps";
              range "16..4608";
            }
          }
          leaf scr {
            tailf:cli-drop-node-name;
            type uint16 {
              tailf:info
                "<16-PCR>;;Sustainable Cell Rate(SCR) in Kbps";
              range "16..4608";
            }
          }
          leaf mbs {
            tailf:cli-drop-node-name;
            type uint16 {
              tailf:info
                "<1-64000>;;Maximum Burst Size(MBS) in Cells";
              range "1..64000";
            }
          }
        }
      }
    }
    container fhrp {
      tailf:ncs-device-type "cli-ned";
      tailf:display-when "not(../../ncs:module) or ../../ncs:module[ncs:name='tailf-ned-cisco-ios']";
      tailf:info
        "Configure First Hop Redundancy Protocols";
      container version {
        tailf:info
          "Configure which FHRP version is allowed to run";
        leaf vrrp {
          tailf:info
            "Configure Virtual Router Rendundancy Protocol";
          type enumeration {
            enum "v2" {
              tailf:info
                "Legacy VRRP - VRRPv2 for IPv4";
            }
            enum "v3" {
              tailf:info
                "Unified VRRP - VRRPv3 for IPv4 and IPv6";
            }
          }
          default "v2";
        }
      }
    }
    container ip {
      tailf:ncs-device-type "cli-ned";
      tailf:display-when "not(../../ncs:module) or ../../ncs:module[ncs:name='tailf-ned-cisco-ios']";
      tailf:info
        "Global IP configuration subcommands";
      leaf subnet-zero {
        tailf:info
          "Allow 'subnet zero' subnets";
        tailf:cli-boolean-no;
        tailf:cli-full-command;
        type boolean;
        default "true";
      }
      leaf source-route {
        tailf:info
          "Process packets with source routing header options";
        tailf:cli-boolean-no;
        tailf:cli-show-with-default;
        tailf:cli-full-command;
        type boolean;
        default "true";
      }
      leaf routing {
        tailf:info
          "Enable IP routing";
        tailf:cli-boolean-no;
        tailf:cli-full-command;
        tailf:cli-diff-dependency "../../router" {
          tailf:xpath-root 3;
          tailf:cli-trigger-on-set;
        }
        type boolean;
        default "true";
      }
      container routing-conf {
        tailf:cli-drop-node-name;
        container routing {
          tailf:info
            "Enable IP routing";
          container protocol {
            tailf:info
              "IP routing protocol";
            container purge {
              tailf:info
                "routes purge";
              leaf interface {
                tailf:info
                  "Perform IP routing protocol routes purge on link failures";
                tailf:cli-boolean-no;
                type boolean;
                default "true";
              }
            }
          }
        }
      }
      container options {
        tailf:info
          "IP Options treatment";
        leaf drop {
          tailf:info
            "Drop all IP options packets";
          tailf:cli-full-command;
          type empty;
        }
      }
      container auth-proxy {
        tailf:info
          "Authentication Proxy";
        leaf max-login-attempts {
          tailf:info
            "Max Login failures per user";
          type uint32 {
            tailf:info
              "<1-2147483647>;;Number of login failures (retries)";
            range "1..2147483647";
          }
        }
        leaf max-nodata-conns {
          tailf:info
            "Max TCP NODATA Connections";
          type uint16 {
            tailf:info
              "<1-1000>;;Number of TCP NODATA";
            range "1..1000";
          }
          default "3";
        }
      }
      container admission {
        tailf:info
          "Network Admission Control (NAC)";
        leaf max-login-attempts {
          tailf:info
            "Max Login failures per user";
          type uint32 {
            tailf:info
              "<1-2147483647>;;Number of login failures (retries)";
            range "1..2147483647";
          }
        }
        leaf max-nodata-conns {
          tailf:info
            "Max TCP NODATA Connections";
          type uint16 {
            tailf:info
              "<1-1000>;;Number of TCP NODATA";
            range "1..1000";
          }
        }
      }
      container arp {
        tailf:info
          "IP ARP global configuration";
        container proxy {
          tailf:info
            "Global proxy ARP configuration";
          leaf disable {
            tailf:info
              "Disable proxy ARP on all interfaces";
            tailf:cli-full-command;
            type empty;
          }
        }
        container inspection {
          tailf:info
            "Arp Inspection configuration";
          leaf-list bridge-domain {
            tailf:info
              "Enable/Disable ARP Inspection on bridge-domains";
            tailf:cli-range-list-syntax;
            type uint16 {
              tailf:info
                "WORD;;bridge-domain range, example: 1,3-5,7,9-11";
              range "1..4094";
            }
          }
          container bridge-domain-list {
            tailf:cli-drop-node-name;
            list bridge-domain {
              tailf:info
                "Enable/Disable ARP Inspection on bridge-domains";
              tailf:cli-suppress-mode;
              tailf:cli-delete-when-empty;
              tailf:cli-compact-syntax;
              tailf:cli-incomplete-command;
              key "id";
              leaf id {
                type uint16 {
                  tailf:info
                    "WORD;;bridge-domain range, example: 1,3-5,7,9-11";
                  range "1..4094";
                }
              }
              container logging {
                tailf:cli-flatten-container;
                choice logging-choice {
                  leaf acl-match {
                    tailf:info
                      "Logging of packets that match ACLs";
                    type enumeration {
                      enum "matchlog" {
                        tailf:info
                          "Log packets on ACE logging configuration";
                      }
                      enum "none" {
                        tailf:info
                          "Do not log packets that match ACLs";
                      }
                    }
                  }
                  leaf dhcp-bindings {
                    tailf:info
                      "Logging of packet that match DHCP bindings";
                    type enumeration {
                      enum "all" {
                        tailf:info
                          "Log all packets that match DHCP bindings";
                      }
                      enum "none" {
                        tailf:info
                          "Do not log packets that match DHCP bindings";
                      }
                      enum "permit" {
                        tailf:info
                          "Log DHCP Binding Permitted packets";
                      }
                    }
                  }
                }
              }
            }
          }
          leaf-list validate {
            tailf:info
              "Validate addresses";
            tailf:cli-flat-list-syntax {
              tailf:cli-replace-all;
            }
            type enumeration {
              enum "src-mac" {
                tailf:info
                  "Validate source MAC address";
              }
              enum "dst-mac" {
                tailf:info
                  "Validate destination MAC address";
              }
              enum "ip" {
                tailf:info
                  "Validate IP addresses";
              }
            }
          }
          container log-buffer {
            tailf:info
              "Log Buffer Configuration";
            leaf entries {
              tailf:info
                "Number of entries for log buffer";
              type uint16 {
                tailf:info
                  "<0-1024>;;Number of entries for log buffer";
                range "0..1024";
              }
            }
            container logs {
              tailf:info
                "Number of logs per interval";
              tailf:cli-compact-syntax;
              tailf:cli-sequence-commands;
              leaf number {
                tailf:cli-drop-node-name;
                tailf:cli-incomplete-command;
                type uint16 {
                  tailf:info
                    "<0-1024>;;Number of entries";
                  range "0..1024";
                }
              }
              leaf interval {
                tailf:info
                  "Interval for controlling logging rate";
                type uint32 {
                  tailf:info
                    "<0-86400>;;Interval (seconds)";
                }
              }
            }
          }
          leaf-list vlan {
            tailf:info
              "Enable/Disable ARP Inspection on vlans";
            tailf:cli-range-list-syntax;
            type uint16 {
              tailf:info
                "WORD;;vlan range, example: 1,3-5,7,9-11";
            }
          }
          list filter {
            tailf:info
              "Specify ARP acl to be applied";
            tailf:cli-suppress-mode;
            tailf:cli-delete-when-empty;
            tailf:cli-compact-syntax;
            tailf:cli-incomplete-command;
            key "name";
            leaf name {
              type string {
                tailf:info
                  "WORD;;ARP acl name";
              }
            }
            leaf-list vlan {
              tailf:info
                "Vlans to apply the filter";
              tailf:cli-range-list-syntax;
              type uint16 {
                tailf:info
                  "WORD;;vlan range, example: 1,3-5,7,9-11";
                range "1..4094";
              }
            }
          }
        }
      }
      choice gratuitous-arps-choice {
        container gratuitous-arps-conf {
          tailf:cli-drop-node-name;
          leaf gratuitous-arps {
            tailf:info
              "Generate gratuitous ARPs for PPP/SLIP peer addresses";
            tailf:cli-boolean-no;
            tailf:cli-full-command;
            type boolean;
          }
        }
        container gratuitous-arps {
          tailf:cli-incomplete-command;
          tailf:cli-incomplete-no;
          leaf non-local {
            tailf:info
              "Send only non-local PPP/SLIP gratuitous ARPs (default)";
            tailf:cli-boolean-no;
            tailf:cli-full-command;
            type boolean;
            default "true";
          }
        }
        default "gratuitous-arps";
      }
      container cef-conf {
        tailf:cli-drop-node-name;
        leaf cef {
          tailf:info
            "Cisco Express Forwarding";
          tailf:cli-show-no;
          type empty;
        }
      }
      container cef {
        tailf:info
          "Cisco Express Forwarding";
        tailf:cli-incomplete-no;
        tailf:cli-incomplete-command;
        tailf:cli-diff-dependency "../cef-conf/cef" {
          tailf:xpath-root 3;
        }
        leaf distributed {
          tailf:info
            "Distributed Cisco Express Forwarding";
          tailf:cli-full-command;
          type empty;
        }
        container optimize {
          tailf:info
            "Optimizations";
          container neighbor {
            tailf:info
              "Optimizations for directly connected neighbors";
            leaf resolution {
              tailf:info
                "Trigger layer 2 address resolution directly from CEF";
              tailf:cli-boolean-no;
              tailf:cli-full-command;
              type boolean;
              default "true";
            }
          }
        }
        container load-sharing {
          tailf:info
            "Load sharing";
          container algorithm {
            tailf:info
              "Per-destination load sharing algorithm selection";
            choice algorithm-choice {
              default "universal";
              leaf original {
                tailf:info
                  "Original algorithm";
                type empty;
              }
              container universal {
                tailf:info
                  "Algorithm for use in most environments";
                tailf:cli-delete-when-empty;
                presence "true";
                leaf id {
                  tailf:cli-drop-node-name;
                  type string {
                    tailf:info
                      "<1-FFFFFFFF>;;Fixed ID";
                  }
                }
              }
            }
          }
        }
      }
      list vrf {
        tailf:info
          "Configure an IP VPN Routing/Forwarding instance";
        tailf:cli-mode-name "config-vrf";
        tailf:cli-explicit-exit;
        key "name";
        leaf name {
          tailf:cli-diff-dependency "../../../vrf/definition" {
            tailf:xpath-root 3;
          }
          type string {
            tailf:info
              "WORD;;VPN Routing/Forwarding instance name";
          }
        }
        leaf description {
          tailf:info
            "VRF specific description";
          tailf:cli-multi-value;
          tailf:cli-preformatted;
          tailf:cli-full-command;
          type string {
            tailf:info
              "LINE;;Up to 244 characters describing this VRF";
            length "1..244";
          }
        }
        leaf rd {
          tailf:info
            "Specify Route Distinguisher";
          tailf:cli-full-command;
          tailf:cli-remove-before-change;
          type rd-type;
        }
        container vpn {
          tailf:info
            "Configure VPN ID as specified in rfc2685";
          leaf id {
            tailf:info
              "Configure VPN ID in rfc2685 format";
            type vpn-id-type;
          }
        }
        leaf context {
          tailf:info
            "Associate SNMP context with this vrf";
          type string {
            tailf:info
              "WORD;;SNMP Context Name";
          }
        }
        container import {
          tailf:info
            "VRF import";
          leaf map {
            tailf:info
              "Route-map based VRF import";
            tailf:cli-full-command;
            tailf:cli-diff-dependency "../ipv4" {
              tailf:xpath-root 3;
              tailf:cli-trigger-on-set;
            }
            type string {
              tailf:info
                "WORD;;VRF import route-map name";
            }
          }
          container ipv4 {
            tailf:info
              "Address family based VRF import";
            tailf:cli-compact-syntax;
            tailf:cli-sequence-commands;
            tailf:cli-diff-dependency "../map" {
              tailf:xpath-root 3;
              tailf:cli-trigger-on-set;
            }
            leaf ipv4-type {
              tailf:cli-drop-node-name;
              type enumeration {
                enum "unicast" {
                  tailf:info
                    "Import prefixes from IPv4 Unicast table";
                }
                enum "multicast" {
                  tailf:info
                    "Import prefixes from IPv4 Multicast table";
                }
              }
            }
            leaf upper-limit {
              tailf:cli-break-sequence-commands;
              tailf:cli-drop-node-name;
              type uint32 {
                tailf:info
                  "<1-2147483647>;;Upper limit on import prefixes without hogging memory";
                range "1..2147483647";
              }
            }
            leaf map {
              tailf:info
                "Route-map based VRF import";
              type string {
                tailf:info
                  "WORD;;VRF import route-map name";
              }
            }
          }
        }
        container export {
          tailf:info
            "VRF export";
          leaf map {
            tailf:info
              "Route-map based VRF export";
            type string {
              tailf:info
                "WORD;;VRF export route-map name";
            }
          }
        }
        container maximum {
          tailf:info
            "Set a limit";
          tailf:cli-compact-syntax;
          tailf:cli-sequence-commands;
          tailf:cli-incomplete-command;
          presence "true";
          leaf routes {
            tailf:info
              "Maximum number of routes allowed in this routing table";
            tailf:cli-incomplete-command;
            type uint32 {
              tailf:info
                "<1-4294967295>;;Maximum number of routes allowed";
              range "1..4294967295";
            }
          }
          choice maximum-choice {
            case threshold-case {
              leaf threshold {
                tailf:cli-drop-node-name;
                type uint16 {
                  tailf:info
                    "<1-100>;;Threshold value (%) at which to generate a warning msg";
                  range "1..100";
                }
              }
              leaf reinstall {
                tailf:info
                  "Reinstall previous rejected route due to over maximum route limit";
                type uint16 {
                  tailf:info
                    "<1-100>;;Threshold value (%) at which to reinstall routes back to VRF";
                  range "1..100";
                }
              }
            }
            case warning-case {
              leaf warning-only {
                tailf:info
                  "Only give a warning message if is limit exceeded";
                type empty;
              }
            }
          }
        }
        container bgp {
          tailf:info
            "Commands pertaining to BGP";
          container next-hop {
            tailf:info
              "Next-hop for the routes of a VRF in the backbone";
            leaf Loopback {
              tailf:info
                "Loopback interface number";
              tailf:cli-allow-join-with-value {
                tailf:cli-display-joined;
              }
              type uint32 {
                tailf:info
                  "<0-2147483647>;;Loopback interface number";
                range "0..2147483647";
              }
            }
          }
        }
        container mdt {
          tailf:info
            "Backbone Multicast Distribution Tree";
          tailf:cli-incomplete-command;
          presence "Backbone Multicast Distribution Tree";
          leaf default {
            tailf:info
              "The default group";
            type inet:ipv4-address {
              tailf:info
                "A.B.C.D;;IP multicast group address";
            }
          }
          container data {
            tailf:info
              "MDT data group range";
            tailf:cli-compact-syntax;
            tailf:cli-sequence-commands;
            tailf:cli-incomplete-command;
            leaf mulicast-address {
              tailf:cli-drop-node-name;
              tailf:cli-incomplete-command;
              type inet:ipv4-address {
                tailf:info
                  "A.B.C.D;;IP multicast group address";
              }
            }
            leaf wildcard-bits {
              tailf:cli-drop-node-name;
              type inet:ipv4-address {
                tailf:info
                  "A.B.C.D;;Wildcard bits";
              }
            }
            choice mdt-data-choice {
              case mdt-data-threshold {
                leaf threshold {
                  tailf:info
                    "MDT switching threshold";
                  type uint32 {
                    tailf:info
                      "<1-4294967>;;Traffic rate in kilobits per second";
                    range "1..4294967";
                  }
                }
                leaf threshold-list {
                  tailf:info
                    "Access-list";
                  tailf:alt-name "list";
                  type ext-acl-type;
                }
              }
              case mdt-data-list {
                leaf list {
                  tailf:info
                    "Access-list";
                  type ext-acl-type;
                }
              }
            }
          }
          leaf log-reuse {
            tailf:info
              "Event logging for data MDT reuse";
            type empty;
          }
        }
        container route-target {
          tailf:info
            "Specify Target VPN Extended Communities";
          tailf:cli-diff-dependency "../rd" {
            tailf:xpath-root 3;
          }
          uses route-target-grouping;
        }
      }
      container dhcp-server {
        tailf:info
          "Specify target DHCP server parameters";
        list dhcp-server-list {
          tailf:cli-drop-node-name;
          tailf:cli-suppress-mode;
          tailf:cli-delete-when-empty;
          tailf:cli-compact-syntax;
          key "server";
          leaf server {
            type inet:host {
              tailf:info
                "Hostname or A.B.C.D;;IP address or Name of DHCP server";
            }
          }
        }
      }
      container dhcp {
        tailf:info
          "Configure DHCP server and relay parameters";
        tailf:cli-explicit-exit;
        leaf smart-relay {
          tailf:info
            "Enable Smart Relay feature";
          type empty;
        }
        container use {
          tailf:info
            "Configure use of certain parameters during allocation";
          container vrf {
            tailf:info
              "Ignore or use receiving interface VRF";
            leaf connected {
              tailf:info
                "Use input interface VRF when servicing connected clients";
              tailf:cli-boolean-no;
              tailf:cli-full-command;
              type boolean;
              default "true";
            }
            leaf remote {
              tailf:info
                "Use input interface VRF when servicing remote clients";
              type empty;
            }
          }
        }
        container conflict {
          tailf:info
            "DHCP address conflict parameters";
          leaf logging {
            tailf:info
              "Record address conflicts in a log file";
            tailf:cli-boolean-no;
            tailf:cli-full-command;
            type boolean;
            default "true";
          }
        }
        container excluded-address {
          tailf:info
            "Prevent DHCP from assigning certain addresses";
          uses ip-dhcp-excluded-address-grouping;
          list vrf {
            tailf:info
              "VRF name for excluded address range";
            tailf:cli-suppress-mode;
            tailf:cli-delete-when-empty;
            tailf:cli-compact-syntax;
            tailf:cli-incomplete-command;
            key "name";
            leaf name {
              tailf:cli-diff-dependency "../../../../vrf" {
                tailf:xpath-root 3;
              }
              tailf:cli-diff-dependency "../../../../../vrf/definition" {
                tailf:xpath-root 3;
              }
              type string {
                tailf:info
                  "WORD;;VPN Routing/Forwarding instance name";
              }
            }
            uses ip-dhcp-excluded-address-grouping;
          }
        }
        list pool {
          tailf:info
            "Configure DHCP address pools";
          tailf:cli-mode-name "dhcp-config";
          key "id";
          leaf id {
            type string {
              tailf:info
                "WORD;;Pool name";
            }
          }
          leaf vrf {
            tailf:info
              "Associate this pool with a VRF";
            tailf:cli-diff-dependency "../../../../ip/vrf" {
              tailf:xpath-root 3;
            }
            tailf:cli-diff-dependency "../../../../vrf/definition" {
              tailf:xpath-root 3;
            }
            type string {
              tailf:info
                "WORD;;VRF name";
            }
          }
          container import {
            tailf:info
              "Programatically importing DHCP option parameters";
            leaf all {
              tailf:info
                "all DHCP options";
              type empty;
            }
          }
          leaf bootfile {
            tailf:info
              "Boot file name";
            type string {
              tailf:info
                "WORD;;Boot file name";
            }
          }
          container host {
            tailf:info
              "Client IP address and mask";
            tailf:cli-compact-syntax;
            tailf:cli-sequence-commands {
              tailf:cli-reset-siblings;
            }
            leaf address {
              tailf:cli-drop-node-name;
              tailf:cli-incomplete-command;
              type inet:ipv4-address {
                tailf:info
                  "A.B.C.D;;IP address in dotted-decimal notation";
              }
            }
            leaf mask {
              tailf:cli-drop-node-name;
              type inet:ipv4-address {
                tailf:info
                  "A.B.C.D;;Network mask or prefix length";
              }
            }
          }
          choice hardware-or-client {
            leaf hardware-address {
              tailf:info
                "Client hardware address";
              tailf:cli-full-command;
              type string {
                tailf:info
                  "WORD;;Dotted-hexadecimal string (aabb.ccdd.eeff ...)";
              }
            }
            leaf client-identifier {
              tailf:info
                "Client identifier";
              tailf:cli-full-command;
              type string {
                tailf:info
                  "WORD;;Dotted-hexadecimal string (aabb.ccdd.eeff ...)";
              }
            }
          }
          container network {
            tailf:info
              "Network number and mask";
            tailf:cli-compact-syntax;
            tailf:cli-sequence-commands {
              tailf:cli-reset-siblings;
            }
            leaf network-number {
              tailf:cli-drop-node-name;
              tailf:cli-remove-before-change;
              type inet:ipv4-address {
                tailf:info
                  "Network number in dotted-decimal notation";
              }
            }
            leaf mask {
              tailf:cli-drop-node-name;
              tailf:cli-remove-before-change;
              type inet:ipv4-address {
                tailf:info
                  "A.B.C.D;;Network mask";
              }
            }
          }
          leaf-list next-server {
            tailf:info
              "Next server in boot process";
            tailf:cli-flat-list-syntax;
            tailf:cli-replace-all;
            ordered-by user;
            max-elements 8;
            type inet:host {
              tailf:info
                "Hostname or A.B.C.D;;Server's name or IP address";
            }
          }
          leaf-list netbios-name-server {
            tailf:info
              "NetBIOS (WINS) name servers";
            tailf:cli-flat-list-syntax;
            tailf:cli-replace-all;
            ordered-by user;
            max-elements 8;
            type inet:host {
              tailf:info
                "Hostname or A.B.C.D;;Server's name or IP address";
            }
          }
          leaf-list dns-server {
            tailf:info
              "DNS servers";
            tailf:cli-flat-list-syntax;
            tailf:cli-replace-all;
            ordered-by user;
            max-elements 8;
            type inet:host {
              tailf:info
                "Hostname or A.B.C.D;;Server's name or IP address";
            }
          }
          leaf-list default-router {
            tailf:info
              "Default routers";
            tailf:cli-flat-list-syntax;
            tailf:cli-replace-all;
            ordered-by user;
            max-elements 8;
            type inet:host {
              tailf:info
                "Hostname or A.B.C.D;;Router's name or IP address";
            }
          }
          leaf domain-name {
            tailf:info
              "Domain name";
            tailf:cli-full-command;
            type string {
              tailf:info
                "NAME;;Domain name";
            }
          }
          list option {
            tailf:info
              "Raw DHCP options";
            tailf:cli-suppress-mode;
            tailf:cli-delete-when-empty;
            tailf:cli-incomplete-command;
            key "code";
            leaf code {
              type uint8 {
                tailf:info
                  "<0-254>;;DHCP option code";
                range "0..254";
              }
            }
            choice option-config {
              leaf ascii {
                tailf:info
                  "Data is an NVT ASCII string";
                tailf:cli-suppress-no;
                tailf:cli-no-name-on-delete;
                tailf:cli-no-value-on-delete;
                type string {
                  tailf:info
                    "LINE;;NVT ASCII string";
                }
              }
              leaf hex {
                tailf:info
                  "Data is a hexadecimal string";
                tailf:cli-suppress-no;
                tailf:cli-no-name-on-delete;
                tailf:cli-no-value-on-delete;
                type union {
                  type string {
                    tailf:info
                      "LINE;;Hexadecimal string";
                  }
                  type enumeration {
                    enum "none" {
                      tailf:info
                        "No data";
                    }
                  }
                }
              }
              leaf-list ip {
                tailf:info
                  "Data is one or more IP addresses";
                tailf:cli-suppress-no;
                tailf:cli-no-name-on-delete;
                tailf:cli-no-value-on-delete;
                tailf:cli-flat-list-syntax;
                type inet:host {
                  tailf:info
                    "Hostname or A.B.C.D;;Server's name or IP address";
                }
              }
            }
            list instance {
              tailf:info
                "Specify the option instance";
              tailf:cli-suppress-mode;
              tailf:cli-delete-when-empty;
              tailf:cli-incomplete-command;
              key "option-instance";
              leaf option-instance {
                tailf:info
                  "Specify the option instance";
                type uint8 {
                  tailf:info
                    "<0-255>;;DHCP option instance";
                }
              }
              choice option-config {
                leaf ascii {
                  tailf:info
                    "Data is an NVT ASCII string";
                  tailf:cli-suppress-no;
                  tailf:cli-no-name-on-delete;
                  tailf:cli-no-value-on-delete;
                  type string {
                    tailf:info
                      "LINE;;NVT ASCII string";
                  }
                }
                leaf hex {
                  tailf:info
                    "Data is a hexadecimal string";
                  tailf:cli-suppress-no;
                  tailf:cli-no-name-on-delete;
                  tailf:cli-no-value-on-delete;
                  type union {
                    type string {
                      tailf:info
                        "LINE;;Hexadecimal string";
                    }
                    type enumeration {
                      enum "none" {
                        tailf:info
                          "No data";
                      }
                    }
                  }
                }
                leaf-list ip {
                  tailf:info
                    "Data is one or more IP addresses";
                  tailf:cli-suppress-no;
                  tailf:cli-no-name-on-delete;
                  tailf:cli-no-value-on-delete;
                  tailf:cli-flat-list-syntax;
                  type inet:host {
                    tailf:info
                      "Hostname or A.B.C.D;;Server's name or IP address";
                  }
                }
              }
            }
          }
          container lease {
            tailf:info
              "Address lease time";
            tailf:cli-compact-syntax;
            tailf:cli-sequence-commands {
              tailf:cli-reset-all-siblings;
            }
            choice lease-choice {
              case a {
                leaf infinite {
                  tailf:info
                    "Infinite lease";
                  type empty;
                }
              }
              case b {
                leaf days {
                  tailf:cli-drop-node-name;
                  type uint16 {
                    tailf:info
                      "<0-365>;;Days";
                    range "0..365";
                  }
                }
                leaf hours {
                  tailf:cli-drop-node-name;
                  type uint16 {
                    tailf:info
                      "<0-23>;;Hours";
                    range "0..23";
                  }
                }
                leaf minutes {
                  tailf:cli-drop-node-name;
                  type uint16 {
                    tailf:info
                      "<0-59>;;Minutes";
                    range "0..59";
                  }
                }
              }
            }
          }
          container update {
            tailf:info
              "Dynamic updates";
            leaf arp {
              tailf:info
                "Add secure ARP entries";
              type empty;
            }
          }
          list class {
            tailf:info
              "Specify a DHCP class";
            tailf:cli-mode-name "config-dhcp-pool-class";
            key "name";
            leaf name {
              type string {
                tailf:info
                  "WORD;;DHCP class name";
              }
            }
            container address {
              tailf:info
                "Specify an address range for this class";
              container range {
                tailf:info
                  "Specify an address range for this class";
                tailf:cli-compact-syntax;
                tailf:cli-sequence-commands {
                  tailf:cli-reset-siblings;
                }
                leaf start-ip {
                  tailf:cli-drop-node-name;
                  tailf:cli-incomplete-command;
                  type inet:ipv4-address {
                    tailf:info
                      "A.B.C.D;;Start IP address";
                  }
                }
                leaf end-ip {
                  tailf:cli-drop-node-name;
                  type inet:ipv4-address {
                    tailf:info
                      "A.B.C.D;;End IP address";
                  }
                }
              }
            }
          }
          leaf netbios-node-type {
            tailf:info
              "NetBIOS node type";
            type union {
              type enumeration {
                enum "b-node" {
                  tailf:info
                    "Broadcast node";
                }
                enum "h-node" {
                  tailf:info
                    "Hybrid node";
                }
                enum "m-node" {
                  tailf:info
                    "Mixed node";
                }
                enum "p-node" {
                  tailf:info
                    "Peer-to-peer node";
                }
              }
              type string {
                tailf:info
                  "<0-FF>;;Hexadecimal number";
              }
            }
          }
        }
        list class {
          tailf:info
            "Configure DHCP classes";
          tailf:cli-mode-name "config-dhcp-class";
          key "id";
          leaf id {
            type string {
              tailf:info
                "WORD;;Class name";
            }
          }
          leaf remark {
            tailf:info
              "Specify a remark for this class";
            tailf:cli-multi-value;
            type string {
              tailf:info
                "LINE;;Up to 240 characters describing this class";
              length "1..240";
            }
          }
          container relay {
            tailf:info
              "Enter relay agent information option configuration submode";
            container agent {
              tailf:info
                "Enter relay agent information option configuration submode";
              container information {
                tailf:info
                  "Enter relay agent information option configuration submode";
                tailf:cli-add-mode;
                tailf:cli-mode-name "config-dhcp-class-relayinfo";
                presence "true";
              }
            }
          }
        }
        container snooping {
          tailf:info
            "DHCP Snooping";
          tailf:cli-incomplete-command;
          tailf:cli-incomplete-no;
          leaf-list bridge-domain {
            tailf:info
              "DHCP Snooping bridge-domain";
            tailf:cli-range-list-syntax;
            tailf:cli-suppress-list-no;
            tailf:cli-full-command;
            tailf:cli-diff-dependency "../../snooping" {
              tailf:xpath-root 3;
            }
            type uint16 {
              tailf:info
                "WORD;;bridge-domain range, example: 1,3-5,7,9-11";
              range "1..4094";
            }
          }
          container information {
            tailf:info
              "DHCP Snooping information";
            container option {
              tailf:info
                "DHCP Snooping information option";
              presence "true";
              leaf allow-untrusted {
                tailf:info
                  "DHCP Snooping information option allow-untrusted";
                type empty;
              }
              container format {
                tailf:info
                  "Option 82 information format";
                container remote-id {
                  tailf:info
                    "Remote id option 82 format";
                  choice remote-id-choice {
                    leaf hostname {
                      tailf:info
                        "Use configured hostname for remote id";
                      type empty;
                    }
                    leaf string {
                      tailf:info
                        "User defined string for remote id";
                      type string {
                        tailf:info
                          "WORD;;Use string for remote id (max length 63)";
                      }
                    }
                  }
                }
              }
            }
          }
          container database {
            tailf:info
              "DHCP snooping database agent";
            leaf url {
              tailf:cli-drop-node-name;
              type string {
                tailf:info
                  "WORD;;Database agent URL";
              }
            }
          }
          container track {
            tailf:info
              "DHCP snooping track";
            leaf host {
              tailf:info
                "DHCP snooping track host";
              type empty;
            }
          }
          container verify {
            tailf:info
              "DHCP snooping verify";
            leaf mac-address {
              tailf:info
                "DHCP snooping verify mac-address";
              type empty;
            }
            leaf no-relay-agent-address {
              tailf:info
                "DHCP snooping verify giaddr";
              type empty;
            }
          }
          leaf-list vlan {
            tailf:info
              "DHCP Snooping vlan";
            tailf:cli-range-list-syntax;
            type uint16 {
              tailf:info
                "WORD;;DHCP Snooping vlan fist number or vlan range, example: 1,3-5,7,9-11";
            }
          }
        }
        container snooping-conf {
          tailf:cli-drop-node-name;
          leaf snooping {
            tailf:info
              "DHCP Snooping ";
            type empty;
          }
        }
        container relay {
          tailf:info
            "DHCP relay agent parameters";
          container information {
            tailf:info
              "Relay agent information option";
            container option {
              tailf:info
                "Insert relay information in BOOTREQUEST";
              presence "true";
            }
            leaf check {
              tailf:info
                "Validate relay information in BOOTREPLY";
              tailf:cli-boolean-no;
              tailf:cli-full-command;
              type boolean;
              default "true";
            }
            leaf trust-all {
              tailf:info
                "Received DHCP packets may contain relay info option with zero giaddr";
              type empty;
            }
          }
          container prefer {
            tailf:info
              "Relay agent server selection approach";
            leaf known-good-server {
              tailf:info
                "For unnumbered interfaces, prefer to send client requests to the server which handled the last one";
              type empty;
            }
          }
        }
        container bootp {
          tailf:info
            "BOOTP specific configuration";
          leaf ignore {
            tailf:info
              "Configure this DHCP server to ignore to BOOTP requests.";
            type empty;
          }
        }
      }
      container bootp {
        tailf:info
          "Config BOOTP services";
        leaf server {
          tailf:info
            "Enable BOOTP server";
          tailf:cli-boolean-no;
          tailf:cli-full-command;
          type boolean;
          default "true";
        }
      }
      container domain {
        tailf:info
          "IP DNS Resolver";
        leaf round-robin {
          tailf:info
            "Round-robin multiple IP addresses in cache";
          tailf:cli-full-command;
          type empty;
        }
        container list-vrf {
          tailf:cli-drop-node-name;
          container list {
            tailf:cli-incomplete-command;
            tailf:cli-incomplete-no;
            list vrf {
              tailf:info
                "Specify VRF";
              tailf:cli-suppress-mode;
              tailf:cli-delete-when-empty;
              tailf:cli-compact-syntax;
              tailf:cli-incomplete-command;
              key "name";
              leaf name {
                tailf:cli-diff-dependency "../../../../../../ip/vrf" {
                  tailf:xpath-root 3;
                }
                tailf:cli-diff-dependency "../../../../../../vrf/definition" {
                  tailf:xpath-root 3;
                }
                type string {
                  tailf:info
                    "WORD;;VRF name";
                }
              }
              leaf domain-name {
                tailf:cli-drop-node-name;
                type string {
                  tailf:info
                    "WORD;;A domain name";
                }
              }
            }
          }
        }
        list list {
          tailf:info
            "Domain name to complete unqualified host names";
          tailf:cli-suppress-mode;
          tailf:cli-delete-when-empty;
          key "name";
          leaf name {
            type string {
              tailf:info
                "WORD;;A domain name";
            }
          }
        }
        leaf retry {
          tailf:info
            "Specify times to retry sending a DNS query";
          tailf:cli-full-command;
          type uint8 {
            tailf:info
              "<0-100>;;Number of retries";
            range "0..100";
          }
        }
        leaf timeout {
          tailf:info
            "Specify timeout waiting for response to a DNS query";
          tailf:cli-full-command;
          type uint16 {
            tailf:info
              "<1-3600>;;Timeout value in seconds";
            range "1..3600";
          }
        }
        container lookup-conf {
          tailf:cli-drop-node-name;
          leaf lookup {
            tailf:info
              "Enable IP Domain Name System hostname translation";
            tailf:cli-boolean-no;
            tailf:cli-full-command;
            type boolean;
            default "true";
          }
        }
        container lookup {
          tailf:info
            "Enable IP Domain Name System hostname translation";
          tailf:cli-incomplete-command;
          tailf:cli-incomplete-no;
          leaf nsap {
            tailf:info
              "Enable IP DNS queries for CLNS NSAP addresses";
            tailf:cli-boolean-no;
            tailf:cli-full-command;
            type boolean;
            default "true";
          }
          leaf recursive {
            tailf:info
              "Enable IP DNS recursive lookup";
            tailf:cli-full-command;
            type empty;
          }
          container source-interface {
            tailf:info
              "Specify source interface for DNS resolver";
            uses interface-name-grouping;
          }
          leaf vrf {
            tailf:info
              "Specify VRF";
            tailf:cli-diff-dependency "../../../../ip/vrf" {
              tailf:xpath-root 3;
            }
            tailf:cli-diff-dependency "../../../../vrf/definition" {
              tailf:xpath-root 3;
            }
            type string {
              tailf:info
                "WORD;;VRF name";
            }
          }
        }
        container name-vrf {
          tailf:cli-drop-node-name;
          container name {
            tailf:cli-incomplete-command;
            tailf:cli-incomplete-no;
            list vrf {
              tailf:info
                "Specify VRF";
              tailf:cli-suppress-mode;
              tailf:cli-delete-when-empty;
              tailf:cli-compact-syntax;
              tailf:cli-incomplete-command;
              key "name";
              leaf name {
                tailf:cli-diff-dependency "../../../../../../ip/vrf" {
                  tailf:xpath-root 3;
                }
                tailf:cli-diff-dependency "../../../../../../vrf/definition" {
                  tailf:xpath-root 3;
                }
                type string {
                  tailf:info
                    "WORD;;VRF name";
                }
              }
              leaf domain-name {
                tailf:cli-drop-node-name;
                type string {
                  tailf:info
                    "WORD;;Default domain name";
                }
              }
            }
          }
        }
        leaf name {
          tailf:info
            "Define the default domain name";
          type string {
            tailf:info
              "WORD;;Default domain name";
          }
        }
        leaf multicast {
          tailf:info
            "Define the domain name for multicast address lookups";
          tailf:cli-full-command;
          type string {
            tailf:info
              "WORD;;Multicast domain name";
          }
        }
        container recursive {
          tailf:info
            "Configure recursive DNS lookup";
          leaf retry {
            tailf:info
              "Configure maximum no. referrals to be allowed";
            tailf:cli-full-command;
            type uint8 {
              tailf:info
                "<0-100>;;Maximum no. of referrals allowed - default 10";
              range "0..100";
            }
          }
          leaf allow-soa {
            tailf:info
              "Treat response containing SOA RR in AUTHORITY as a referral";
            tailf:cli-full-command;
            type empty;
          }
        }
      }
      container host {
        tailf:info
          "Add an entry to the ip hostname table";
        uses ip-host-grouping;
        list vrf {
          tailf:info
            "Specify VRF";
          tailf:cli-suppress-mode;
          tailf:cli-delete-when-empty;
          tailf:cli-compact-syntax;
          tailf:cli-incomplete-command;
          key "name";
          leaf name {
            tailf:cli-diff-dependency "../../../../ip/vrf" {
              tailf:xpath-root 3;
            }
            tailf:cli-diff-dependency "../../../../vrf/definition" {
              tailf:xpath-root 3;
            }
            type string {
              tailf:info
                "WORD;;VRF name";
            }
          }
          uses ip-host-grouping;
        }
      }
      container name-server {
        tailf:info
          "Specify address of name server to use";
        uses ip-name-server-grouping;
        list vrf {
          tailf:info
            "Specify VRF";
          tailf:cli-suppress-mode;
          tailf:cli-delete-when-empty;
          tailf:cli-compact-syntax;
          tailf:cli-incomplete-command;
          key "name";
          leaf name {
            tailf:cli-diff-dependency "../../../../ip/vrf" {
              tailf:xpath-root 3;
            }
            tailf:cli-diff-dependency "../../../../vrf/definition" {
              tailf:xpath-root 3;
            }
            type string {
              tailf:info
                "WORD;;VRF name";
            }
          }
          uses ip-name-server-grouping;
        }
      }
      container mcr-conf {
        tailf:cli-drop-node-name;
        leaf multicast-routing {
          tailf:info
            "Enable IP multicast forwarding";
          type empty;
        }
      }
      container multicast-routing {
        tailf:info
          "Enable IP multicast forwarding";
        tailf:cli-incomplete-no;
        tailf:cli-incomplete-command;
        tailf:cli-diff-dependency "../mcr-conf/multicast-routing" {
          tailf:xpath-root 3;
        }
        list vrf {
          tailf:info
            "Select VPN Routing/Forwarding instance";
          tailf:cli-suppress-list-no;
          tailf:cli-suppress-mode;
          tailf:cli-delete-when-empty;
          tailf:cli-compact-syntax;
          tailf:cli-reset-container;
          tailf:cli-diff-dependency "../../mcr-conf/multicast-routing" {
            tailf:xpath-root 3;
          }
          key "name";
          leaf name {
            tailf:cli-diff-dependency "../../../../ip/vrf" {
              tailf:xpath-root 3;
            }
            tailf:cli-diff-dependency "../../../../vrf/definition" {
              tailf:xpath-root 3;
            }
            type string {
              tailf:info
                "WORD;;VPN Routing/Forwarding instance name";
            }
          }
          leaf distributed {
            tailf:info
              "Distributed multicast switching";
            type empty;
          }
        }
        leaf distributed {
          tailf:info
            "Distributed multicast switching";
          tailf:cli-full-command;
          type empty;
        }
      }
      container multicast {
        tailf:info
          "Global IP Multicast Commands";
        leaf route-limit {
          tailf:info
            "Maximum number of multicast routes";
          type uint32 {
            tailf:info
              "<1-2147483647>;;number of routes";
            range "1..2147483647";
          }
        }
        container multipath {
          tailf:info
            "RPF across equal-cost paths";
          presence "true";
          leaf s-g-hash {
            tailf:info
              "Per-(source, group) load sharing algorithm selection";
            type enumeration {
              enum "basic" {
                tailf:info
                  "Basic hash on (source, group)";
              }
              enum "next-hop-based" {
                tailf:info
                  "Advanced hash on (source, group) and next-hop";
              }
            }
          }
        }
        list vrf {
          tailf:info
            "Select VPN Routing/Forwarding instance";
          tailf:cli-suppress-mode;
          tailf:cli-delete-when-empty;
          key "name";
          leaf name {
            tailf:cli-diff-dependency "../../../../ip/vrf" {
              tailf:xpath-root 3;
            }
            tailf:cli-diff-dependency "../../../../vrf/definition" {
              tailf:xpath-root 3;
            }
            type string {
              tailf:info
                "WORD;;VPN Routing/Forwarding instance name";
            }
          }
          container route-limit {
            tailf:info
              "Maximum number of multicast routes";
            tailf:cli-compact-syntax;
            tailf:cli-sequence-commands;
            tailf:cli-reset-container;
            leaf limit {
              tailf:cli-drop-node-name;
              type uint32 {
                tailf:info
                  "<1-2147483647>;;number of routes";
                range "1..2147483647";
              }
            }
            leaf threshold {
              tailf:cli-drop-node-name;
              type uint32 {
                tailf:info
                  "<1-2147483647>;;Threshold at which to generate warning message";
                range "1..2147483647";
              }
            }
          }
          container multipath {
            tailf:info
              "RPF across equal-cost paths";
            presence "true";
          }
        }
      }
      container icmp {
        tailf:info
          "ICMP options";
        container rate-limit {
          tailf:info
            "rate limit ICMP messages generated";
          container unreachable {
            tailf:info
              "ICMP type 3, Destination Unreachable";
            tailf:cli-compact-syntax;
            tailf:cli-sequence-commands {
              tailf:cli-reset-siblings;
            }
            leaf DF {
              tailf:info
                "code 4, fragmentation needed and DF set";
              tailf:cli-optional-in-sequence;
              type empty;
            }
            leaf ms {
              tailf:cli-drop-node-name;
              type uint32 {
                tailf:info
                  "<1-4294967295>;;Once per milliseconds";
              }
            }
            leaf log {
              tailf:info
                "log message if rate limiting is excessive";
              type empty;
            }
            leaf packets {
              when "../log" {
                tailf:xpath-root 3;
                tailf:dependency "../log";
              }
              tailf:cli-drop-node-name;
              type uint32 {
                tailf:info
                  "<1-4294967295>;;number of unreachables within interval to trigger a message";
                range "1..4294967295";
              }
            }
            leaf interval-ms {
              when "../log" {
                tailf:xpath-root 3;
                tailf:dependency "../log";
              }
              tailf:cli-drop-node-name;
              type uint32 {
                tailf:info
                  "<10000-4294967295>;;log message once per milliseconds";
                range "10000..4294967295";
              }
            }
          }
        }
        leaf redirect {
          tailf:info
            "Redirect type";
          tailf:cli-full-command;
          type enumeration {
            enum "subnet" {
              tailf:info
                "Send ICMP subnet redirects";
            }
            enum "host" {
              tailf:info
                "Send ICMP host redirects";
            }
          }
          default "subnet";
        }
      }
      container igmp {
        tailf:info
          "IGMP global configuration";
        uses ip-igmp-grouping;
        container snooping-conf {
          tailf:cli-drop-node-name;
          container snooping {
            tailf:info
              "Global IGMP Snooping enable for Catalyst Vlans";
            tailf:cli-incomplete-command;
            tailf:cli-incomplete-no;
            leaf l2-entry-limit {
              tailf:info
                "limit on the l2 entry that can be installed by IGMP snooping";
              type uint32 {
                tailf:info
                  "<1-100000>;;maximum number of l2 entries";
                range "1..100000";
              }
            }
            leaf last-member-query-interval {
              tailf:info
                "Last member query interval";
              tailf:cli-full-command;
              type uint16 {
                tailf:info
                  "<100-32767>;;Interval (milliseconds)";
                range "100..32767";
              }
            }
            container source-only-learning {
              tailf:info
                "source-only gce entries";
              leaf age-timer {
                tailf:info
                  "configure age-timer for source-only entries";
                type uint32 {
                  tailf:info
                    "<0-86400>;;source-only entries age timer in secs";
                  range "0..86400";
                }
                default "600";
              }
            }
          }
        }
        leaf snooping {
          tailf:info
            "Global IGMP Snooping enable for Catalyst Vlans";
          tailf:cli-boolean-no;
          tailf:cli-full-command;
          type boolean;
          default "true";
        }
        container snooping-vlan {
          tailf:cli-drop-node-name;
          when "not(../snooping = 'false')" {
            tailf:xpath-root 3;
            tailf:dependency "../snooping";
          }
          container snooping {
            tailf:info
              "Global IGMP Snooping enable for Catalyst Vlans";
            tailf:cli-incomplete-command;
            tailf:cli-incomplete-no;
            container vlan {
              tailf:info
                "IGMP Snooping enable for Catalyst VLAN";
              list no-list {
                tailf:info
                  "'no ip igmp snooping vlan' entry";
                tailf:cli-suppress-mode;
                tailf:cli-delete-when-empty;
                key "id";
                leaf id {
                  type uint16 {
                    tailf:info
                      "<1-4094>;;VLAN ID";
                    range "1..4094";
                  }
                }
              }
            }
          }
        }
        list vrf {
          tailf:info
            "Select VPN Routing/Forwarding instance";
          tailf:cli-suppress-mode;
          tailf:cli-delete-when-empty;
          key "name";
          leaf name {
            tailf:cli-diff-dependency "../../../../ip/vrf" {
              tailf:xpath-root 3;
            }
            tailf:cli-diff-dependency "../../../../vrf/definition" {
              tailf:xpath-root 3;
            }
            type string {
              tailf:info
                "WORD;;VPN Routing/Forwarding instance name";
            }
          }
          uses ip-igmp-grouping;
        }
      }
      container msdp {
        tailf:info
          "MSDP global commands";
        uses ip-msdp-grouping;
        list vrf {
          tailf:info
            "Select VPN Routing/Forwarding instance";
          tailf:cli-suppress-mode;
          tailf:cli-delete-when-empty;
          key "name";
          leaf name {
            tailf:cli-diff-dependency "../../../../ip/vrf" {
              tailf:xpath-root 3;
            }
            tailf:cli-diff-dependency "../../../../vrf/definition" {
              tailf:xpath-root 3;
            }
            type string {
              tailf:info
                "WORD;;VPN Routing/Forwarding instance name";
            }
          }
          uses ip-msdp-grouping;
        }
      }
      container device {
        tailf:info
          "Device tracking";
        container tracking {
          tailf:info
            "Device tracking";
          tailf:cli-delete-when-empty;
          presence "true";
          container probe {
            tailf:info
              "Probe";
            container auto-source {
              tailf:info
                "Probe source selection algorithm";
              tailf:cli-compact-syntax;
              tailf:cli-reset-container;
              tailf:cli-delete-when-empty;
              presence "true";
              container fallback {
                tailf:info
                  "Specify IP and MASK to use as last resort";
                tailf:cli-flatten-container;
                tailf:cli-compact-syntax;
                tailf:cli-sequence-commands {
                  tailf:cli-reset-siblings;
                }
                leaf address {
                  tailf:cli-drop-node-name;
                  tailf:cli-incomplete-command;
                  type inet:ipv4-address {
                    tailf:info
                      "A.B.C.D;;IP of fallback source";
                  }
                }
                leaf mask {
                  tailf:cli-drop-node-name;
                  type inet:ipv4-address {
                    tailf:info
                      "A.B.C.D;;IP prefix mask";
                  }
                }
              }
              leaf override {
                tailf:info
                  "Do not select source address from device track table";
                type empty;
              }
            }
            leaf delay {
              tailf:info
                "Probe delay";
              type uint8 {
                tailf:info
                  "<1-120>;;delay";
                range "1..120";
              }
            }
          }
        }
      }
      container finger {
        tailf:info
          "finger server";
        presence "true";
        leaf rfc-compliant {
          tailf:info
            "Comply with RFC 1288";
          type empty;
        }
      }
      container tcp {
        tailf:info
          "Global TCP parameters";
        leaf selective-ack {
          tailf:info
            "Enable TCP selective-ACK";
          type empty;
        }
        leaf mss {
          tailf:info
            "TCP initial maximum segment size ";
          type uint16 {
            tailf:info
              "<68-10000>;;MSS";
            range "68..10000";
          }
        }
        container path-mtu-discovery {
          tailf:info
            "Enable path-MTU discovery on new TCP connections";
          presence "true";
          leaf age-timer {
            tailf:info
              "Set PMTU aging timer";
            type union {
              type enumeration {
                enum "infinite" {
                  tailf:info
                    "Disable pathmtu aging timer";
                }
              }
              type uint8 {
                tailf:info
                  "<10-30>;;Aging time";
                range "10..30";
              }
            }
          }
        }
        leaf window-size {
          tailf:info
            "TCP window size";
          type uint32 {
            tailf:info
              "<68-1073741823>;;Window size";
            range "68..1073741823";
          }
        }
        leaf synwait-time {
          tailf:info
            "Set time to wait on new TCP connections";
          type uint16 {
            tailf:info
              "<5-300>;;Wait time";
            range "5..300";
          }
        }
      }
      container telnet {
        tailf:info
          "Specify telnet options";
        leaf tos {
          tailf:info
            "Specify type of service";
          type string {
            tailf:info
              "<0-FF>;;TOS value";
          }
        }
        container source-interface {
          tailf:info
            "Specify source interface";
          uses interface-name-grouping;
        }
      }
      container ftp {
        tailf:info
          "FTP configuration commands";
        leaf passive {
          tailf:info
            "Connect using passive mode";
          tailf:cli-boolean-no;
          tailf:cli-full-command;
          type boolean;
          default "true";
        }
        container source-interface {
          tailf:info
            "Specify interface for source address in FTP connections";
          uses interface-name-grouping;
        }
        leaf username {
          tailf:info
            "Specify username for FTP connections";
          tailf:cli-full-command;
          type string {
            tailf:info
              "WORD;;Username";
          }
        }
        container password {
          tailf:info
            "Specify password for FTP connections;";
          tailf:cli-compact-syntax;
          tailf:cli-sequence-commands;
          uses password-grouping;
        }
      }
      container tftp {
        tailf:info
          "tftp configuration commands";
        container source-interface {
          tailf:info
            "Specify interface for source address in TFTP connections";
          tailf:cli-compact-syntax;
          uses interface-name-grouping;
        }
        container boot-interface {
          tailf:info
            "Force interface to use for TFTP booting";
          uses interface-name-grouping;
        }
        leaf blocksize {
          tailf:info
            "Specify TFTP client blocksize";
          type uint16 {
            tailf:info
              "<512-8192>;;blocksize value";
            range "512..8192";
          }
        }
      }
      container ssh {
        tailf:info
          "Configure ssh options";
        leaf time-out {
          tailf:info
            "Specify SSH time-out interval";
          type uint8 {
            tailf:info
              "<1-120>;;SSH time-out interval (secs)";
            range "1..120";
          }
          default "120";
        }
        list port {
          tailf:info
            "Starting (or only) Port number to listen on";
          tailf:cli-suppress-mode;
          tailf:cli-delete-when-empty;
          tailf:cli-compact-syntax;
          tailf:cli-sequence-commands;
          tailf:cli-incomplete-command;
          key "port";
          leaf port {
            type uint16 {
              tailf:info
                "<2000-10000>;;Starting Port number";
              range "2000..10000";
            }
          }
          leaf rotary {
            tailf:info
              "Starting (or only) rotary group number";
            type uint8 {
              tailf:info
                "<1-127>;;Low (or only) Rotary group numbe";
              range "1..127";
            }
          }
          leaf rotary-high {
            tailf:cli-drop-node-name;
            type uint8 {
              tailf:info
                "<1-127>;;High Rotary group numbe";
              range "1..127";
            }
          }
        }
        leaf break-string {
          tailf:info
            "break-string";
          tailf:cli-full-command;
          type string {
            tailf:info
              "WORD;;Break string";
          }
        }
        leaf authentication-retries {
          tailf:info
            "Specify number of authentication retries";
          type uint8 {
            tailf:info
              "<0-5>;;Number of authentication retries";
            range "0..5";
          }
          default "3";
        }
        leaf dscp {
          tailf:info
            "IP DSCP value for SSH traffic";
          type uint8 {
            tailf:info
              "<0-63>;;ip dscp value (default value 0)";
            range "0..63";
          }
        }
        container logging {
          tailf:info
            "Configure logging for SSH";
          leaf events {
            tailf:info
              "Log SSH events";
            type empty;
          }
        }
        leaf version {
          tailf:info
            "Specify protocol version supported";
          type uint8 {
            tailf:info
              "<1-2>;;Protocol version";
            range "1..2";
          }
        }
        leaf precedence {
          tailf:info
            "IP Precedence value for SSH traffic";
          type uint8 {
            tailf:info
              "<0-7>;;ip precedence value (default value 0)";
            range "0..7";
          }
        }
        leaf stricthostkeycheck {
          tailf:info
            "Enable SSH Server Authentication";
          type empty;
        }
        container source-interface {
          tailf:info
            "Specify interface for source address in SSH connections";
          uses interface-name-grouping;
        }
        container dh {
          tailf:info
            "Diffie-Hellman";
          container min {
            tailf:info
              "minimum";
            leaf size {
              tailf:info
                "key size";
              type enumeration {
                enum "1024" {
                  tailf:info
                    "Diffie Group 1 1024-bit key";
                }
                enum "2048" {
                  tailf:info
                    "Diffie Group 14 2048-bit key";
                }
                enum "4096" {
                  tailf:info
                    "Diffie Group 16 4096-bit key";
                }
              }
              default "1024";
            }
          }
        }
        container server {
          tailf:info
            "Configuration for server";
          container authenticate {
            tailf:info
              "Authentication configuration parameter";
            container user {
              tailf:info
                "User configuration";
              leaf publickey {
                tailf:info
                  "Public key based authentication";
                tailf:cli-boolean-no;
                tailf:cli-full-command;
                type boolean;
                default "true";
              }
              leaf keyboard {
                tailf:info
                  "keyboard-interactive based authentication";
                tailf:cli-boolean-no;
                tailf:cli-full-command;
                type boolean;
                default "true";
              }
              leaf password {
                tailf:info
                  "Password based authentication";
                tailf:cli-boolean-no;
                tailf:cli-full-command;
                type boolean;
                default "true";
              }
            }
          }
          uses ip-ssh-algorithm-grouping;
        }
        container client {
          tailf:info
            "Configuration for client";
          uses ip-ssh-algorithm-grouping;
        }
        container rsa {
          tailf:info
            "Configure RSA keypair name for SSH";
          leaf keypair-name {
            tailf:info
              "keypair-name";
            type string {
              tailf:info
                "WORD;;keypair name";
            }
          }
        }
        container pubkey-chain {
          tailf:info
            "pubkey-chain";
          tailf:cli-add-mode;
          tailf:cli-mode-name "conf-ssh-pubkey";
          tailf:cli-full-command;
          list username {
            tailf:cli-mode-name "conf-ssh-pubkey-user";
            tailf:cli-exit-command "quit";
            key "name";
            leaf name {
              type string {
                tailf:info
                  "WORD;;Name of the user";
              }
            }
            list key-hash {
              tailf:info
                "Key hash data";
              tailf:cli-suppress-mode;
              tailf:cli-delete-when-empty;
              tailf:cli-incomplete-command;
              key "key-type";
              leaf key-type {
                type enumeration {
                  enum "ssh-rsa" {
                    tailf:info
                      "WORD;;key type ssh-rsa";
                  }
                }
              }
              leaf key-name {
                tailf:cli-drop-node-name;
                type string {
                  tailf:info
                    "WORD;;key hash data";
                }
              }
            }
          }
        }
      }
      container scp {
        tailf:info
          "Scp commands";
        container server {
          tailf:info
            "Configure SCP server-side functionality";
          leaf enable {
            tailf:info
              "Enable server side of SCP";
            type empty;
          }
        }
      }
      container local {
        tailf:info
          "Specify local options";
        container policy {
          tailf:info
            "Enable policy routing";
          leaf route-map {
            tailf:info
              "Policy route map";
            type string {
              tailf:info
                "WORD;;Route map name";
            }
          }
        }
        list pool {
          tailf:info
            "IP Local address pool lists";
          tailf:cli-suppress-mode;
          tailf:cli-delete-when-empty;
          tailf:cli-compact-syntax;
          tailf:cli-sequence-commands {
            tailf:cli-reset-siblings;
          }
          key "id";
          leaf id {
            type union {
              type string {
                tailf:info
                  "WORD;;Create named local address pool";
              }
              type enumeration {
                enum "default" {
                  tailf:info
                    "Create default local address pool";
                }
              }
            }
          }
          leaf start {
            tailf:cli-drop-node-name;
            type inet:ipv4-address {
              tailf:info
                "A.B.C.D;;First IP address of range";
            }
          }
          leaf last {
            tailf:cli-drop-node-name;
            tailf:cli-optional-in-sequence;
            type inet:ipv4-address {
              tailf:info
                "A.B.C.D;;Last IP address of range";
            }
          }
          leaf group {
            tailf:info
              "Create ip local pool group";
            type string {
              tailf:info
                "WORD;;Group name for this named local address pool";
            }
          }
        }
      }
      leaf default-gateway {
        tailf:info
          "Specify default gateway (if not routing IP)";
        type inet:ipv4-address {
          tailf:info
            "A.B.C.D;;IP address of default gateway";
        }
      }
      leaf-list default-network {
        tailf:info
          "Flags networks as candidates for default routes";
        tailf:cli-list-syntax;
        type inet:ipv4-address {
          tailf:info
            "A.B.C.D;;IP address of default network";
        }
      }
      leaf classless {
        tailf:info
          "Follow classless routing forwarding rules";
        tailf:cli-boolean-no;
        tailf:cli-full-command;
        type boolean;
        default "true";
      }
      container forward-protocol {
        tailf:info
          "Controls forwarding of physical and directed IP broadcasts";
        leaf nd {
          tailf:info
            "Sun's Network Disk protocol";
          tailf:cli-show-no;
          type empty;
        }
        leaf sdns {
          tailf:info
            "Network Security Protocol";
          tailf:cli-boolean-no;
          type boolean;
        }
        leaf turbo-flood {
          tailf:info
            "Fast flooding of UDP broadcasts";
          tailf:cli-boolean-no;
          type boolean;
        }
        container spanning-tree {
          tailf:info
            "Use transparent bridging to flood UDP broadcasts";
          presence "true";
          leaf any-local-broadcast {
            tailf:info
              "Accept any local broadcast when flooding";
            type empty;
          }
        }
        choice udp-choice {
          leaf udp {
            tailf:info
              "Packets to a specific UDP port";
            tailf:cli-boolean-no;
            tailf:cli-full-command;
            type boolean;
            default "true";
          }
          container udp-conf {
            tailf:cli-drop-node-name;
            container udp {
              tailf:info
                "Packets to a specific UDP port";
              tailf:cli-incomplete-command;
              tailf:cli-incomplete-no;
              list service {
                tailf:cli-drop-node-name;
                tailf:cli-suppress-mode;
                tailf:cli-delete-when-empty;
                tailf:cli-suppress-list-no;
                key "name";
                leaf name {
                  type string {
                    tailf:info
                      "WORD;;Port or UDP service name";
                  }
                }
                leaf disabled {
                  tailf:info
                    "service disabled";
                  type empty;
                }
              }
            }
          }
        }
      }
      container rcmd {
        tailf:info
          "Rcmd commands";
        leaf domain-lookup {
          tailf:info
            "Enable IP DNS queries for Rcmd";
          tailf:cli-boolean-no;
          tailf:cli-full-command;
          type boolean;
          default "true";
        }
        leaf rcp-enable {
          tailf:info
            "Enable server side of RCP";
          type empty;
        }
        leaf rsh-enable {
          tailf:info
            "Enable server side of RSH";
          type empty;
        }
        list remote-host {
          tailf:info
            "Set host+user equivalence";
          tailf:cli-suppress-mode;
          tailf:cli-delete-when-empty;
          key "local-username host remote-username";
          leaf local-username {
            type string {
              tailf:info
                "WORD;;Local username";
            }
          }
          leaf host {
            type inet:host {
              tailf:info
                "Hostname or A.B.C.D;;Remote hostname or IP address";
            }
          }
          leaf remote-username {
            type string {
              tailf:info
                "WORD;;Remote username";
            }
          }
          leaf enable {
            tailf:info
              "Allow enable-mode commands";
            type empty;
          }
        }
        container source-interface {
          tailf:info
            "Specify interface for source address in rcmd connections";
          uses interface-name-grouping;
        }
      }
      container http {
        tailf:info
          "HTTP server configuration";
        leaf server {
          tailf:info
            "Enable http server";
          tailf:cli-boolean-no;
          tailf:cli-full-command;
          type boolean;
        }
        leaf access-class {
          tailf:info
            "Restrict http server access by access-class";
          tailf:cli-full-command;
          type uint8 {
            tailf:info
              "<1-99>;;Access list number";
            range "1..99";
          }
        }
        container authentication {
          tailf:info
            "Set http server authentication method";
          choice authentication-choice {
            container aaa {
              tailf:info
                "Use AAA access control methods";
              presence "true";
              leaf exec-authorization {
                tailf:info
                  "Set method list for exec authorization";
                tailf:cli-diff-dependency "../../../../../aaa/authorization/exec" {
                  tailf:xpath-root 3;
                }
                type string {
                  tailf:info
                    "WORD;;Use an authorization list with this name.";
                }
              }
            }
            leaf local {
              tailf:info
                "Use local username and passwords";
              tailf:cli-full-command;
              type empty;
            }
          }
        }
        leaf secure-server {
          tailf:info
            "Enable HTTP secure server";
          tailf:cli-boolean-no;
          tailf:cli-full-command;
          type boolean;
        }
        container secure-active-session-modules {
          tailf:info
            "Set up active http secure server session modules";
          choice modules-choice {
            leaf name {
              tailf:cli-drop-node-name;
              tailf:cli-disallow-value "all|none";
              type string {
                tailf:info
                  "WORD;;Session module list name to activate";
              }
            }
            leaf all {
              tailf:info
                "Activate all session modules";
              type empty;
            }
            leaf none {
              tailf:info
                "Deactivate all session modules";
              type empty;
            }
            default "all";
          }
        }
        container active-session-modules {
          tailf:info
            "Set up active http server session modules";
          choice modules-choice {
            leaf name {
              tailf:cli-drop-node-name;
              tailf:cli-disallow-value "all|none";
              type string {
                tailf:info
                  "WORD;;Session module list name to activate";
              }
            }
            leaf all {
              tailf:info
                "Activate all session modules";
              type empty;
            }
            leaf none {
              tailf:info
                "Deactivate all session modules";
              type empty;
            }
            default "all";
          }
        }
        container timeout-policy {
          tailf:info
            "Set http server time-out policy parameters";
          tailf:cli-compact-syntax;
          tailf:cli-sequence-commands {
            tailf:cli-reset-all-siblings;
          }
          leaf idle {
            tailf:info
              "Idle time-out of a http server connection in seconds";
            tailf:cli-incomplete-command;
            type uint16 {
              tailf:info
                "<1-600>;;Connection idle time-out value in seconds";
              range "1..600";
            }
          }
          leaf life {
            tailf:info
              "Life time of a http server connection in seconds";
            tailf:cli-incomplete-command;
            type uint32 {
              tailf:info
                "<1-86400>;;Connection life time value in seconds";
              range "1..86400";
            }
          }
          leaf requests {
            tailf:info
              "Maximum number of requests allowed on a http server connection";
            type uint32 {
              tailf:info
                "<1-86400>;;Maximum number of requests allowed on a http server connection";
              range "1..86400";
            }
          }
        }
        container client {
          tailf:info
            "Set http client parameters";
          container source-interface {
            tailf:info
              "Specify interface for source address in all HTTP(S) client connections";
            uses interface-name-grouping;
          }
          container proxy-server {
            tailf:info
              "Specify proxy server name for HTTP file system client connections";
            tailf:cli-compact-syntax;
            tailf:cli-sequence-commands;
            leaf address {
              tailf:cli-drop-node-name;
              tailf:cli-incomplete-command;
              type inet:host {
                tailf:info
                  "WORD;;Proxy server name";
              }
            }
            leaf proxy-port {
              tailf:info
                "Specify proxy port number for HTTP file system client connections";
              type uint16 {
                tailf:info
                  "<1-65535>;;Proxy port number";
                range "1..65535";
              }
            }
          }
        }
        leaf help-path {
          tailf:info
            "HTTP help root URL";
          type string {
            tailf:info
              "WORD;;root URL for help pages";
          }
        }
      }
      container ospf {
        tailf:info
          "OSPF";
        leaf name-lookup {
          tailf:info
            "Display OSPF router ids as DNS names";
          type empty;
        }
      }
      container bgp-community {
        tailf:info
          "format for BGP community";
        leaf new-format {
          tailf:info
            "select aa:nn format for BGP community";
          type empty;
        }
      }
      container community-list {
        tailf:info
          "Add a community list entry";
        list number {
          tailf:cli-drop-node-name;
          tailf:cli-suppress-mode;
          tailf:cli-delete-when-empty;
          tailf:cli-incomplete-command;
          key "no";
          leaf no {
            type union {
              type uint16 {
                tailf:info
                  "<1-99>;;Community list number (standard)";
                range "1..99";
              }
              type uint16 {
                tailf:info
                  "<100-500>;;Community list number (expanded)";
                range "100..500";
              }
            }
          }
          uses ip-community-list-grouping;
        }
        list standard {
          tailf:info
            "Add a standard community-list entry";
          tailf:cli-suppress-mode;
          tailf:cli-delete-when-empty;
          tailf:cli-incomplete-command;
          tailf:meta-data "replace-list" {
            tailf:meta-value "ip community-list standard :: entry :: expr :: C3550";
          }
          tailf:ned-data "." {
            tailf:xpath-root 3;
            tailf:transaction to;
          }
          key "name";
          leaf name {
            type string {
              tailf:info
                "WORD;;Community list name";
            }
          }
          uses ip-community-list-grouping;
        }
        list expanded {
          tailf:info
            "Add an expanded community-list entry";
          tailf:cli-suppress-mode;
          tailf:cli-delete-when-empty;
          tailf:cli-incomplete-command;
          tailf:meta-data "replace-list" {
            tailf:meta-value "ip community-list expanded :: entry :: expr :: C3550";
          }
          tailf:ned-data "." {
            tailf:xpath-root 3;
            tailf:transaction to;
          }
          key "name";
          leaf name {
            type string {
              tailf:info
                "WORD;;Community list name";
            }
          }
          uses ip-community-list-grouping;
        }
      }
      container extcommunity-list {
        tailf:info
          "Add a extended community list entry";
        list number {
          tailf:cli-drop-node-name;
          tailf:cli-suppress-mode;
          tailf:cli-delete-when-empty;
          tailf:cli-incomplete-command;
          key "no";
          leaf no {
            type union {
              type uint16 {
                tailf:info
                  "<1-99>;;Extended Community list number (standard)";
                range "1..99";
              }
              type uint16 {
                tailf:info
                  "<100-500>;;Extended Community list number (expanded)";
                range "100..500";
              }
            }
          }
          uses ip-extcommunity-list-grouping;
        }
        container standard {
          tailf:info
            "Add a standard community-list entry";
          list no-mode-list {
            tailf:cli-drop-node-name;
            tailf:cli-suppress-mode;
            tailf:cli-delete-when-empty;
            tailf:cli-incomplete-command;
            key "name";
            leaf name {
              type string {
                tailf:info
                  "WORD;;Extended community-list name";
              }
            }
            uses ip-extcommunity-list-grouping;
          }
          list mode-list {
            tailf:cli-drop-node-name;
            tailf:cli-mode-name "config-extcomm-list";
            tailf:cli-full-command;
            key "name";
            leaf name {
              type string {
                tailf:info
                  "WORD;;Extended community-list name";
              }
            }
            list entry {
              tailf:cli-drop-node-name;
              tailf:cli-suppress-mode;
              tailf:cli-delete-when-empty;
              tailf:cli-incomplete-command;
              key "id";
              leaf id {
                type uint32 {
                  tailf:info
                    "<1-2147483647>;;Sequence Number";
                  range "1..2147483647";
                }
              }
              leaf expr {
                tailf:cli-drop-node-name;
                tailf:cli-multi-value;
                type string {
                  tailf:info
                    "<RULE>;;deny <LINE> | permit <LINE>";
                  pattern '(permit.*)|(deny.*)';
                }
              }
            }
          }
        }
        container expanded {
          tailf:info
            "Add an expanded community-list entry";
          list no-mode-list {
            tailf:cli-drop-node-name;
            tailf:cli-suppress-mode;
            tailf:cli-delete-when-empty;
            tailf:cli-incomplete-command;
            key "name";
            leaf name {
              type string {
                tailf:info
                  "WORD;;Extended community-list name";
              }
            }
            uses ip-extcommunity-list-grouping;
          }
          list mode-list {
            tailf:cli-drop-node-name;
            tailf:cli-mode-name "config-extcomm-list";
            tailf:cli-full-command;
            key "name";
            leaf name {
              type string {
                tailf:info
                  "WORD;;Extended community-list name";
              }
            }
            list entry {
              tailf:cli-drop-node-name;
              tailf:cli-suppress-mode;
              tailf:cli-delete-when-empty;
              tailf:cli-incomplete-command;
              key "id";
              leaf id {
                type uint32 {
                  tailf:info
                    "<1-2147483647>;;Sequence Number";
                  range "1..2147483647";
                }
              }
              leaf expr {
                tailf:cli-drop-node-name;
                tailf:cli-multi-value;
                type string {
                  tailf:info
                    "<RULE>;;deny <LINE> | permit <LINE>";
                  pattern '(permit.*)|(deny.*)';
                }
              }
            }
          }
        }
      }
      container as-path {
        tailf:info
          "BGP autonomous system path filter";
        list access-list {
          tailf:info
            "Specify an access list number";
          tailf:cli-suppress-mode;
          tailf:cli-delete-when-empty;
          tailf:cli-compact-syntax;
          tailf:cli-incomplete-command;
          key "name";
          leaf name {
            tailf:cli-incomplete-command;
            type string {
              tailf:info
                "WORD;;Access-list number or name";
            }
          }
          list as-path-rule {
            tailf:cli-suppress-mode;
            tailf:cli-delete-when-empty;
            tailf:cli-drop-node-name;
            tailf:cli-compact-syntax;
            tailf:cli-show-long-obu-diffs;
            ordered-by user;
            key "operation rule";
            leaf operation {
              tailf:cli-drop-node-name;
              tailf:cli-incomplete-command;
              type enumeration {
                enum "deny" {
                  tailf:code-name "operation_deny";
                  tailf:info
                    "Specify packets to reject";
                }
                enum "permit" {
                  tailf:code-name "operation_permit";
                  tailf:info
                    "Specify packets to forward";
                }
              }
            }
            leaf rule {
              tailf:cli-drop-node-name;
              tailf:cli-multi-value;
              tailf:cli-full-command;
              type string {
                tailf:info
                  "LINE;;A regular-expression to match BGP AS paths.";
              }
            }
          }
        }
      }
      container flow-cache {
        tailf:info
          "Configure netflow cache parameters";
        leaf entries {
          tailf:info
            "Specify the number of entries in the flow cache";
          type uint32 {
            tailf:info
              "<1024-524288>;;Entries";
            range "1024..524288";
          }
        }
        container timeout {
          tailf:info
            "Specify flow cache timeout parameters";
          leaf inactive {
            tailf:info
              "Specify the inactive flow timeout";
            tailf:cli-full-command;
            type uint16 {
              tailf:info
                "<10-600>;;Timeout in seconds";
              range "10..600";
            }
          }
          leaf active {
            tailf:info
              "Specify the active flow timeout";
            tailf:cli-full-command;
            type uint16 {
              tailf:info
                "<1-60>;;Timeout in minutes";
              range "1..60";
            }
          }
        }
      }
      container flow-export {
        tailf:info
          "Specify host/port to send flow statistics";
        container source {
          tailf:info
            "Specify the interface for source address";
          uses interface-name-grouping;
        }
        leaf version {
          tailf:info
            "Specify the version number";
          type enumeration {
            enum "1";
            enum "5";
            enum "9";
          }
        }
        container template {
          tailf:info
            "Specify the template specific configurations";
          tailf:cli-diff-dependency "../version" {
            tailf:xpath-root 3;
          }
          container options {
            tailf:info
              "Specify the template option";
            leaf export-stats {
              tailf:info
                "Specify the template option export statistics";
              tailf:cli-full-command;
              type empty;
            }
          }
          leaf timeout-rate {
            tailf:info
              "Specify the time before template is resent";
            tailf:cli-full-command;
            type uint16 {
              tailf:info
                "<1-3600>;;Timeout in minutes (default 30 minutes)";
              range "1..3600";
            }
            default "30";
          }
          leaf refresh-rate {
            tailf:info
              "Specify the number of export packets before template is resent";
            tailf:cli-full-command;
            type uint16 {
              tailf:info
                "<1-600>;;refresh rate in export packets (default 20 packets)";
              range "1..600";
            }
            default "20";
          }
        }
        container destination {
          tailf:info
            "Specify the Destination IP address";
          tailf:cli-compact-syntax;
          tailf:cli-sequence-commands {
            tailf:cli-reset-all-siblings;
          }
          leaf ip {
            tailf:cli-drop-node-name;
            type inet:host {
              tailf:info
                "Hostname or A.B.C.D;;Destination IP address";
            }
          }
          leaf port {
            tailf:cli-drop-node-name;
            type uint16 {
              tailf:info
                "<1-65535>;;UDP port number";
              range "1..65535";
            }
          }
        }
      }
      container flow-aggregation {
        tailf:info
          "Configure flow aggregation";
        list cache {
          tailf:info
            "Create flow aggregation cache or enter flow-cache command mode";
          tailf:cli-mode-name "config-flow-cache";
          key "name";
          leaf name {
            type string;
          }
          container cache {
            tailf:info
              "Configure netflow cache parameters";
            container timeout {
              tailf:info
                "Specify flow cache timeout parameters";
              leaf active {
                tailf:info
                  "Specify the active flow timeout";
                type uint8 {
                  tailf:info
                    "<1-60>;;Timeout in minutes";
                  range "1..60";
                }
              }
            }
          }
          container export {
            tailf:info
              "Specify host/port to send flow statistics";
            list destination {
              tailf:info
                "Specify the Destination IP address";
              tailf:cli-suppress-mode;
              tailf:cli-delete-when-empty;
              tailf:cli-compact-syntax;
              tailf:cli-incomplete-command;
              key "address";
              leaf address {
                type inet:host {
                  tailf:info
                    "Hostname or A.B.C.D;;Destination IP addres";
                }
              }
              leaf port {
                tailf:cli-drop-node-name;
                type uint16 {
                  tailf:info
                    "<1-65535>;;UDP/SCTP port number";
                  range "1..65535";
                }
              }
            }
          }
        }
      }
      container dns {
        tailf:info
          "Configure DNS server for a zone";
        list view {
          tailf:info
            "Configure a DNS view";
          tailf:cli-mode-name "cfg-dns-view";
          key "name";
          leaf name {
            type string {
              tailf:info
                "WORD;;View name";
            }
          }
          uses ip-dns-view-grouping;
        }
        container view-vrf {
          tailf:cli-drop-node-name;
          list view {
            tailf:info
              "Configure a DNS view";
            tailf:cli-mode-name "cfg-dns-view";
            key "vrf name";
            leaf vrf {
              tailf:info
                "Specify a VRF";
              tailf:cli-expose-key-name;
              tailf:cli-diff-dependency "../../../../../ip/vrf" {
                tailf:xpath-root 3;
              }
              tailf:cli-diff-dependency "../../../../../vrf/definition" {
                tailf:xpath-root 3;
              }
              type string {
                tailf:info
                  "WORD;;VRF name";
              }
            }
            leaf name {
              type string {
                tailf:info
                  "WORD;;View name";
              }
            }
            uses ip-dns-view-grouping;
          }
        }
        list view-list {
          tailf:info
            "Configure a DNS view-list";
          tailf:cli-mode-name "cfg-dns-view-list";
          key "name";
          leaf name {
            type string {
              tailf:info
                "WORD;;View-list name";
            }
          }
          list view {
            tailf:cli-mode-name "cfg-dns-view-list-member";
            tailf:cli-incomplete-command;
            key "name";
            leaf name {
              type string {
                tailf:info
                  "WORD;;View name";
              }
            }
            leaf order {
              tailf:cli-drop-node-name;
              tailf:cli-hide-in-submode;
              type uint32 {
                tailf:info
                  "<1-2147483647>;;Evaluation order";
                range "1..2147483647";
              }
            }
            container restrict {
              tailf:info
                "Configure view usage restrictions";
              leaf name-group {
                tailf:info
                  "Restrict to users matching an ip dns name-list";
                type uint32 {
                  tailf:info
                    "<1-2147483647>;;IP DNS access-list number";
                  range "1..2147483647";
                }
              }
              leaf authenticate {
                tailf:info
                  "Restrict to authenticated users";
                type empty;
              }
            }
          }
          container view-vrf {
            tailf:cli-drop-node-name;
            list view {
              tailf:cli-mode-name "cfg-dns-view-list-member";
              tailf:cli-incomplete-command;
              key "vrf name";
              leaf vrf {
                tailf:info
                  "Specify vrf";
                tailf:cli-expose-key-name;
                tailf:cli-diff-dependency "../../../../../../ip/vrf" {
                  tailf:xpath-root 3;
                }
                tailf:cli-diff-dependency "../../../../../../vrf/definition" {
                  tailf:xpath-root 3;
                }
                type string {
                  tailf:info
                    "WORD;;vrf name";
                }
              }
              leaf name {
                type string {
                  tailf:info
                    "WORD;;View name";
                }
              }
              leaf order {
                tailf:cli-drop-node-name;
                tailf:cli-hide-in-submode;
                type uint32 {
                  tailf:info
                    "<1-2147483647>;;Evaluation order";
                  range "1..2147483647";
                }
              }
              container restrict {
                tailf:info
                  "Configure view usage restrictions";
                leaf name-group {
                  tailf:info
                    "Restrict to users matching an ip dns name-list";
                  type uint32 {
                    tailf:info
                      "<1-2147483647>;;IP DNS access-list number";
                    range "1..2147483647";
                  }
                }
                leaf authenticate {
                  tailf:info
                    "Restrict to authenticated users";
                  type empty;
                }
              }
            }
          }
        }
        list name-list {
          tailf:info
            "Regular expression name-list";
          tailf:cli-suppress-mode;
          tailf:cli-delete-when-empty;
          tailf:cli-compact-syntax;
          key "id operation";
          leaf id {
            type uint16 {
              tailf:info
                "<1-500>;;Regular expression name-list number";
              range "1..500";
            }
          }
          leaf operation {
            type enumeration {
              enum "permit" {
                tailf:info
                  "Specify packets to forward";
              }
              enum "deny" {
                tailf:info
                  "Specify packets to reject";
              }
            }
          }
          leaf regexp {
            tailf:cli-drop-node-name;
            tailf:cli-multi-value;
            tailf:cli-preformatted;
            tailf:cli-full-command;
            type string {
              tailf:info
                "LINE;;A regular-expression to match hostnames";
            }
          }
        }
        container server {
          tailf:info
            "Enable DNS server";
          tailf:cli-display-separated;
          presence "true";
          leaf view-group {
            tailf:info
              "Configure a DNS view-list for global use on this system";
            tailf:non-strict-leafref {
              path "../../../../ip/dns/view-list/name";
            }
            type string {
              tailf:info
                "WORD;;View-list name";
            }
          }
        }
        container spoofing {
          tailf:info
            "Configure DNS spoofing";
          presence "true";
        }
      }
      container mobile {
        tailf:info
          "Enable Mobile IP services";
        container secure {
          tailf:info
            "Security association";
          list home-agent {
            tailf:info
              "Home agent security association";
            tailf:cli-suppress-mode;
            tailf:cli-delete-when-empty;
            tailf:cli-compact-syntax;
            tailf:cli-sequence-commands {
              tailf:cli-reset-all-siblings;
            }
            key "lower-address";
            leaf lower-address {
              tailf:cli-diff-dependency "../../../../../router/mobile" {
                tailf:xpath-root 3;
              }
              type inet:ipv4-address {
                tailf:info
                  "A.B.C.D;;IP address (lower range)";
              }
            }
            leaf upper-address {
              tailf:cli-drop-node-name;
              tailf:cli-optional-in-sequence;
              type inet:ipv4-address {
                tailf:info
                  "A.B.C.D;;Upper range IP address for security";
              }
            }
            choice spi-choice {
              case single-spi {
                container spi {
                  tailf:info
                    "Security parameter index - bidirectional";
                  tailf:cli-flatten-container;
                  tailf:cli-compact-syntax;
                  uses mobile-ip-spi-grouping;
                }
              }
              case range-spi {
                container inbound-spi {
                  tailf:info
                    "Security parameter index - inbound";
                  tailf:cli-flatten-container;
                  tailf:cli-compact-syntax;
                  uses mobile-ip-spi-grouping;
                }
                container outbound-spi {
                  tailf:info
                    "Security parameter index - outbound";
                  tailf:cli-flatten-container;
                  tailf:cli-compact-syntax;
                  uses mobile-ip-spi-grouping;
                }
              }
            }
            container key {
              tailf:info
                "Security key";
              tailf:cli-flatten-container;
              tailf:cli-compact-syntax;
              choice key-choice {
                leaf ascii {
                  tailf:info
                    "Key entered in ASCII string";
                  type string {
                    tailf:info
                      "WORD;;Key entered in ASCII";
                  }
                }
                leaf hex {
                  tailf:info
                    "Key entered in hex string";
                  type string {
                    tailf:info
                      "Hex-string;;Hex string";
                  }
                }
              }
            }
            container algorithm {
              tailf:cli-break-sequence-commands;
              tailf:info
                "Authentication algorithm";
              tailf:cli-flatten-container;
              tailf:cli-compact-syntax;
              choice algorithm-choice {
                leaf hmac-md5 {
                  tailf:info
                    "HMAC MD5 authentication";
                  type empty;
                }
                container md5 {
                  tailf:info
                    "Keyed MD5 authentication";
                  tailf:cli-flatten-container;
                  tailf:cli-compact-syntax;
                  container mode {
                    tailf:info
                      "Authentication mode";
                    tailf:cli-flatten-container;
                    tailf:cli-compact-syntax;
                    leaf prefix-suffix {
                      tailf:info
                        "Prefix-suffix mode";
                      type empty;
                    }
                  }
                }
              }
            }
            leaf ignore-spi {
              tailf:info
                "Ignore SPI for Authentication";
              type empty;
            }
          }
        }
        container router {
          tailf:info
            "Mobile Router commands";
          tailf:cli-add-mode;
          tailf:cli-mode-name "mobile-router";
          tailf:cli-diff-dependency "../../../router/mobile" {
            tailf:xpath-root 3;
          }
          presence "true";
          container address {
            tailf:info
              "Mobile router's home address";
            tailf:cli-compact-syntax;
            tailf:cli-sequence-commands {
              tailf:cli-reset-all-siblings;
            }
            leaf ipv4-address {
              tailf:cli-drop-node-name;
              tailf:cli-incomplete-command;
              tailf:cli-diff-dependency "../../../../../router/mobile" {
                tailf:xpath-root 3;
              }
              type inet:ipv4-address {
                tailf:info
                  "A.B.C.D;;IP address";
              }
            }
            leaf ipv4-mask {
              tailf:cli-drop-node-name;
              type inet:ipv4-address {
                tailf:info
                  "A.B.C.D;;Home network mask";
              }
            }
          }
          container collocated {
            tailf:info
              "Collocated CoA parameters";
            leaf single-tunnel {
              tailf:info
                "Optimized tunneling between MR and HA";
              tailf:cli-diff-dependency "../../../../../router/mobile" {
                tailf:xpath-root 3;
              }
              type empty;
            }
          }
          list home-agent {
            tailf:info
              "Mobile router's home agent";
            tailf:cli-suppress-mode;
            tailf:cli-delete-when-empty;
            tailf:cli-diff-dependency "../../../../router/mobile" {
              tailf:xpath-root 3;
            }
            key "address";
            leaf address {
              type inet:ipv4-address {
                tailf:info
                  "A.B.C.D;;IP address";
              }
            }
            leaf priority {
              tailf:info
                "Priority level";
              type uint8 {
                tailf:info
                  "<0-255>;;Priority value (default is 100)";
              }
              default "100";
            }
          }
          list mobile-network {
            tailf:info
              "Mobile router's mobile network";
            tailf:cli-suppress-mode;
            tailf:cli-delete-when-empty;
            key "name";
            leaf name {
              tailf:cli-diff-dependency "../../../../../interface" {
                tailf:xpath-root 3;
              }
              type string {
                tailf:info
                  "WORD;;Interface Name";
              }
            }
            container policy {
              tailf:info
                "Enable MIP policy routing";
              leaf mobile-map {
                tailf:info
                  "Apply mobile-map dyn route-map";
                type string {
                  tailf:info
                    "WORD;;mobile-map tag";
                }
              }
            }
          }
          container register {
            tailf:info
              "Registration settings";
            container extend {
              tailf:info
                "Extend registration lifetime";
              tailf:cli-compact-syntax;
              tailf:cli-sequence-commands {
                tailf:cli-reset-siblings;
              }
              leaf expire {
                tailf:info
                  "Reregister before expiration";
                tailf:cli-incomplete-command;
                tailf:cli-diff-dependency "../../../../../../router/mobile" {
                  tailf:xpath-root 3;
                }
                type uint16 {
                  tailf:info
                    "<1-3600>;;Number of seconds before expiration";
                  range "1..3600";
                }
              }
              leaf retry {
                tailf:info
                  "Number of attempts to extend registration";
                tailf:cli-incomplete-command;
                type uint8 {
                  tailf:info
                    "<0-10>;;Stop after number of retries attempted";
                  range "0..10";
                }
              }
              leaf interval {
                tailf:info
                  "Interval between retries";
                type uint16 {
                  tailf:info
                    "<1-3600>;;Number of seconds between attempts";
                  range "1..3600";
                }
              }
              leaf reverse-tunnel {
                type empty;
              }
            }
          }
          leaf reverse-tunnel {
            tailf:info
              "Reverse Tunnel requested";
            type empty;
          }
          container tunnel {
            tailf:info
              "Tunnel parameters";
            container mode {
              tailf:info
                "Tunnel mode";
              leaf gre {
                tailf:info
                  "GRE encapsulation";
                type empty;
              }
            }
          }
          container template {
            tailf:info
              "Configure a tunnel template for tunnels to the Home Agent";
            leaf Tunnel {
              tailf:info
                "Tunnel interface";
              tailf:cli-allow-join-with-value {
                tailf:cli-display-joined;
              }
              type uint32 {
                tailf:info
                  "<0-2147483647>;;Tunnel interface number";
              }
            }
          }
        }
      }
      container pim {
        tailf:info
          "PIM global commands";
        tailf:cli-diff-dependency "../../interface" {
          tailf:xpath-root 3;
        }
        uses ip-pim-grouping;
        list vrf {
          tailf:info
            "Select VPN Routing/Forwarding instance";
          tailf:cli-suppress-mode;
          tailf:cli-delete-when-empty;
          key "id";
          leaf id {
            tailf:cli-diff-dependency "../../../../ip/vrf" {
              tailf:xpath-root 3;
            }
            tailf:cli-diff-dependency "../../../../vrf/definition" {
              tailf:xpath-root 3;
            }
            type string {
              tailf:info
                "WORD;;VPN Routing/Forwarding instance name";
            }
          }
          uses ip-pim-grouping;
        }
      }
      container rsvp {
        tailf:info
          "Configure static RSVP information";
        container signalling {
          tailf:info
            "RSVP Signalling";
          container refresh {
            tailf:info
              "Configure RSVP refresh behavior";
            container reduction-conf {
              tailf:cli-drop-node-name;
              container reduction {
                tailf:info
                  "Configure refresh reduction";
                tailf:cli-incomplete-command;
                tailf:cli-incomplete-no;
                leaf ack-delay {
                  tailf:info
                    "Time to wait to accumulate ACKs (msecs)";
                  type uint16 {
                    tailf:info
                      "<100-10000>;;ACK delay (msecs)";
                    range "100..10000";
                  }
                }
              }
            }
            leaf reduction {
              tailf:info
                "Configure refresh reduction";
              tailf:cli-full-command;
              type empty;
            }
          }
          container hello {
            tailf:info
              "Enable neighbor-down detection";
            tailf:cli-delete-when-empty;
            presence "true";
            container graceful-restart {
              tailf:info
                "Configure RSVP Graceful Restart";
              leaf mode {
                tailf:info
                  "Select Graceful Restart capabilities";
                type enumeration {
                  enum "full" {
                    tailf:info
                      "Capable of recovering self, and helping neighbor recover";
                  }
                  enum "help-neighbor" {
                    tailf:info
                      "Capable of helping neighbor recover";
                  }
                }
              }
            }
          }
        }
      }
      container nat {
        tailf:info
          "NAT configuration commands";
        container settings {
          tailf:info
            "NAT general settings";
          leaf mode {
            tailf:info
              "NAT operating mode";
            type enumeration {
              enum "cgn" {
                tailf:info
                  "The carrier grade NAT (CGN) operating mode";
              }
              enum "default" {
                tailf:info
                  "The default NAT operating mode";
              }
            }
            default "default";
          }
        }
        container translation {
          tailf:info
            "NAT translation entry configuration";
          leaf finrst-timeout {
            tailf:info
              "Specify timeout for NAT TCP flows after a FIN or RST";
            type union {
              type uint32 {
                tailf:info
                  "<0-536870>;;Timeout in seconds";
                range "0..536870";
              }
              type enumeration {
                enum "never" {
                  tailf:info
                    "Never timeout";
                }
              }
            }
          }
          leaf icmp-timeout {
            tailf:info
              "Specify timeout for NAT ICMP flows";
            type union {
              type uint32 {
                tailf:info
                  "<0-536870>;;Timeout in seconds";
                range "0..536870";
              }
              type enumeration {
                enum "never" {
                  tailf:info
                    "Never timeout";
                }
              }
            }
          }
          leaf tcp-timeout {
            tailf:info
              "Specify timeout for NAT TCP flows";
            type union {
              type uint32 {
                tailf:info
                  "<0-536870>;;Timeout in seconds";
                range "0..536870";
              }
              type enumeration {
                enum "never" {
                  tailf:info
                    "Never timeout";
                }
              }
            }
          }
          container max-entries {
            tailf:info
              "Specify maximum number of NAT entries";
            leaf all-host {
              tailf:info
                "Specify maximum number of NAT entries for each host";
              type uint32 {
                tailf:info
                  "<1-2147483647>;;Number of entries";
                range "1..2147483647";
              }
            }
            list vrf {
              tailf:cli-suppress-mode;
              tailf:cli-delete-when-empty;
              tailf:cli-incomplete-command;
              tailf:cli-diff-dependency "../../../../../ip/vrf" {
                tailf:xpath-root 3;
              }
              tailf:cli-diff-dependency "../../../../../vrf/definition" {
                tailf:xpath-root 3;
              }
              key "name";
              leaf name {
                type string {
                  tailf:info
                    "Specify per-VRF NAT entry limit";
                }
              }
              leaf number {
                tailf:cli-drop-node-name;
                type uint32 {
                  tailf:info
                    "<1-2147483647>;;Number of entries";
                  range "1..2147483647";
                }
              }
            }
            container list {
              tailf:info
                "Specify access list based NAT entry limit";
              tailf:cli-compact-syntax;
              tailf:cli-sequence-commands {
                tailf:cli-reset-siblings;
              }
              leaf access-list {
                tailf:cli-drop-node-name;
                tailf:cli-incomplete-command;
                type exp-ip-acl-type;
              }
              leaf number {
                tailf:cli-drop-node-name;
                type uint32 {
                  tailf:info
                    "<1-2147483647>;;Number of entries";
                  range "1..2147483647";
                }
              }
            }
          }
        }
        container service {
          tailf:info
            "Special translation for application using non-standard port";
          container list-ftp-tcp {
            tailf:cli-drop-node-name;
            list list {
              tailf:info
                "Specify access list describing global addresses";
              tailf:cli-suppress-mode;
              tailf:cli-delete-when-empty;
              tailf:cli-compact-syntax;
              tailf:cli-sequence-commands {
                tailf:cli-reset-siblings;
              }
              key "access-list port";
              leaf access-list {
                type union {
                  type uint16 {
                    tailf:info
                      "<1-2699>;;Access list number for global addresses";
                  }
                  type string {
                    tailf:info
                      "WORD;;Access list name for server local address";
                  }
                }
              }
              leaf ftp {
                tailf:info
                  "ftp protocol";
                tailf:cli-prefix-key {
                  tailf:cli-before-key 2;
                }
                type empty;
              }
              leaf tcp {
                tailf:info
                  "TCP protocol";
                tailf:cli-prefix-key {
                  tailf:cli-before-key 2;
                }
                type empty;
              }
              leaf port {
                tailf:info
                  "Special non-standard port";
                tailf:cli-expose-key-name;
                type uint16 {
                  tailf:info
                    "<1-65535>;;Port number";
                  range "1..65535";
                }
              }
            }
          }
        }
        list pool {
          tailf:info
            "Define pool of addresses";
          tailf:cli-suppress-mode;
          tailf:cli-delete-when-empty;
          tailf:cli-compact-syntax;
          tailf:cli-sequence-commands {
            tailf:cli-reset-siblings;
          }
          key "id";
          leaf id {
            type string {
              tailf:info
                "WORD;;Pool name";
            }
          }
          leaf start-address {
            tailf:cli-drop-node-name;
            tailf:cli-optional-in-sequence;
            type inet:ipv4-address {
              tailf:info
                "A.B.C.D;;Start IP address";
            }
          }
          leaf end-address {
            tailf:cli-drop-node-name;
            when "../start-address" {
              tailf:xpath-root 3;
              tailf:dependency "../start-address";
            }
            type inet:ipv4-address {
              tailf:info
                "A.B.C.D;;End IP address";
            }
          }
          choice prefix-choice {
            leaf netmask {
              tailf:info
                "Specify the network mask";
              type inet:ipv4-address {
                tailf:info
                  "A.B.C.D;;Network mask";
              }
            }
            leaf prefix-length {
              tailf:info
                "Specify the prefix length";
              type uint8 {
                tailf:info
                  "<1-32>;;Prefix length";
                range "1..32";
              }
            }
          }
          leaf accounting {
            tailf:cli-optional-in-sequence;
            tailf:info
              "Specify the accounting";
            type string {
              tailf:info
                "WORD;;Accounting method-list name";
            }
          }
          choice nat-choice {
            leaf arp-ping {
              tailf:info
                "WLAN ARP Ping";
              type empty;
            }
            leaf type {
              tailf:info
                "Specify the pool type";
              type enumeration {
                enum "match-host" {
                  tailf:info
                    "Keep host numbers the same after translation";
                }
                enum "rotary" {
                  tailf:info
                    "Rotary address pool";
                }
              }
            }
            leaf add-route {
              tailf:info
                "Add special route to Virtual Interface";
              type empty;
            }
          }
        }
        container inside {
          tailf:info
            "Inside address translation";
          container source {
            tailf:info
              "Source address translation";
            list list {
              tailf:info
                "Specify access list describing local addresses";
              tailf:cli-suppress-mode;
              tailf:cli-delete-when-empty;
              tailf:cli-compact-syntax;
              tailf:cli-sequence-commands {
                tailf:cli-reset-all-siblings;
              }
              tailf:cli-incomplete-command;
              key "id";
              leaf id {
                type union {
                  type uint16 {
                    tailf:info
                      "<1-2699>;;Access list number for global addresses";
                    range "1..2699";
                  }
                  type string {
                    tailf:info
                      "WORD;;Access list name for global addresses";
                  }
                }
              }
              uses ip-nat-inside-grouping;
              uses ip-nat-inside-options-grouping;
            }
            container list-vrf {
              tailf:cli-drop-node-name;
              list list {
                tailf:info
                  "Specify access list describing local addresses";
                tailf:cli-suppress-mode;
                tailf:cli-delete-when-empty;
                tailf:cli-compact-syntax;
                tailf:cli-sequence-commands {
                  tailf:cli-reset-all-siblings;
                }
                tailf:cli-incomplete-command;
                tailf:cli-diff-dependency "../../../../../../ip/vrf" {
                  tailf:xpath-root 3;
                }
                tailf:cli-diff-dependency "../../../../../../vrf/definition" {
                  tailf:xpath-root 3;
                }
                key "id vrf";
                leaf id {
                  type union {
                    type uint16 {
                      tailf:info
                        "<1-2699>;;Access list number for global addresses";
                      range "1..2699";
                    }
                    type string {
                      tailf:info
                        "WORD;;Access list name for global addresses";
                    }
                  }
                }
                uses ip-nat-inside-vrf-grouping;
                uses ip-nat-inside-options-grouping;
              }
            }
            container static {
              tailf:info
                "Specify static local->global mapping";
              list nat-static-address-list {
                tailf:cli-drop-node-name;
                tailf:cli-suppress-mode;
                tailf:cli-delete-when-empty;
                tailf:cli-compact-syntax;
                tailf:cli-sequence-commands {
                  tailf:cli-reset-siblings;
                }
                key "local-ip global-ip";
                leaf local-ip {
                  type inet:ipv4-address {
                    tailf:info
                      "A.B.C.D;;Inside local IP address";
                  }
                }
                leaf global-ip {
                  type inet:ipv4-address {
                    tailf:info
                      "A.B.C.D;;Inside global IP address";
                  }
                }
                uses ip-nat-source-static-grouping;
              }
              list nat-static-address-list-vrf {
                tailf:cli-drop-node-name;
                tailf:cli-suppress-mode;
                tailf:cli-delete-when-empty;
                tailf:cli-compact-syntax;
                tailf:cli-sequence-commands {
                  tailf:cli-reset-siblings;
                }
                key "local-ip global-ip vrf";
                leaf local-ip {
                  type inet:ipv4-address {
                    tailf:info
                      "A.B.C.D;;Inside local IP address";
                  }
                }
                leaf global-ip {
                  type inet:ipv4-address {
                    tailf:info
                      "A.B.C.D;;Inside global IP address";
                  }
                }
                leaf vrf {
                  tailf:info
                    "Specify vrf";
                  tailf:cli-expose-key-name;
                  tailf:cli-diff-dependency "../../../../../../../ip/vrf" {
                    tailf:xpath-root 3;
                  }
                  tailf:cli-diff-dependency "../../../../../../../vrf/definition" {
                    tailf:xpath-root 3;
                  }
                  type string {
                    tailf:info
                      "WORD;;vrf name";
                  }
                }
                uses ip-nat-source-static-grouping;
              }
              list nat-static-transport-list {
                tailf:cli-drop-node-name;
                tailf:cli-suppress-mode;
                tailf:cli-delete-when-empty;
                tailf:cli-compact-syntax;
                tailf:cli-sequence-commands {
                  tailf:cli-reset-siblings;
                }
                key "proto local-ip local-port global-ip global-port";
                leaf proto {
                  type enumeration {
                    enum "tcp" {
                      tailf:info
                        "Transmission Control Protocol";
                    }
                    enum "udp" {
                      tailf:info
                        "User Datagram Protocol";
                    }
                  }
                }
                leaf local-ip {
                  type inet:ipv4-address {
                    tailf:info
                      "A.B.C.D;;Inside local IP address";
                  }
                }
                leaf local-port {
                  type uint16 {
                    tailf:info
                      "<1-65535>;;Local UDP/TCP port";
                    range "1..65535";
                  }
                }
                leaf global-ip {
                  type inet:ipv4-address {
                    tailf:info
                      "A.B.C.D;;Inside global IP address";
                  }
                }
                leaf global-port {
                  type uint16 {
                    tailf:info
                      "<1-65535>;;Global UDP/TCP port";
                    range "1..65535";
                  }
                }
                uses ip-nat-source-static-grouping;
              }
              list nat-static-transport-list-vrf {
                tailf:cli-drop-node-name;
                tailf:cli-suppress-mode;
                tailf:cli-delete-when-empty;
                tailf:cli-compact-syntax;
                tailf:cli-sequence-commands {
                  tailf:cli-reset-siblings;
                }
                key "proto local-ip local-port global-ip global-port vrf";
                leaf proto {
                  type enumeration {
                    enum "tcp" {
                      tailf:info
                        "Transmission Control Protocol";
                    }
                    enum "udp" {
                      tailf:info
                        "User Datagram Protocol";
                    }
                  }
                }
                leaf local-ip {
                  type inet:ipv4-address {
                    tailf:info
                      "A.B.C.D;;Inside local IP address";
                  }
                }
                leaf local-port {
                  type uint16 {
                    tailf:info
                      "<1-65535>;;Local UDP/TCP port";
                    range "1..65535";
                  }
                }
                leaf global-ip {
                  type inet:ipv4-address {
                    tailf:info
                      "A.B.C.D;;Inside global IP address";
                  }
                }
                leaf global-port {
                  type uint16 {
                    tailf:info
                      "<1-65535>;;Global UDP/TCP port";
                    range "1..65535";
                  }
                }
                leaf vrf {
                  tailf:info
                    "Specify vrf";
                  tailf:cli-expose-key-name;
                  tailf:cli-diff-dependency "../../../../../../../ip/vrf" {
                    tailf:xpath-root 3;
                  }
                  tailf:cli-diff-dependency "../../../../../../../vrf/definition" {
                    tailf:xpath-root 3;
                  }
                  type string {
                    tailf:info
                      "WORD;;vrf name";
                  }
                }
                uses ip-nat-source-static-grouping;
              }
              list nat-static-transport-interface-list {
                tailf:cli-drop-node-name;
                tailf:cli-suppress-mode;
                tailf:cli-delete-when-empty;
                tailf:cli-compact-syntax;
                tailf:cli-sequence-commands {
                  tailf:cli-reset-siblings;
                }
                tailf:cli-incomplete-command;
                key "proto local-ip local-port";
                leaf proto {
                  type enumeration {
                    enum "tcp" {
                      tailf:info
                        "Transmission Control Protocol";
                    }
                    enum "udp" {
                      tailf:info
                        "User Datagram Protocol";
                    }
                  }
                }
                leaf local-ip {
                  type inet:ipv4-address {
                    tailf:info
                      "A.B.C.D;;Inside local IP address";
                  }
                }
                leaf local-port {
                  type uint16 {
                    tailf:info
                      "<1-65535>;;Local UDP/TCP port";
                    range "1..65535";
                  }
                }
                container interface {
                  tailf:info
                    "Specify interface for global address";
                  tailf:cli-flatten-container;
                  tailf:cli-compact-syntax;
                  uses interface-name-grouping;
                }
                leaf global-port {
                  tailf:cli-drop-node-name;
                  type uint16 {
                    tailf:info
                      "<1-65535>;;Global UDP/TCP port";
                    range "1..65535";
                  }
                }
              }
            }
            list route-map {
              tailf:info
                "Specify route-map";
              tailf:cli-suppress-mode;
              tailf:cli-delete-when-empty;
              tailf:cli-compact-syntax;
              tailf:cli-sequence-commands {
                tailf:cli-reset-all-siblings;
              }
              tailf:cli-incomplete-command;
              key "id";
              leaf id {
                type string {
                  tailf:info
                    "WORD;;Route-map name";
                }
              }
              uses ip-nat-inside-grouping;
              uses ip-nat-inside-options-grouping;
            }
            container route-map-vrf {
              tailf:cli-drop-node-name;
              list route-map {
                tailf:info
                  "Specify route-map";
                tailf:cli-suppress-mode;
                tailf:cli-delete-when-empty;
                tailf:cli-compact-syntax;
                tailf:cli-sequence-commands {
                  tailf:cli-reset-all-siblings;
                }
                tailf:cli-incomplete-command;
                tailf:cli-diff-dependency "../../../../../../ip/vrf" {
                  tailf:xpath-root 3;
                }
                tailf:cli-diff-dependency "../../../../../../vrf/definition" {
                  tailf:xpath-root 3;
                }
                key "id vrf";
                leaf id {
                  type string {
                    tailf:info
                      "WORD;;Route-map name";
                  }
                }
                uses ip-nat-inside-vrf-grouping;
                uses ip-nat-inside-options-grouping;
              }
            }
          }
          container destination {
            tailf:info
              "Destination address translation";
            list list {
              tailf:info
                "Specify access list describing global addresses";
              tailf:cli-suppress-mode;
              tailf:cli-delete-when-empty;
              tailf:cli-compact-syntax;
              tailf:cli-sequence-commands {
                tailf:cli-reset-siblings;
              }
              tailf:cli-incomplete-command;
              key "id";
              leaf id {
                type union {
                  type uint16 {
                    tailf:info
                      "<1-2699>;;Access list number for global addresses";
                    range "1..2699";
                  }
                  type string {
                    tailf:info
                      "WORD;;Access list name for global addresses";
                  }
                }
              }
              leaf pool {
                tailf:info
                  "Name pool of local addresses";
                tailf:non-strict-leafref {
                  path "../../../../../../ip/nat/pool/id";
                }
                type string {
                  tailf:info
                    "WORD;;Pool name for local addresses ";
                }
              }
              leaf redundancy {
                tailf:info
                  "NAT redundancy operation";
                tailf:cli-optional-in-sequence;
                type uint8 {
                  tailf:info
                    "<1-2>;;IP redundancy ID";
                  range "1..2";
                }
              }
              leaf mapping-id {
                tailf:info
                  "Associate a mapping id to this mapping";
                type uint32 {
                  tailf:info
                    "<1-2147483647>;;Stateful NAT mapping id";
                  range "1..2147483647";
                }
              }
            }
          }
        }
        container outside {
          tailf:info
            "Outside address translation";
          container source {
            tailf:info
              "Source address translation";
            list list {
              tailf:info
                "Specify access list describing global addresses";
              tailf:cli-suppress-mode;
              tailf:cli-delete-when-empty;
              tailf:cli-compact-syntax;
              tailf:cli-sequence-commands {
                tailf:cli-reset-siblings;
              }
              key "id";
              leaf id {
                type union {
                  type uint16 {
                    tailf:info
                      "<1-2699>;;Access list number for global addresses";
                    range "1..2699";
                  }
                  type string {
                    tailf:info
                      "WORD;;Access list name for global addresses";
                  }
                }
              }
              leaf pool {
                tailf:info
                  "Name pool of local addresses";
                tailf:non-strict-leafref {
                  path "../../../../../../ip/nat/pool/id";
                }
                type string {
                  tailf:info
                    "WORD;;Pool name for local addresses ";
                }
              }
              uses ip-nat-outside-source-grouping;
            }
            container list-vrf {
              tailf:cli-drop-node-name;
              list list {
                tailf:info
                  "Specify access list describing local addresses";
                tailf:cli-suppress-mode;
                tailf:cli-delete-when-empty;
                tailf:cli-compact-syntax;
                tailf:cli-sequence-commands {
                  tailf:cli-reset-all-siblings;
                }
                key "id vrf";
                leaf id {
                  type union {
                    type uint16 {
                      tailf:info
                        "<1-2699>;;Access list number for global addresses";
                      range "1..2699";
                    }
                    type string {
                      tailf:info
                        "WORD;;Access list name for global addresses";
                    }
                  }
                }
                leaf pool {
                  tailf:info
                    "Name pool of local addresses";
                  tailf:cli-prefix-key {
                    tailf:cli-before-key 2;
                  }
                  tailf:non-strict-leafref {
                    path "../../../../../../../ip/nat/pool/id";
                  }
                  type string {
                    tailf:info
                      "WORD;;Pool name for local addresses ";
                  }
                }
                leaf vrf {
                  tailf:info
                    "Specify vrf";
                  tailf:cli-expose-key-name;
                  tailf:cli-diff-dependency "../../../../../../../ip/vrf" {
                    tailf:xpath-root 3;
                  }
                  tailf:cli-diff-dependency "../../../../../../../vrf/definition" {
                    tailf:xpath-root 3;
                  }
                  type string {
                    tailf:info
                      "WORD;;vrf name";
                  }
                }
                uses ip-nat-outside-source-grouping;
              }
            }
            list route-map {
              tailf:info
                "Specify route-map";
              tailf:cli-suppress-mode;
              tailf:cli-delete-when-empty;
              tailf:cli-compact-syntax;
              tailf:cli-sequence-commands {
                tailf:cli-reset-siblings;
              }
              key "id";
              leaf id {
                type string {
                  tailf:info
                    "WORD;;Route-map name";
                }
              }
              leaf pool {
                tailf:info
                  "Name pool of local addresses";
                tailf:non-strict-leafref {
                  path "../../../../pool/id";
                }
                type string {
                  tailf:info
                    "WORD;;Pool Name";
                }
              }
              uses ip-nat-outside-source-grouping;
            }
            container route-map-vrf {
              tailf:cli-drop-node-name;
              list route-map {
                tailf:info
                  "Specify route-map";
                tailf:cli-suppress-mode;
                tailf:cli-delete-when-empty;
                tailf:cli-compact-syntax;
                tailf:cli-sequence-commands {
                  tailf:cli-reset-siblings;
                }
                key "id vrf";
                leaf id {
                  type string {
                    tailf:info
                      "WORD;;Route-map name";
                  }
                }
                leaf pool {
                  tailf:info
                    "Name pool of local addresses";
                  tailf:cli-prefix-key {
                    tailf:cli-before-key 2;
                  }
                  tailf:non-strict-leafref {
                    path "../../../../../pool/id";
                  }
                  type string {
                    tailf:info
                      "WORD;;Pool Name";
                  }
                }
                leaf vrf {
                  tailf:info
                    "Specify vrf";
                  tailf:cli-expose-key-name;
                  tailf:cli-diff-dependency "../../../../../../vrf" {
                    tailf:xpath-root 3;
                  }
                  tailf:cli-diff-dependency "../../../../../../../vrf/definition" {
                    tailf:xpath-root 3;
                  }
                  type string {
                    tailf:info
                      "WORD;;vrf name";
                  }
                }
                uses ip-nat-outside-source-grouping;
              }
            }
            container static {
              tailf:info
                "Specify static global->local mapping";
              list nat-static-address-list {
                tailf:cli-drop-node-name;
                tailf:cli-suppress-mode;
                tailf:cli-delete-when-empty;
                tailf:cli-compact-syntax;
                tailf:cli-sequence-commands {
                  tailf:cli-reset-siblings;
                }
                key "global-ip local-ip";
                leaf global-ip {
                  type inet:ipv4-address {
                    tailf:info
                      "A.B.C.D;;Outside global IP address";
                  }
                }
                leaf local-ip {
                  type inet:ipv4-address {
                    tailf:info
                      "A.B.C.D;;Outside local IP address";
                  }
                }
                uses ip-nat-source-static-grouping;
              }
              list nat-static-address-list-vrf {
                tailf:cli-drop-node-name;
                tailf:cli-suppress-mode;
                tailf:cli-delete-when-empty;
                tailf:cli-compact-syntax;
                tailf:cli-sequence-commands {
                  tailf:cli-reset-siblings;
                }
                key "global-ip local-ip";
                leaf global-ip {
                  type inet:ipv4-address {
                    tailf:info
                      "A.B.C.D;;Outside global IP address";
                  }
                }
                leaf local-ip {
                  type inet:ipv4-address {
                    tailf:info
                      "A.B.C.D;;Outside local IP address";
                  }
                }
                leaf vrf {
                  tailf:info
                    "Specify vrf";
                  tailf:cli-expose-key-name;
                  tailf:cli-diff-dependency "../../../../../../vrf" {
                    tailf:xpath-root 3;
                  }
                  tailf:cli-diff-dependency "../../../../../../../vrf/definition" {
                    tailf:xpath-root 3;
                  }
                  type string {
                    tailf:info
                      "WORD;;vrf name";
                  }
                }
                uses ip-nat-source-static-grouping;
              }
              list nat-static-transport-list {
                tailf:cli-drop-node-name;
                tailf:cli-suppress-mode;
                tailf:cli-delete-when-empty;
                tailf:cli-compact-syntax;
                tailf:cli-sequence-commands {
                  tailf:cli-reset-siblings;
                }
                key "proto global-ip global-port local-ip local-port";
                leaf proto {
                  type enumeration {
                    enum "tcp" {
                      tailf:info
                        "Transmission Control Protocol";
                    }
                    enum "udp" {
                      tailf:info
                        "User Datagram Protocol";
                    }
                  }
                }
                leaf global-ip {
                  type inet:ipv4-address {
                    tailf:info
                      "A.B.C.D;;Outside global IP address";
                  }
                }
                leaf global-port {
                  type uint16 {
                    tailf:info
                      "<1-65535>;;Global UDP/TCP port";
                    range "1..65535";
                  }
                }
                leaf local-ip {
                  type inet:ipv4-address {
                    tailf:info
                      "A.B.C.D;;Outside local IP address";
                  }
                }
                leaf local-port {
                  type uint16 {
                    tailf:info
                      "<1-65535>;;Local UDP/TCP port";
                    range "1..65535";
                  }
                }
                uses ip-nat-source-static-grouping;
              }
              list nat-static-transport-list-vrf {
                tailf:cli-drop-node-name;
                tailf:cli-suppress-mode;
                tailf:cli-delete-when-empty;
                tailf:cli-compact-syntax;
                tailf:cli-sequence-commands {
                  tailf:cli-reset-siblings;
                }
                key "proto global-ip global-port local-ip local-port vrf";
                leaf proto {
                  type enumeration {
                    enum "tcp" {
                      tailf:info
                        "Transmission Control Protocol";
                    }
                    enum "udp" {
                      tailf:info
                        "User Datagram Protocol";
                    }
                  }
                }
                leaf global-ip {
                  type inet:ipv4-address {
                    tailf:info
                      "A.B.C.D;;Outside global IP address";
                  }
                }
                leaf global-port {
                  type uint16 {
                    tailf:info
                      "<1-65535>;;Global UDP/TCP port";
                    range "1..65535";
                  }
                }
                leaf local-ip {
                  type inet:ipv4-address {
                    tailf:info
                      "A.B.C.D;;Outside local IP address";
                  }
                }
                leaf local-port {
                  type uint16 {
                    tailf:info
                      "<1-65535>;;Local UDP/TCP port";
                    range "1..65535";
                  }
                }
                leaf vrf {
                  tailf:info
                    "Specify vrf";
                  tailf:cli-expose-key-name;
                  tailf:cli-diff-dependency "../../../../../../vrf" {
                    tailf:xpath-root 3;
                  }
                  tailf:cli-diff-dependency "../../../../../../../vrf/definition" {
                    tailf:xpath-root 3;
                  }
                  type string {
                    tailf:info
                      "WORD;;vrf name";
                  }
                }
                uses ip-nat-source-static-grouping;
              }
            }
          }
        }
      }
      container route {
        tailf:info
          "Establish static routes";
        container static {
          tailf:info
            "Allow static routes";
          leaf adjust-time {
            tailf:info
              "Time period for adjusting static routes";
            tailf:cli-full-command;
            type uint8 {
              tailf:info
                "<1-60>;;Adjustment time in seconds";
              range "1..60";
            }
          }
          leaf inter-vrf {
            tailf:info
              "Across VRF interfaces";
            tailf:cli-boolean-no;
            tailf:cli-full-command;
            type boolean;
            default "true";
          }
          container bfd {
            tailf:info
              "BFD tracked";
            list ip-route-bfd-forwarding-list {
              tailf:cli-drop-node-name;
              tailf:cli-suppress-mode;
              tailf:cli-delete-when-empty;
              tailf:cli-compact-syntax;
              key "interface ip-address";
              leaf interface {
                tailf:cli-diff-dependency "../../../../../../interface" {
                  tailf:xpath-root 3;
                }
                type string {
                  tailf:info
                    "WORD;;Interface name";
                }
              }
              leaf ip-address {
                type union {
                  type inet:ipv4-address {
                    tailf:info
                      "A.B.C.D;;Gateway IP address";
                  }
                  type enumeration {
                    enum "multicast" {
                      tailf:info
                        "multicast route";
                    }
                  }
                }
              }
              leaf group {
                tailf:info
                  "assign a bfd group";
                type string {
                  tailf:info
                    "WORD;;bfd group name";
                }
              }
            }
          }
          leaf install-routes-recurse-via-nexthop {
            tailf:info
              "installing recursive route next hop";
            type empty;
          }
          container install-routes-recurse-via-nexthop-vrf {
            tailf:cli-drop-node-name;
            container install-routes-recurse-via-nexthop {
              tailf:info
                "installing recursive route next hop";
              tailf:cli-incomplete-no;
              tailf:cli-incomplete-command;
              list vrf {
                tailf:info
                  "Configure static route for a VPN Routing/Forwarding instance";
                tailf:cli-suppress-mode;
                tailf:cli-delete-when-empty;
                key "name";
                leaf name {
                  tailf:cli-diff-dependency "../../../../../../vrf" {
                    tailf:xpath-root 3;
                  }
                  tailf:cli-diff-dependency "../../../../../../../vrf/definition" {
                    tailf:xpath-root 3;
                  }
                  type string {
                    tailf:info
                      "WORD;;VPN Routing/Forwarding instance name";
                  }
                }
              }
            }
          }
        }
        leaf profile {
          tailf:info
            "Enable IP routing table profile";
          tailf:cli-full-command;
          type empty;
        }
        uses ip-route-grouping {
          refine "ip-route-interface-forwarding-list/interface" {
            tailf:cli-diff-dependency "../../../../interface" {
              tailf:xpath-root 3;
            }
          }
          refine "ip-route-interface-list/interface" {
            tailf:cli-diff-dependency "../../../../interface" {
              tailf:xpath-root 3;
            }
          }
        }
        list vrf {
          tailf:info
            "Configure static route for a VPN Routing/Forwarding instance";
          tailf:cli-suppress-mode;
          tailf:cli-delete-when-empty;
          tailf:cli-compact-syntax;
          tailf:cli-reset-container;
          tailf:cli-incomplete-command;
          tailf:cli-diff-dependency "/ios:interface" {
            tailf:xpath-root 3;
          }
          key "name";
          leaf name {
            tailf:cli-diff-dependency "../../../vrf" {
              tailf:xpath-root 3;
            }
            tailf:cli-diff-dependency "../../../../vrf/definition" {
              tailf:xpath-root 3;
            }
            type string {
              tailf:info
                "WORD;;VPN Routing/Forwarding instance name";
            }
          }
          uses ip-route-grouping {
            refine "ip-route-interface-forwarding-list/interface" {
              tailf:cli-diff-dependency "../../../../../interface" {
                tailf:xpath-root 3;
              }
            }
            refine "ip-route-interface-list/interface" {
              tailf:cli-diff-dependency "../../../../../interface" {
                tailf:xpath-root 3;
              }
            }
          }
        }
      }
      container explicit-path {
        tailf:info
          "Configure explicit-path";
        list identifier {
          tailf:info
            "Specify explicit path by number";
          tailf:cli-mode-name "cfg-ip-expl-path";
          key "number";
          leaf number {
            tailf:cli-suppress-range;
            type uint16 {
              tailf:info
                "<1-65535>;;Enter number";
              range "1..65535";
            }
          }
          leaf mode {
            tailf:cli-drop-node-name;
            tailf:cli-hide-in-submode;
            type enumeration {
              enum "enable" {
                tailf:info
                  "enable the explicit path";
              }
              enum "disable" {
                tailf:info
                  "disable the explicit path";
              }
            }
          }
          uses ip-explicit-path-grouping;
        }
        list name {
          tailf:info
            "Specify explicit path by name";
          tailf:cli-mode-name "cfg-ip-expl-path";
          key "name";
          leaf name {
            tailf:cli-suppress-range;
            type string {
              tailf:info
                "WORD;;Enter name";
            }
          }
          leaf mode {
            tailf:cli-drop-node-name;
            tailf:cli-hide-in-submode;
            type enumeration {
              enum "enable" {
                tailf:info
                  "enable the explicit path";
              }
              enum "disable" {
                tailf:info
                  "disable the explicit path";
              }
            }
          }
          uses ip-explicit-path-grouping;
        }
      }
      container tacacs {
        tailf:info
          "TACACS configuration commands";
        container source-interface {
          tailf:info
            "Specify interface for source address in TACACS packets";
          uses interface-name-grouping;
        }
      }
      container access-list {
        tailf:info
          "Named access list";
        tailf:cli-compact-syntax;
        tailf:cli-incomplete-command;
        tailf:cli-diff-dependency "../../object-group" {
          tailf:xpath-root 3;
        }
        container logging {
          tailf:info
            "Control access list logging";
          leaf interval {
            tailf:info
              "Set access list logging interval";
            type uint32 {
              tailf:info
                "<0-2147483647>;;Access list logging interval (milliseconds)";
              range "0..2147483647";
            }
          }
          leaf hash-generation {
            tailf:info
              "Enable syslog hash code generation";
            type empty;
          }
        }
        leaf persistent {
          tailf:info
            "enable persistency across reload";
          tailf:cli-full-command;
          type empty;
        }
        container standard {
          when "not(../../../tailfned/api/new-ip-access-list)" {
            tailf:xpath-root 3;
            tailf:dependency "../../../tailfned/api/new-ip-access-list";
          }
          tailf:info
            "Standard Access List";
          tailf:cli-incomplete-command;
          list std-named-acl {
            tailf:cli-drop-node-name;
            tailf:cli-full-command;
            tailf:cli-no-key-completion;
            tailf:cli-mode-name "config-std-nacl";
            key "name";
            leaf name {
              type std-ip-acl-type;
            }
            list std-access-list-rule {
              tailf:cli-suppress-mode;
              tailf:cli-delete-when-empty;
              tailf:cli-drop-node-name;
              tailf:cli-compact-syntax;
              tailf:cli-show-long-obu-diffs;
              ordered-by user;
              key "rule";
              leaf rule {
                tailf:cli-multi-word-key;
                tailf:cli-diff-dependency "../../../../../../object-group" {
                  tailf:xpath-root 3;
                }
                type string {
                  tailf:info
                    "deny;;Specify packets to reject
                     permit;;Specify packets to forwards
                     remark;;Access list entry comment";
                  pattern '(permit .*)|(deny .*)|(remark .*)|([0-9]+.*)|(dynamic .*)|(evaluate .*)';
                }
              }
            }
          }
        }
        container extended {
          when "not(../../../tailfned/api/new-ip-access-list)" {
            tailf:xpath-root 3;
            tailf:dependency "../../../tailfned/api/new-ip-access-list";
          }
          tailf:info
            "Extended Access List";
          tailf:cli-incomplete-command;
          list ext-named-acl {
            tailf:cli-drop-node-name;
            tailf:cli-mode-name "config-ext-nacl";
            tailf:cli-full-command;
            tailf:cli-explicit-exit;
            key "name";
            leaf name {
              type ext-acl-type;
            }
            list ext-access-list-rule {
              tailf:cli-suppress-mode;
              tailf:cli-delete-when-empty;
              tailf:cli-drop-node-name;
              tailf:cli-compact-syntax;
              tailf:cli-show-long-obu-diffs;
              ordered-by user;
              key "rule";
              leaf rule {
                tailf:cli-multi-word-key;
                tailf:cli-diff-dependency "../../../../../../object-group" {
                  tailf:xpath-root 3;
                }
                type string {
                  tailf:info
                    "deny;;Specify packets to reject
                     permit;;Specify packets to forwards
                     remark;;Access list entry comment";
                  pattern '(permit .*)|(deny .*)|(remark .*)|([0-9]+.*)|(dynamic .*)|(evaluate .*)';
                }
              }
            }
          }
        }
        list filter-list {
          when "../../../tailfned/api/new-ip-access-list" {
            tailf:xpath-root 3;
            tailf:dependency "../../../tailfned/api/new-ip-access-list";
          }
          tailf:cli-drop-node-name;
          tailf:cli-mode-name "config-nacl";
          tailf:cli-no-key-completion;
          tailf:cli-compact-syntax;
          tailf:cli-sequence-commands;
          tailf:cli-full-command;
          tailf:cli-diff-dependency "../persistent" {
            tailf:xpath-root 3;
          }
          key "name";
          leaf name {
            tailf:cli-suppress-range;
            type string {
              tailf:info
                "WORD;;Access-list name or number";
            }
          }
          leaf type {
            tailf:cli-drop-node-name;
            tailf:cli-prefix-key;
            type enumeration {
              enum "standard" {
                tailf:info
                  "Standard Access List";
              }
              enum "extended" {
                tailf:info
                  "Extended Access List";
              }
            }
          }
          list entry-list {
            tailf:cli-drop-node-name;
            tailf:cli-suppress-mode;
            tailf:cli-delete-when-empty;
            tailf:cli-remove-before-change;
            tailf:cli-incomplete-command;
            key "seq";
            leaf seq {
              tailf:cli-suppress-range;
              type uint32 {
                tailf:info
                  "<1-2147483647>;;Sequence Number";
                range "1..2147483647";
              }
            }
            leaf entry {
              tailf:cli-drop-node-name;
              tailf:cli-multi-value;
              tailf:cli-diff-dependency "../../../../../object-group" {
                tailf:xpath-root 3;
              }
              type string {
                tailf:info
                  "WORD;;deny | permit | remark | dynamic | evaluate ACL entry";
                pattern '(permit .*)|(deny .*)|(remark .*)|(dynamic .*)|(evaluate .*)';
              }
            }
          }
        }
      }
      container prefix-list {
        tailf:info
          "Build a prefix list";
        leaf sequence-number {
          tailf:info
            "Include/exclude sequence numbers in NVGEN";
          tailf:cli-boolean-no;
          tailf:cli-full-command;
          type boolean;
          default "true";
        }
        list prefixes {
          when "not(../sequence-number) or (../sequence-number = 'true')" {
            tailf:xpath-root 3;
            tailf:dependency "../sequence-number";
          }
          tailf:cli-drop-node-name;
          tailf:cli-suppress-mode;
          tailf:cli-delete-when-empty;
          tailf:cli-compact-syntax;
          tailf:cli-diff-dependency "../sequence-number" {
            tailf:xpath-root 3;
          }
          key "name";
          leaf name {
            tailf:cli-disallow-value "sequence-number";
            type string {
              tailf:info
                "WORD;;Name of a prefix list";
            }
          }
          leaf description {
            tailf:info
              "Prefix-list specific description";
            tailf:cli-multi-value;
            tailf:cli-preformatted;
            tailf:cli-full-command;
            type string {
              tailf:info
                "LINE;;Up to 80 characters describing this prefix-list";
              length "1..80";
            }
          }
          list seq {
            tailf:info
              "sequence number of an entry";
            tailf:cli-suppress-mode;
            tailf:cli-delete-when-empty;
            tailf:cli-compact-syntax;
            tailf:cli-remove-before-change;
            key "no";
            leaf no {
              type uint32 {
                tailf:info
                  "<1-4294967294>;;Sequence number";
                range "1..4294967294";
              }
            }
            container deny {
              tailf:info
                "Specify packets to reject";
              tailf:cli-compact-syntax;
              tailf:cli-sequence-commands {
                tailf:cli-reset-all-siblings;
              }
              leaf ip {
                tailf:cli-drop-node-name;
                type ios:ipv4-prefix {
                  tailf:info
                    "A.B.C.D;;IP prefix <network>/<length>, e.g., 35.0.0.0/8";
                }
              }
              leaf ge {
                tailf:info
                  "Minimum prefix length to be matched";
                tailf:cli-break-sequence-commands;
                type uint8 {
                  tailf:info
                    "<1-32>;;Minimum prefix length";
                  range "1..32";
                }
              }
              leaf le {
                tailf:info
                  "Maximum prefix length to be matched";
                tailf:cli-full-command;
                type uint8 {
                  tailf:info
                    "<1-32>;;Maximum prefix length";
                  range "1..32";
                }
              }
            }
            container permit {
              tailf:info
                "Specify packets to forward";
              tailf:cli-compact-syntax;
              tailf:cli-sequence-commands {
                tailf:cli-reset-all-siblings;
              }
              leaf ip {
                tailf:cli-drop-node-name;
                tailf:cli-remove-before-change;
                type ios:ipv4-prefix {
                  tailf:info
                    "A.B.C.D;;IP prefix <network>/<length>, e.g., 35.0.0.0/8";
                }
              }
              leaf ge {
                tailf:info
                  "Minimum prefix length to be matched";
                tailf:cli-break-sequence-commands;
                type uint8 {
                  tailf:info
                    "<1-32>;;Minimum prefix length";
                  range "1..32";
                }
              }
              leaf le {
                tailf:info
                  "Maximum prefix length to be matched";
                tailf:cli-full-command;
                type uint8 {
                  tailf:info
                    "<1-32>;;Maximum prefix length";
                  range "1..32";
                }
              }
            }
          }
        }
        list prefixes-no-seq {
          when "../sequence-number = 'false'" {
            tailf:xpath-root 3;
            tailf:dependency "../sequence-number";
          }
          tailf:cli-drop-node-name;
          tailf:cli-suppress-mode;
          tailf:cli-delete-when-empty;
          tailf:cli-compact-syntax;
          tailf:cli-diff-dependency "../sequence-number" {
            tailf:xpath-root 3;
          }
          key "name";
          leaf name {
            tailf:cli-disallow-value "sequence-number";
            type string {
              tailf:info
                "WORD;;Name of a prefix list";
            }
          }
          leaf description {
            tailf:info
              "Prefix-list specific description";
            tailf:cli-multi-value;
            tailf:cli-preformatted;
            tailf:cli-full-command;
            type string {
              tailf:info
                "LINE;;Up to 80 characters describing this prefix-list";
              length "1..80";
            }
          }
          list entry {
            tailf:cli-drop-node-name;
            tailf:cli-suppress-mode;
            tailf:cli-delete-when-empty;
            tailf:cli-show-long-obu-diffs;
            ordered-by user;
            key "rule";
            leaf rule {
              tailf:cli-multi-word-key;
              type string {
                tailf:info
                  "WORD;;permit <entry> | deny <entry>";
                pattern '(deny .*)|(permit .*)';
              }
            }
          }
        }
      }
      container radius {
        tailf:info
          "RADIUS configuration commands";
        container source-interface {
          tailf:info
            "Specify interface for source address in RADIUS packets";
          uses interface-name-grouping;
        }
        container source-interface-vrf {
          tailf:cli-drop-node-name;
          list source-interface {
            tailf:cli-suppress-mode;
            tailf:cli-delete-when-empty;
            tailf:cli-diff-dependency "../../../../interface" {
              tailf:xpath-root 3;
            }
            key "vrf";
            leaf name {
              tailf:cli-drop-node-name;
              tailf:cli-prefix-key;
              type string {
                tailf:info
                  "WORD;;Interface Name";
              }
            }
            leaf vrf {
              tailf:info
                "VPN Routing/Forwarding parameters";
              tailf:cli-expose-key-name;
              tailf:cli-diff-dependency "../../../../../ip/vrf" {
                tailf:xpath-root 3;
              }
              tailf:cli-diff-dependency "../../../../../vrf/definition" {
                tailf:xpath-root 3;
              }
              type string {
                tailf:info
                  "WORD;;Table name";
              }
            }
          }
        }
      }
      container sla {
        tailf:info
          "IP Service Level Agreement";
        tailf:cli-diff-dependency "../../ethernet/evc" {
          tailf:xpath-root 3;
        }
        tailf:cli-diff-dependency "../../ethernet/cfm/domain" {
          tailf:xpath-root 3;
        }
        container auto {
          tailf:info
            "IP SLAs Auto Configuration";
          leaf discovery {
            tailf:info
              "Enable auto-discovery";
            type empty;
          }
        }
        container responder-twamp {
          tailf:cli-drop-node-name;
          container responder {
            tailf:info
              "Enable IP SLAs Responder";
            container twamp {
              tailf:info
                "Setup TWAMP responder";
              tailf:cli-add-mode;
              tailf:cli-mode-name "config-twamp-ref";
              presence "true";
              leaf timeout {
                tailf:info
                  "Inactivity timeout period";
                type uint32 {
                  tailf:info
                    "<1-604800>;;Inactivity timeout value in seconds";
                  range "1..604800";
                }
              }
            }
          }
        }
        container responder {
          tailf:info
            "Enable IP SLAs Responder";
          presence "true";
        }
        container responder-udp-echo {
          tailf:cli-drop-node-name;
          container responder {
            tailf:info
              "Enable IP SLAs Responder";
            container udp-echo {
              tailf:info
                "Setup udp-echo responder";
              tailf:cli-compact-syntax;
              leaf ipaddress {
                tailf:info
                  "Permanent address";
                type inet:host {
                  tailf:info
                    "WORD;;IP Address or IP HostName";
                }
              }
              leaf port {
                tailf:info
                  "Permanent port";
                type uint16 {
                  tailf:info
                    "<1-65535>;;Port Number (Recommended ports greater than 1023)";
                  range "1..65535";
                }
              }
            }
          }
        }
        container server {
          tailf:info
            "IPPM server configuration";
          container twamp {
            tailf:info
              "IPPM TWAMP server configuration";
            tailf:cli-add-mode;
            tailf:cli-mode-name "config-twamp-srvr";
            presence "true";
            leaf port {
              tailf:info
                "Port on which to listen";
              type uint16 {
                tailf:info
                  "<1-65535>;;Max port value";
                range "1..65535";
              }
              default "862";
            }
            container timer {
              tailf:info
                "Timer configurations";
              leaf inactivity {
                tailf:info
                  "Inactivity timer";
                type uint16 {
                  tailf:info
                    "<1-6000>;;Max number of inactive seconds";
                  range "1..6000";
                }
              }
            }
          }
        }
        container logging {
          tailf:info
            "Enable Syslog";
          leaf traps {
            tailf:info
              "Enable syslog traps";
            type empty;
          }
        }
        leaf key-chain {
          tailf:info
            "Use MD5 Authentication for IP SLAs Control Messages";
          tailf:cli-full-command;
          type string {
            tailf:info
              "WORD;;Name of key-chain";
          }
        }
        list ip-sla-list {
          tailf:cli-drop-node-name;
          tailf:cli-mode-name "config-ip-sla";
          tailf:cli-full-command;
          tailf:cli-diff-dependency "../../../ip/vrf" {
            tailf:xpath-root 3;
          }
          tailf:cli-diff-dependency "../../../vrf/definition" {
            tailf:xpath-root 3;
          }
          key "id";
          leaf id {
            type uint32 {
              tailf:info
                "<1-2147483647>;;Entry Number";
              range "1..2147483647";
            }
          }
          list tcp-connect {
            tailf:info
              "TCP Connect Operation";
            tailf:cli-suppress-mode;
            tailf:cli-delete-when-empty;
            tailf:cli-compact-syntax;
            key "destination destination-port";
            leaf destination {
              type inet:host {
                tailf:info
                  "Hostname or A.B.C.D;;Destination IP address or hostname, broadcast disallowed";
              }
            }
            leaf destination-port {
              type uint16 {
                tailf:info
                  "<0-65535>;;Port Number (Recommended ports greater than 1023)";
              }
            }
            leaf source-ip {
              tailf:info
                "Source address";
              type inet:host {
                tailf:info
                  "WORD;;Hostname or X:X:X:X::X or A.B.C.D address";
              }
            }
            leaf source-port {
              tailf:info
                "Source Port";
              type uint16 {
                tailf:info
                  "<1-65535>;;Port Number";
                range "1..65535";
              }
            }
            leaf control {
              tailf:info
                "Enable or disable control packets";
              type enumeration {
                enum "disable" {
                  tailf:info
                    "Disable control packets exchange";
                }
                enum "enable" {
                  tailf:info
                    "Enable control packets exchange (default)";
                }
              }
              default "enable";
            }
          }
          list udp-jitter {
            tailf:info
              "UDP Jitter Operation";
            tailf:cli-suppress-mode;
            tailf:cli-delete-when-empty;
            tailf:cli-compact-syntax;
            key "destination destination-port";
            leaf destination {
              type inet:host {
                tailf:info
                  "WORD;;Hostname or X:X:X:X::X or A.B.C.D address";
              }
            }
            leaf destination-port {
              type uint16 {
                tailf:info
                  "<0-65535>;;Port Number.";
              }
            }
            leaf source-ip {
              tailf:info
                "Source address";
              type inet:host {
                tailf:info
                  "WORD;;Hostname or X:X:X:X::X or A.B.C.D address";
              }
            }
            leaf source-port {
              tailf:info
                "Source Port";
              type uint16 {
                tailf:info
                  "<1-65535>;;Port Number";
                range "1..65535";
              }
            }
            leaf num-packets {
              tailf:info
                "Number of Packets to be transmitted";
              type uint16 {
                tailf:info
                  "<1-60000>;;Number of Packets (default 10)";
                range "1..60000";
              }
              default "10";
            }
            leaf codec {
              tailf:info
                "codec type to be configured";
              type enumeration {
                enum "g711alaw" {
                  tailf:info
                    "G.711 A Law 64000 bps";
                }
                enum "g711ulaw" {
                  tailf:info
                    "G.711 U Law 64000 bps";
                }
                enum "g729a" {
                  tailf:info
                    "G.729 8000 bps";
                }
              }
            }
            leaf codec-numpackets {
              tailf:info
                "Number of Packets to be transmitted";
              when "../codec" {
                tailf:xpath-root 3;
                tailf:dependency "../codec";
              }
              type uint32 {
                tailf:info
                  "<1-60000>;;Number of Packets";
                range "1..60000";
              }
            }
            leaf interval {
              tailf:info
                "Inter Packet Interval";
              type uint32 {
                tailf:info
                  "<4-60000>;;Delay (default 20)";
              }
              default "20";
            }
            leaf control {
              tailf:info
                "Enable or disable control packets";
              type enumeration {
                enum "disable" {
                  tailf:info
                    "Disable control packets exchange";
                }
                enum "enable" {
                  tailf:info
                    "Enable control packets exchange (default)";
                }
              }
              default "enable";
            }
          }
          list icmp-echo {
            tailf:info
              "ICMP Echo Operation";
            tailf:cli-suppress-mode;
            tailf:cli-delete-when-empty;
            tailf:cli-compact-syntax;
            key "host";
            leaf host {
              type inet:host {
                tailf:info
                  "Hostname or A.B.C.D  Destination IP address or hostname, broadcast disallowed";
              }
            }
            choice source-choice {
              container source-interface {
                tailf:info
                  "Source Interface (ingress icmp packet interface)";
                tailf:cli-flatten-container;
                uses interface-name-grouping;
              }
              leaf source-ip {
                tailf:info
                  "Source Address";
                type inet:host {
                  tailf:info
                    "Hostname or A.B.C.D;;IP address or hostname, broadcast disallowed";
                }
              }
            }
          }
          list udp-echo {
            tailf:info
              "UDP Echo Operation";
            tailf:cli-suppress-mode;
            tailf:cli-delete-when-empty;
            tailf:cli-compact-syntax;
            key "host port";
            leaf host {
              type inet:host {
                tailf:info
                  "Hostname or A.B.C.D;;Destination IP address or hostname, broadcast disallowed";
              }
            }
            leaf port {
              type uint16 {
                tailf:info
                  "<0-65535>;;Port Number";
              }
            }
            leaf control {
              tailf:info
                "Enable or disable control packets";
              type enumeration {
                enum "disable" {
                  tailf:info
                    "Disable control packets exchange";
                }
                enum "enable" {
                  tailf:info
                    "Enable control packets exchange (default)";
                }
              }
            }
            leaf source-ip {
              tailf:info
                "Source Address";
              type inet:host {
                tailf:info
                  "Hostname or A.B.C.D;;IP address or hostname, broadcast disallowed";
              }
            }
            leaf source-port {
              tailf:info
                "source-port;;Source Port";
              type uint16 {
                tailf:info
                  "<1-65535>;;Port Number";
                range "1..65535";
              }
            }
          }
          container ethernet {
            tailf:info
              "Ethernet Operations";
            list ethernet-list {
              tailf:cli-drop-node-name;
              tailf:cli-suppress-mode;
              tailf:cli-delete-when-empty;
              tailf:cli-incomplete-command;
              key "type mpid domain";
              leaf type {
                type enumeration {
                  enum "jitter" {
                    tailf:info
                      "Ethernet Jitter Operation";
                  }
                  enum "echo" {
                    tailf:info
                      "Ethernet Echo Operation (802.1ag Loopback)";
                  }
                }
              }
              leaf mpid {
                tailf:info
                  "Maintenance Point ID";
                tailf:cli-expose-key-name;
                type uint16 {
                  tailf:info
                    "<1-8191>;;MPID Value";
                  range "1..8191";
                }
              }
              leaf domain {
                tailf:info
                  "Domain Name";
                tailf:cli-expose-key-name;
                type string {
                  tailf:info
                    "WORD;;Domain Name Value";
                }
              }
              choice vlan-or-port {
                leaf port {
                  tailf:info
                    "DOWN service direction with no vlan association";
                  type empty;
                }
                leaf vlan {
                  tailf:info
                    "VLAN ID";
                  type uint16 {
                    tailf:info
                      "<1-65535>;;VLAN ID";
                    range "1..65535";
                  }
                }
              }
            }
            container y1731 {
              tailf:info
                "Y1731 Ethernet OAM Performance Measurement Operations";
              list delay {
                tailf:info
                  "Y1731 Delay and Delay Variation Operation";
                tailf:cli-suppress-mode;
                tailf:cli-delete-when-empty;
                tailf:cli-compact-syntax;
                tailf:cli-sequence-commands;
                key "name";
                leaf name {
                  type enumeration {
                    enum "1DM" {
                      tailf:info
                        "1DM frames";
                    }
                    enum "DMM" {
                      tailf:info
                        "DMM/DMR frames";
                    }
                    enum "DMMv1" {
                      tailf:info
                        "DMMv1 frames";
                    }
                  }
                }
                leaf burst {
                  tailf:info
                    "enable bursting of delay frames";
                  tailf:cli-optional-in-sequence;
                  type empty;
                }
                leaf domain {
                  tailf:info
                    "Specify Domain name";
                  type string {
                    tailf:info
                      "WORD;;Specify the Ethernet OAM domain";
                  }
                }
                choice evc-or-vlan {
                  leaf evc {
                    tailf:info
                      "Specify the Ethernet Virtual Circuit Identifier";
                    type string {
                      tailf:info
                        "WORD;;Specify the EVC Identifier value";
                    }
                  }
                  leaf vlan {
                    tailf:info
                      "Specify the VLAN";
                    type uint16 {
                      tailf:info
                        "<1-4096>;;Specify Vlan value";
                      range "1..4096";
                    }
                  }
                }
                choice mpid-or-mac {
                  leaf mac-address {
                    tailf:info
                      "Specify the remote mac-address";
                    type string {
                      tailf:info
                        "H.H.H;;Destination mac-address value";
                    }
                  }
                  leaf mpid {
                    tailf:info
                      "Specify the remote MPID";
                    type uint16 {
                      tailf:info
                        "<1-8191>;;Specify MPID value";
                      range "1..8191";
                    }
                  }
                }
                leaf cos {
                  tailf:info
                    "Specify the Class of Service";
                  type uint8 {
                    tailf:info
                      "<0-7>;;Specify CoS value";
                    range "0..7";
                  }
                }
                container source {
                  tailf:info
                    "Specify the local MPID or MAC-Address";
                  tailf:cli-flatten-container;
                  choice mpid-or-mac {
                    leaf mac-address {
                      tailf:info
                        "Specify the remote mac-address";
                      type string {
                        tailf:info
                          "H.H.H;;Destination mac-address value";
                      }
                    }
                    leaf mpid {
                      tailf:info
                        "Specify the remote MPID";
                      type uint16 {
                        tailf:info
                          "<1-8191>;;Specify MPID value";
                        range "1..8191";
                      }
                    }
                  }
                }
              }
              container delay-receive {
                tailf:cli-drop-node-name;
                container delay {
                  tailf:info
                    "Y1731 Delay and Delay Variation Operation";
                  list receive {
                    tailf:info
                      "Receive only operation";
                    tailf:cli-suppress-mode;
                    tailf:cli-delete-when-empty;
                    tailf:cli-compact-syntax;
                    tailf:cli-sequence-commands;
                    key "name";
                    leaf name {
                      type enumeration {
                        enum "1DM" {
                          tailf:info
                            "1DM frames";
                        }
                      }
                    }
                    leaf domain {
                      tailf:info
                        "Specify Domain name";
                      type string {
                        tailf:info
                          "WORD;;Specify the Ethernet OAM domain";
                      }
                    }
                    choice evc-or-vlan {
                      leaf evc {
                        tailf:info
                          "Specify the Ethernet Virtual Circuit Identifier";
                        type string {
                          tailf:info
                            "WORD;;Specify the EVC Identifier value";
                        }
                      }
                      leaf vlan {
                        tailf:info
                          "Specify the VLAN";
                        type uint16 {
                          tailf:info
                            "<1-4096>;;Specify Vlan value";
                          range "1..4096";
                        }
                      }
                    }
                    leaf cos {
                      tailf:info
                        "Specify the Class of Service";
                      type uint8 {
                        tailf:info
                          "<0-7>;;Specify CoS value";
                        range "0..7";
                      }
                    }
                    choice mpid-or-mac {
                      leaf mac-address {
                        tailf:info
                          "Specify the remote mac-address";
                        type string {
                          tailf:info
                            "H.H.H;;Destination mac-address value";
                        }
                      }
                      leaf mpid {
                        tailf:info
                          "Specify the remote MPID";
                        type uint16 {
                          tailf:info
                            "<1-8191>;;Specify MPID value";
                          range "1..8191";
                        }
                      }
                    }
                  }
                }
              }
              list loss {
                tailf:info
                  "Y1731 Loss Operation";
                tailf:cli-suppress-mode;
                tailf:cli-delete-when-empty;
                tailf:cli-compact-syntax;
                tailf:cli-sequence-commands;
                key "name";
                leaf name {
                  type enumeration {
                    enum "LMM" {
                      tailf:info
                        "LMM/LMR frames";
                    }
                    enum "SLM" {
                      tailf:info
                        "SLM/SLR frames";
                    }
                  }
                }
                leaf burst {
                  tailf:info
                    "enable bursting of SLM frames";
                  tailf:cli-optional-in-sequence;
                  type empty;
                }
                leaf domain {
                  tailf:info
                    "Specify Domain name";
                  type string {
                    tailf:info
                      "WORD;;Specify the Ethernet OAM domain";
                  }
                }
                choice evc-or-vlan {
                  leaf evc {
                    tailf:info
                      "Specify the Ethernet Virtual Circuit Identifier";
                    type string {
                      tailf:info
                        "WORD;;Specify the EVC Identifier value";
                    }
                  }
                  leaf vlan {
                    tailf:info
                      "Specify the VLAN";
                    type uint16 {
                      tailf:info
                        "<1-4096>;;Specify Vlan value";
                      range "1..4096";
                    }
                  }
                }
                choice mpid-or-mac {
                  leaf mac-address {
                    tailf:info
                      "Specify the remote mac-address";
                    type string {
                      tailf:info
                        "H.H.H;;Destination mac-address value";
                    }
                  }
                  leaf mpid {
                    tailf:info
                      "Specify the remote MPID";
                    type uint16 {
                      tailf:info
                        "<1-8191>;;Specify MPID value";
                      range "1..8191";
                    }
                  }
                }
                leaf cos {
                  tailf:info
                    "Specify the Class of Service";
                  type uint8 {
                    tailf:info
                      "<0-7>;;Specify CoS value";
                    range "0..7";
                  }
                }
                container source {
                  tailf:info
                    "Specify the local MPID or MAC-Address";
                  tailf:cli-flatten-container;
                  choice mpid-or-mac {
                    leaf mac-address {
                      tailf:info
                        "Specify the remote mac-address";
                      type string {
                        tailf:info
                          "H.H.H;;Destination mac-address value";
                      }
                    }
                    leaf mpid {
                      tailf:info
                        "Specify the remote MPID";
                      type uint16 {
                        tailf:info
                          "<1-8191>;;Specify MPID value";
                        range "1..8191";
                      }
                    }
                  }
                }
              }
            }
          }
          container http {
            tailf:info
              "HTTP Operation";
            leaf get {
              tailf:info
                "HTTP get operation";
              type string {
                tailf:info
                  "WORD;;URL";
              }
            }
          }
          list service-performance {
            tailf:info
              "Service Performance Operation";
            tailf:cli-suppress-mode;
            tailf:cli-delete-when-empty;
            tailf:cli-compact-syntax;
            tailf:cli-sequence-commands;
            tailf:cli-incomplete-command;
            key "type";
            leaf type {
              tailf:info
                "Server Performance identifer";
              tailf:cli-expose-key-name;
              type enumeration {
                enum "ethernet" {
                  tailf:info
                    "Service Performance Ethernet";
                }
                enum "ip" {
                  tailf:info
                    "Service Performance IP";
                }
              }
            }
            leaf dest-mac-addr {
              when "../type = 'ethernet'" {
                tailf:xpath-root 3;
                tailf:dependency "../type";
              }
              tailf:info
                "Specify the remote mac-address";
              type string {
                tailf:info
                  "H.H.H;;Remote mac-address value";
              }
            }
            leaf dest-ip-addr {
              when "../type = 'ip'" {
                tailf:xpath-root 3;
                tailf:dependency "../type";
              }
              tailf:info
                "Specify the target ip";
              type inet:host {
                tailf:info
                  "Hostname or A.B.C.D/X:X:X:X::X;;Destination IPv6/IP address or hostname";
              }
            }
            leaf vrf {
              when "../type = 'ip'" {
                tailf:xpath-root 3;
                tailf:dependency "../type";
              }
              tailf:info
                "Configure an VRF";
              tailf:cli-optional-in-sequence;
              tailf:cli-full-command;
              type uint16 {
                tailf:info
                  "<1-4096>;;VRF Id";
                range "1..4096";
              }
            }
            container interface {
              tailf:info
                "Interface Name";
              tailf:cli-flatten-container;
              tailf:cli-compact-syntax;
              uses interface-name-grouping;
            }
            container service {
              tailf:info
                "Specify the Service Instance";
              tailf:cli-flatten-container;
              tailf:cli-compact-syntax;
              leaf instance {
                tailf:info
                  "Specify the Service Instance";
                type uint16 {
                  tailf:info
                    "<1-4096>;;Service-Instance value";
                  range "1..4096";
                }
              }
            }
            leaf ethernet {
              tailf:info
                "Configure an Ethernet Instance";
              type string {
                tailf:info
                  "WORD;;EVC name";
              }
            }
          }
          uses description-grouping;
          leaf tos {
            tailf:info
              "Type Of Service";
            type uint8 {
              tailf:info
                "<0-255>;;Type of Service Value";
            }
          }
          leaf verify-data {
            tailf:info
              "Verify data";
            type empty;
          }
          leaf data-pattern {
            tailf:info
              "Data Pattern";
            type string {
              tailf:info
                "WORD;;Data Pattern in Hex";
              pattern '[a-fA-F0-9].*';
            }
          }
          leaf vrf {
            tailf:info
              "Configure IP SLAs for a VPN Routing/Forwarding instance";
            type string {
              tailf:info
                "WORD;;VRF name";
            }
          }
          leaf owner {
            tailf:info
              "Owner of Entry";
            tailf:cli-multi-value;
            tailf:cli-full-command;
            type string {
              tailf:info
                "LINE;;Owner String";
            }
          }
          leaf tag {
            tailf:info
              "User defined tag";
            tailf:cli-multi-value;
            tailf:cli-full-command;
            type string {
              tailf:info
                "LINE;;Tag string";
            }
          }
          container frequency {
            tailf:info
              "Frequency of an operation";
            leaf seconds {
              tailf:cli-drop-node-name;
              tailf:cli-diff-dependency "../../timeout" {
                tailf:xpath-root 3;
                tailf:cli-trigger-on-set;
              }
              tailf:cli-diff-dependency "../../threshold" {
                tailf:xpath-root 3;
                tailf:cli-trigger-on-set;
              }
              type uint32 {
                tailf:info
                  "<1-604800>;;Frequency in seconds (default 60)";
                range "1..604800";
              }
              default "60";
            }
            leaf time {
              tailf:info
                "Frequency period";
              type uint32 {
                tailf:info
                  "<20-604800>;;Specify time duration (seconds)";
                range "20..604800";
              }
            }
          }
          leaf timeout {
            tailf:info
              "Timeout of an operation";
            type uint32 {
              tailf:info
                "<0-604800000>;;Timeout in milliseconds";
              range "0..604800000";
            }
          }
          leaf threshold {
            tailf:info
              "Operation threshold in milliseconds";
            type uint16 {
              tailf:info
                "<0-60000>;;Millisecond threshold value";
              range "0..60000";
            }
          }
          container history {
            tailf:info
              "History and Distribution Data";
            leaf hours-of-statistics-kept {
              tailf:info
                "Maximum number of statistics hour groups to capture";
              type uint8 {
                tailf:info
                  "<0-25>;;Hour groups size value (default 2)";
                range "0..25";
              }
              default "2";
            }
            leaf distributions-of-statistics-kept {
              tailf:info
                "Maximum number of statistics distribution buckets to capture";
              type uint8 {
                tailf:info
                  "<1-20>;;Distribution bucket size value (default 1)";
                range "1..20";
              }
              default "1";
            }
            leaf statistics-distribution-interval {
              tailf:info
                "Statistics distribution interval size";
              type uint8 {
                tailf:info
                  "<1-100>;;Distribution interval value (default 20)";
                range "1..100";
              }
              default "20";
            }
            leaf lives-kept {
              tailf:info
                "Maximum number of history lives to collect";
              type uint8 {
                tailf:info
                  "<0-2>;;Life size value (default 0)";
                range "0..2";
              }
              default "0";
            }
            leaf buckets-kept {
              tailf:info
                "Maximum number of history buckets to collect";
              type uint8 {
                tailf:info
                  "<1-60>;;Bucket size value (default 15)";
                range "1..60";
              }
              default "15";
            }
            leaf filter {
              tailf:info
                "Add operation to History when...";
              type enumeration {
                enum "all" {
                  tailf:info
                    "Collect every operation in History";
                }
                enum "failures" {
                  tailf:info
                    "Collect operations that fail in History";
                }
                enum "none" {
                  tailf:info
                    "Shutoff History collection";
                }
                enum "overThreshold" {
                  tailf:info
                    "Collect operations that are over threshold in History";
                }
              }
            }
            container enhanced {
              tailf:info
                "Enable enhanced history collection";
              tailf:cli-compact-syntax;
              tailf:cli-sequence-commands;
              leaf interval {
                tailf:info
                  "Aggregation interval";
                tailf:cli-incomplete-command;
                type uint16 {
                  tailf:info
                    "<1-3600>;;Interval in seconds";
                  range "1..3600";
                }
              }
              leaf buckets {
                tailf:info
                  "Number of buckets to collect data";
                type uint8 {
                  tailf:info
                    "<1-100>;;Number of buckets";
                  range "1..100";
                }
              }
            }
            leaf interval {
              tailf:info
                "Specify number of intervals";
              type uint8 {
                tailf:info
                  "<1-10>;;Number of intervals to store";
                range "1..10";
              }
            }
          }
          container duration {
            tailf:info
              "Service Performance duration configuration";
            leaf time {
              tailf:info
                "Time based duration";
              type uint32 {
                tailf:info
                  "<1-86400>;;Specify time duration in seconds";
                range "1..86400";
              }
            }
          }
          list measurement-type {
            tailf:info
              "Measurement";
            tailf:cli-mode-name "config-sla-service-performance-measurement";
            key "direction";
            leaf direction {
              tailf:cli-expose-key-name;
              tailf:info
                "Measurement direction";
              type enumeration {
                enum "internal" {
                  tailf:info
                    "internal direction";
                }
                enum "external" {
                  tailf:info
                    "external direction";
                }
              }
            }
            leaf delay {
              tailf:info
                "Delay measurement";
              type empty;
            }
            leaf jitter {
              tailf:info
                "Jitter measurement";
              type empty;
            }
            leaf loss {
              tailf:info
                "loss measurement";
              type empty;
            }
            leaf receive {
              tailf:info
                "Received bytes/packets measurement";
              type empty;
            }
            leaf throughput {
              tailf:info
                "Througput measurement";
              type empty;
            }
          }
          container profile {
            tailf:info
              "Service Performance Profile";
            container packet {
              tailf:info
                "Packet Profiles";
              tailf:cli-add-mode;
              tailf:cli-mode-name "config-sla-service-performance-packet";
              leaf inner-cos {
                tailf:info
                  "Inner COS";
                type uint8 {
                  tailf:info
                    "<0-7>;;COS value";
                  range "0..7";
                }
              }
              leaf outer-cos {
                tailf:info
                  "Outer COS";
                type uint8 {
                  tailf:info
                    "<0-7>;;COS value";
                  range "0..7";
                }
              }
              leaf inner-vlan {
                tailf:info
                  "Specify the Inner VLAN";
                type uint16 {
                  tailf:info
                    "<1-4094>;;Specify Vlan value";
                  range "1..4094";
                }
              }
              leaf outer-vlan {
                tailf:info
                  "Specify the Outer VLAN";
                type uint16 {
                  tailf:info
                    "<1-4094>;;Specify Vlan value";
                  range "1..4094";
                }
              }
              leaf source-ip-addr {
                tailf:info
                  "ip address";
                tailf:cli-full-command;
                type inet:host {
                  tailf:info
                    "Hostname or A.B.C.D/X:X:X:X::X;;Source IPv6/IP address or hostname";
                }
              }
              leaf packet-size {
                tailf:info
                  "Packet Size";
                type enumeration {
                  enum "1024" {
                    tailf:info
                      "1024 byte";
                  }
                  enum "128" {
                    tailf:info
                      "128 byte";
                  }
                  enum "1280" {
                    tailf:info
                      "1280 byte";
                  }
                  enum "1518" {
                    tailf:info
                      "1518 byte";
                  }
                  enum "256" {
                    tailf:info
                      "256 byte";
                  }
                  enum "512" {
                    tailf:info
                      "512 byte";
                  }
                  enum "64" {
                    tailf:info
                      "64 byte";
                  }
                  enum "9216" {
                    tailf:info
                      "9216 byte";
                  }
                  enum "imix" {
                    tailf:info
                      "Imix packet size";
                  }
                }
              }
              leaf src-mac-addr {
                tailf:info
                  "The source mac-address";
                type string {
                  tailf:info
                    "H.H.H;;Source mac-address value";
                }
              }
            }
            list traffic {
              tailf:info
                "Service Performance traffic profile";
              tailf:cli-mode-name "config-sla-service-performance-traffic";
              key "direction";
              leaf direction {
                tailf:info
                  "Traffic direction";
                tailf:cli-expose-key-name;
                type enumeration {
                  enum "internal" {
                    tailf:info
                      "internal direction";
                  }
                  enum "external" {
                    tailf:info
                      "external direction";
                  }
                }
              }
              container rate-step {
                tailf:info
                  "Rate Step";
                container kbps {
                  tailf:info
                    "Kilobits per second rate";
                  tailf:cli-compact-syntax;
                  leaf-list step {
                    tailf:cli-drop-node-name;
                    tailf:cli-replace-all;
                    tailf:cli-flat-list-syntax;
                    ordered-by user;
                    type uint32 {
                      tailf:info
                        "<1-1000000>;;Step X (1-10) (Kbps/pps)";
                      range "1..1000000";
                    }
                  }
                }
              }
            }
          }
          leaf cos {
            tailf:info
              "Class Of Service";
            type uint8 {
              tailf:info
                "<0-7>;;Class of Service Value";
              range "0..7";
            }
          }
          leaf request-data-size {
            tailf:info
              "Request data size";
            type uint16 {
              tailf:info
                "<0-1500>;;Padding size (bytes) in payload";
              range "0..1500";
            }
          }
          container aggregate {
            tailf:info
              "Aggregate parameters";
            leaf interval {
              tailf:info
                "Specify interval period";
              type uint16 {
                tailf:info
                  "<1-65535>;;Aggregation period in seconds";
                range "1..65535";
              }
            }
          }
          container availability {
            tailf:info
              "Specify the availability parameters";
            leaf algorithm {
              tailf:info
                "Specify the algorithm to use";
              type enumeration {
                enum "sliding-window" {
                  tailf:info
                    "Use a sliding window";
                }
                enum "static-window" {
                  tailf:info
                    "Use a static window";
                }
              }
            }
          }
        }
        list schedule {
          tailf:info
            "IP SLAs Entry Scheduling";
          tailf:cli-suppress-mode;
          tailf:cli-delete-when-empty;
          tailf:cli-compact-syntax;
          tailf:cli-incomplete-command;
          key "operation-number";
          leaf operation-number {
            type uint32 {
              tailf:info
                "<1-2147483647>;;Entry number";
            }
            tailf:non-strict-leafref {
              path "../../ip-sla-list/id";
            }
          }
          leaf life {
            tailf:info
              "Length of time to execute in seconds";
            type union {
              type enumeration {
                enum "forever" {
                  tailf:info
                    "continue running forever";
                }
              }
              type uint32 {
                tailf:info
                  "<0-2147483647>;;Life seconds";
              }
            }
          }
          container start-time {
            tailf:info
              "When to start this entry";
            tailf:cli-flatten-container;
            tailf:cli-compact-syntax;
            choice start-time-choice {
              leaf after {
                tailf:info
                  "Start after a certain amount of time from now";
                type string {
                  tailf:info
                    "hh:mm:ss;;Start after (hh:mm:ss) has elapsed";
                }
              }
              leaf now {
                tailf:info
                  "Start now";
                type empty;
              }
              leaf pending {
                tailf:info
                  "Start pending";
                type empty;
              }
              leaf time {
                tailf:cli-drop-node-name;
                type string {
                  tailf:info
                    "hh:mm[:ss];;Start time (hh:mm:[ss])";
                }
              }
            }
          }
          leaf ageout {
            tailf:info
              "How long to keep this Entry when inactive";
            type uint32 {
              tailf:info
                "<0-2073600>;;Ageout Seconds";
            }
          }
          leaf recurring {
            tailf:info
              "Probe to be scheduled automatically every day";
            type empty;
          }
        }
        container ethernet-monitor {
          tailf:info
            "IP SLAs Auto Ethernet configuration";
          list ip-sla-ethernet-monitor-list {
            tailf:cli-drop-node-name;
            tailf:cli-mode-name "config-ip-sla-ethernet-monitor";
            tailf:cli-full-command;
            key "id";
            leaf id {
              type uint32 {
                tailf:info
                  "<1-2147483647>;;Entry number";
              }
            }
            list type {
              tailf:info
                "Type of entry";
              tailf:cli-mode-name "config-ip-sla-ethernet-params";
              key "type domain vlan";
              leaf type {
                type enumeration {
                  enum "echo" {
                    tailf:info
                      "Perform Ethernet Echo operation";
                  }
                  enum "jitter" {
                    tailf:info
                      "Perform Ethernet Jitter operation";
                  }
                }
              }
              leaf domain {
                tailf:info
                  "Domain Name";
                tailf:cli-expose-key-name;
                type string {
                  tailf:info
                    "WORD;;Domain Name Value";
                }
              }
              leaf vlan {
                tailf:info
                  "VLAN ID";
                tailf:cli-expose-key-name;
                type uint16 {
                  tailf:info
                    "<1-4095>;;VLAN ID";
                  range "1..4095";
                }
              }
              leaf cos {
                tailf:info
                  "Class of Service";
                type uint8 {
                  tailf:info
                    "<0-7>;;Class of Service Value";
                  range "0..7";
                }
              }
              leaf request-data-size {
                tailf:info
                  "Request data size";
                type uint16 {
                  tailf:info
                    "<0-1400>;;Padding size (bytes) in payload";
                  range "0..1400";
                }
              }
            }
          }
          list schedule {
            tailf:info
              "IP SLAs Auto ethernet Scheduling";
            tailf:cli-delete-when-empty;
            tailf:cli-suppress-mode;
            tailf:cli-compact-syntax;
            tailf:cli-incomplete-command;
            key "operation-number";
            leaf operation-number {
              type uint32 {
                tailf:info
                  "<1-2147483647>;;Entry number";
              }
              tailf:non-strict-leafref {
                path "../../ip-sla-ethernet-monitor-list/id";
              }
            }
            leaf schedule-period {
              tailf:info
                "Group schedule period range";
              type uint32 {
                tailf:info
                  "<1-604800>;;seconds";
              }
            }
            container start-time {
              tailf:info
                "When to start this entry";
              tailf:cli-flatten-container;
              tailf:cli-compact-syntax;
              choice start-time-choice {
                leaf after {
                  tailf:info
                    "Start after a certain amount of time from now";
                  type string {
                    tailf:info
                      "hh:mm:ss;;Start after (hh:mm:ss) has elapsed";
                  }
                }
                leaf now {
                  tailf:info
                    "Start now";
                  type empty;
                }
                leaf pending {
                  tailf:info
                    "Start pending";
                  type empty;
                }
                leaf time {
                  tailf:cli-drop-node-name;
                  type string {
                    tailf:info
                      "hh:mm[:ss];;Start time (hh:mm:[ss])";
                  }
                }
              }
            }
          }
          list reaction-configuration {
            tailf:info
              "IP SLAs Ethernet CFM Reaction Configuration";
            tailf:cli-suppress-mode;
            tailf:cli-delete-when-empty;
            tailf:cli-compact-syntax;
            tailf:cli-sequence-commands {
              tailf:cli-reset-all-siblings;
            }
            tailf:cli-incomplete-command;
            key "operation-number";
            leaf operation-number {
              type uint32 {
                tailf:info
                  "<1-2147483647>;;Entry number";
              }
              tailf:non-strict-leafref {
                path "../../ip-sla-ethernet-monitor-list/id";
              }
            }
            container react {
              tailf:info
                "Reaction variable to be configured";
              container rtt {
                tailf:info
                  "Round Trip Time";
                presence "true";
              }
              container timeout {
                tailf:info
                  "timeout";
                presence "true";
              }
            }
          }
        }
        list reaction-configuration {
          tailf:info
            "IP SLAs Reaction-Configuration";
          tailf:cli-suppress-mode;
          tailf:cli-delete-when-empty;
          tailf:cli-compact-syntax;
          tailf:cli-sequence-commands {
            tailf:cli-reset-all-siblings;
          }
          key "operation-number react";
          leaf operation-number {
            type uint32 {
              tailf:info
                "<1-2147483647>;;Entry number";
            }
            tailf:non-strict-leafref {
              path "../../ip-sla-list/id";
            }
          }
          leaf react {
            tailf:info
              "Reaction variable to be configured";
            tailf:cli-expose-key-name;
            type string {
              tailf:info
                "monitored-element";
            }
          }
          container threshold-value {
            tailf:cli-break-sequence-commands;
            tailf:info
              "Threshold value";
            tailf:cli-flatten-container;
            tailf:cli-compact-syntax;
            tailf:cli-sequence-commands;
            leaf upper-threshold {
              tailf:cli-drop-node-name;
              type uint16 {
                tailf:info
                  "<1-60000>;;Upper limit for Threshold";
              }
            }
            leaf lower-threshold {
              tailf:cli-drop-node-name;
              type uint16 {
                tailf:info
                  "<1-60000>;;Lower limit for Threshold";
              }
            }
          }
          container threshold-type {
            tailf:info
              "Threshold Type";
            tailf:cli-flatten-container;
            tailf:cli-compact-syntax;
            tailf:cli-sequence-commands {
              tailf:cli-reset-siblings;
            }
            choice threshold-type-choice {
              case average {
                leaf average {
                  tailf:info
                    "Average over N attempts";
                  type empty;
                }
                leaf n {
                  tailf:cli-drop-node-name;
                  type uint8 {
                    tailf:info
                      "<1-16>;;N Value";
                    range "1..16";
                  }
                }
              }
              case consecutive {
                leaf consecutive {
                  tailf:info
                    "Consecutive occurrences";
                  type empty;
                }
                leaf number {
                  tailf:cli-drop-node-name;
                  type uint8 {
                    tailf:info
                      "<1-16>;;Number of occurrences";
                    range "1..16";
                  }
                }
              }
              leaf immediate {
                tailf:info
                  "React immediately";
                type empty;
              }
              leaf never {
                tailf:info
                  "Never react";
                type empty;
              }
              container xOfy {
                tailf:info
                  "X out of Y occurrences";
                tailf:cli-flatten-container;
                tailf:cli-compact-syntax;
                tailf:cli-sequence-commands;
                leaf x {
                  tailf:cli-drop-node-name;
                  tailf:cli-incomplete-command;
                  type uint8 {
                    tailf:info
                      "<1-16>;;X Value";
                    range "1..16";
                  }
                }
                leaf y {
                  tailf:cli-drop-node-name;
                  type uint8 {
                    tailf:info
                      "<1-16>;;Y Value";
                    range "1..16";
                  }
                }
              }
            }
          }
          leaf action-type {
            tailf:info
              "IP SLAs Reaction Action Type";
            type enumeration {
              enum "none" {
                tailf:info
                  "No action";
              }
              enum "trapAndTrigger" {
                tailf:info
                  "Trap and Trigger action";
              }
              enum "trapOnly" {
                tailf:info
                  "Trap Only action";
              }
              enum "triggerOnly" {
                tailf:info
                  "Trigger Only action";
              }
            }
          }
        }
        list reaction-trigger {
          tailf:info
            "IP SLAs Trigger Assignment";
          tailf:cli-suppress-mode;
          tailf:cli-delete-when-empty;
          tailf:cli-incomplete-command;
          key "operation-number";
          leaf operation-number {
            type uint32 {
              tailf:info
                "<1-2147483647>;;Entry number";
            }
            tailf:non-strict-leafref {
              path "../../ip-sla-list/id";
            }
          }
          leaf target-operation {
            tailf:cli-drop-node-name;
            type uint32 {
              tailf:info
                "<1-2147483647>;;Target entry num";
            }
          }
        }
        container enable {
          tailf:info
            "Enable Event Notifications";
          leaf timestamp {
            tailf:info
              "Enable timestamping";
            type empty;
          }
          leaf reaction-alerts {
            tailf:info
              "Enable Reaction Alert Notifications";
            type empty;
          }
        }
      }
      container wccp {
        tailf:info
          "Web-Cache Coordination Protocol Commands";
        uses ip-wccp-grouping;
        list vrf {
          tailf:info
            "Configure WCCP for a VRF";
          tailf:cli-suppress-mode;
          tailf:cli-delete-when-empty;
          tailf:cli-compact-syntax;
          tailf:cli-incomplete-command;
          key "name";
          leaf name {
            tailf:cli-diff-dependency "../../../../vrf/definition" {
              tailf:xpath-root 3;
            }
            tailf:cli-diff-dependency "../../../../ip/vrf" {
              tailf:xpath-root 3;
            }
            type string {
              tailf:info
                "WORD;;VRF name";
            }
          }
          uses ip-wccp-grouping;
        }
      }
      container nbar {
        tailf:info
          "NBAR - Network Based Application Recognition";
        list attribute-map {
          tailf:cli-mode-name "config-attribute-map";
          key "name";
          leaf name {
            type string {
              tailf:info
                "WORD: Attribute Profile Name";
            }
          }
          container attribute {
            tailf:info
              "Attribute Name";
            leaf business-relevance {
              tailf:info
                "Application business-relevance";
              type enumeration {
                enum "business-relevant" {
                  tailf:info
                    "Business critical applications";
                }
                enum "business-irrelevant" {
                  tailf:info
                    "Undesirable business traffic";
                }
                enum "default" {
                  tailf:info
                    "Related business applications";
                }
              }
            }
            leaf traffic-class {
              tailf:info
                "SRND class";
              type enumeration {
                enum "transactional-data" {
                  tailf:info
                    "Interactive data applications";
                }
                enum "voip-telephony" {
                  tailf:info
                    "VoIP telephony (bearer-only) traffic";
                }
                enum "signaling" {
                  tailf:info
                    "Signaling traffic that supports IP voice and video telephony";
                }
                enum "real-time-interactive" {
                  tailf:info
                    "High-definition interactive video applications";
                }
                enum "ops-admin-mgmt" {
                  tailf:info
                    "Network operations, administration, and management traffic";
                }
                enum "network-control" {
                  tailf:info
                    "Network control plane traffic";
                }
                enum "multimedia-streaming" {
                  tailf:info
                    "Video-on-Demand (VoD) streaming video";
                }
                enum "multimedia-conferencing" {
                  tailf:info
                    "Desktop software multimedia collaboration applications";
                }
                enum "bulk-data" {
                  tailf:info
                    "Non-interactive data applications";
                }
                enum "broadcast-video" {
                  tailf:info
                    "Broadcast TV, live events, video surveillance";
                }
              }
            }
            leaf application-group {
              tailf:info
                "Application-group attribute";
              type string {
                tailf:info
                  "WORD;;Related applications group";
              }
            }
          }
        }
        list custom {
          tailf:info
            "Custom PDL (protocol description language) Module";
          tailf:cli-suppress-mode;
          tailf:cli-delete-when-empty;
          tailf:cli-incomplete-command;
          key "name";
          leaf name {
            type string {
              tailf:info
                "WORD;;Name of the User defined Protocol";
            }
          }
          container composite {
            tailf:info
              "Custom protocols based on multiple underlying protocols";
            tailf:cli-compact-syntax;
            leaf server-name {
              tailf:info
                "Match the server name based on various protocols";
              type string {
                tailf:info
                  "WORD  Enter String Format - cannot exceed 30 characters";
              }
            }
            leaf id {
              tailf:info
                "Selector ID";
              type uint16 {
                tailf:info
                  "<1-65535>;;Enter Selector ID";
                range "1..65535";
              }
            }
          }
        }
        list attribute-set {
          tailf:info
            "Set attribute-set";
          tailf:cli-suppress-mode;
          tailf:cli-delete-when-empty;
          tailf:cli-incomplete-command;
          key "protocol-name";
          leaf protocol-name {
            type string {
              tailf:info
                "WORD;;Name of protocol";
            }
          }
          leaf profile-name {
            tailf:cli-drop-node-name;
            type string {
              tailf:info
                "Attribute Profile Name";
            }
            tailf:non-strict-leafref {
              path "../../attribute-map/name";
            }
          }
        }
        container protocol-discovery {
          tailf:info
            "Enable protocol discovery for both ipv4 and ipv6";
          presence "true";
        }
      }
      container inspect {
        tailf:info
          "Context-based Access Control Engine";
        list name {
          tailf:info
            "Specify an inspection rule";
          tailf:cli-suppress-mode;
          tailf:cli-delete-when-empty;
          tailf:cli-incomplete-command;
          key "name";
          leaf name {
            type string {
              tailf:info
                "WORD;;Name of inspection defined (16 characters max)";
            }
          }
          list rule {
            tailf:cli-drop-node-name;
            tailf:cli-suppress-mode;
            tailf:cli-delete-when-empty;
            tailf:cli-show-long-obu-diffs;
            ordered-by user;
            key "rule";
            leaf rule {
              tailf:cli-multi-word-key;
              type string {
                tailf:info
                  "WORD;;Rule";
              }
            }
          }
        }
      }
      container spd {
        leaf enable {
          tailf:cli-boolean-no;
          tailf:cli-full-command;
          type boolean;
          default "true";
        }
      }
      container source {
        tailf:info
          "static IP binding";
        list binding {
          tailf:info
            "static IP binding";
          tailf:cli-suppress-mode;
          tailf:cli-delete-when-empty;
          tailf:cli-compact-syntax;
          tailf:cli-sequence-commands {
            tailf:cli-reset-siblings;
          }
          tailf:cli-incomplete-command;
          key "mac-address";
          leaf mac-address {
            tailf:cli-diff-dependency "../../../../interface/Ethernet/switchport" {
              tailf:xpath-root 3;
            }
            tailf:cli-diff-dependency "../../../../interface/FastEthernet/switchport" {
              tailf:xpath-root 3;
            }
            tailf:cli-diff-dependency "../../../../interface/GigabitEthernet/switchport" {
              tailf:xpath-root 3;
            }
            tailf:cli-diff-dependency "../../../../interface/TenGigabitEthernet/switchport" {
              tailf:xpath-root 3;
            }
            tailf:cli-diff-dependency "../../../../interface/FortyGigabitEthernet/switchport" {
              tailf:xpath-root 3;
            }
            tailf:cli-diff-dependency "../../../../interface/HundredGigE/switchport" {
              tailf:xpath-root 3;
            }
            tailf:cli-diff-dependency "../../../../interface/Port-channel/switchport" {
              tailf:xpath-root 3;
            }
            type string {
              tailf:info
                "H.H.H;;binding MAC address";
            }
          }
          leaf vlan {
            tailf:info
              "binding VLAN learned";
            tailf:cli-incomplete-command;
            type uint16 {
              tailf:info
                "<1-4094>;;binding VLAN number";
              range "1..4094";
            }
          }
          leaf ip-address {
            tailf:cli-drop-node-name;
            tailf:cli-incomplete-command;
            type inet:ipv4-address {
              tailf:info
                "A.B.C.D;;binding IP address";
            }
          }
          container interface {
            tailf:info
              "binding interface";
            tailf:cli-flatten-container;
            tailf:cli-compact-syntax;
            uses interface-name-grouping;
          }
        }
      }
    }
    container isdn {
      tailf:ncs-device-type "cli-ned";
      tailf:display-when "not(../../ncs:module) or ../../ncs:module[ncs:name='tailf-ned-cisco-ios']";
      tailf:info
        "ISDN configuration commands";
      leaf switch-type {
        tailf:info
          "Select the ISDN switch type";
        tailf:cli-full-command;
        type string {
          tailf:info
            "WORD;;switch type";
        }
      }
      container leased-line {
        tailf:info
          "Sets a BRI interface to support leased lines on B & D channels";
        leaf BRI {
          tailf:info
            "ISDN Basic Rate Interface";
          tailf:cli-allow-join-with-value {
            tailf:cli-display-joined;
          }
          tailf:non-strict-leafref {
            path "../../../interface/BRI/name";
          }
          type string {
            tailf:info
              "<slot>/<port>;;BRI interface number";
            pattern '[0-9]+.*';
          }
        }
      }
    }
    container vmps {
      tailf:ncs-device-type "cli-ned";
      tailf:display-when "not(../../ncs:module) or ../../ncs:module[ncs:name='tailf-ned-cisco-ios']";
      tailf:info
        "VMPS settings";
      leaf reconfirm {
        tailf:info
          "Set VMPS reconfirm interval";
        type uint8 {
          tailf:info
            "Number of minutes between reconfirmations";
          range "0..120";
        }
      }
      leaf retry {
        tailf:info
          "Set VMPS retry count";
        type uint8 {
          tailf:info
            "<1-10>;;Retry count per server";
          range "1..10";
        }
      }
      list server {
        tailf:info
          "Configure server IP address";
        tailf:cli-suppress-mode;
        tailf:cli-delete-when-empty;
        tailf:cli-compact-syntax;
        key "name";
        leaf name {
          type inet:host {
            tailf:info
              "Hostname or A.B.C.D;;IP address";
          }
        }
        leaf primary {
          tailf:info
            "Specify primary server";
          type empty;
        }
      }
    }
    container ipv6 {
      tailf:ncs-device-type "cli-ned";
      tailf:display-when "not(../../ncs:module) or ../../ncs:module[ncs:name='tailf-ned-cisco-ios']";
      tailf:info
        "Global IPv6 configuration commands";
      leaf unicast-routing {
        tailf:info
          "Enable unicast routing";
        type empty;
      }
      leaf source-route {
        tailf:info
          "Process packets with source routing header options";
        tailf:cli-boolean-no;
        tailf:cli-full-command;
        type boolean;
      }
      leaf cef {
        tailf:info
          "Cisco Express Forwarding";
        tailf:cli-show-no;
        type empty;
      }
      container cef-conf {
        tailf:cli-drop-node-name;
        container cef {
          tailf:info
            "Cisco Express Forwarding";
          tailf:cli-incomplete-no;
          tailf:cli-incomplete-command;
          tailf:cli-diff-dependency "../../cef" {
            tailf:xpath-root 3;
          }
          container accounting {
            tailf:info
              "Enable CEF accounting";
            tailf:cli-compact-syntax;
            leaf per-prefix {
              tailf:info
                "Enable per prefix accounting";
              type empty;
            }
            leaf prefix-length {
              tailf:info
                "Enable prefix length accounting";
              type empty;
            }
          }
          leaf distributed {
            tailf:info
              "Distributed Cisco Express Forwarding";
            tailf:cli-full-command;
            type empty;
          }
          container load-sharing {
            tailf:info
              "Load sharing";
            container algorithm {
              tailf:info
                "Per-destination load sharing algorithm selection";
              choice algorithm-choice {
                leaf original {
                  tailf:info
                    "Original algorithm";
                  type empty;
                }
                container universal {
                  tailf:info
                    "Algorithm for use in most environments";
                  leaf id {
                    tailf:cli-drop-node-name;
                    type string {
                      tailf:info
                        "<1-FFFFFFFF>;;Fixed ID";
                    }
                  }
                }
              }
            }
          }
        }
      }
      leaf flowset {
        tailf:info
          "Set flow label random for originated packets";
        tailf:cli-full-command;
        type empty;
      }
      container icmp {
        tailf:info
          "Configure ICMP parameters";
        container error-interval {
          tailf:info
            "Interval between ICMP error messages";
          tailf:cli-compact-syntax;
          tailf:cli-sequence-commands {
            tailf:cli-reset-siblings;
          }
          leaf milliseconds {
            tailf:cli-drop-node-name;
            type uint32 {
              tailf:info
                "<0-2147483647>;;Interval between tokens in milliseconds";
              range "0..2147483647";
            }
          }
          leaf bucketsize {
            tailf:cli-drop-node-name;
            type uint8 {
              tailf:info
                "<1-200>;;Bucket size";
              range "1..200";
            }
          }
        }
      }
      container wccp {
        tailf:info
          "Web-Cache Coordination Protocol IPv6 Commands";
        uses ip-wccp-grouping;
        list vrf {
          tailf:info
            "Configure WCCP for a VRF";
          tailf:cli-suppress-mode;
          tailf:cli-delete-when-empty;
          tailf:cli-compact-syntax;
          tailf:cli-incomplete-command;
          key "name";
          leaf name {
            tailf:cli-diff-dependency "../../../../vrf/definition" {
              tailf:xpath-root 3;
            }
            type string {
              tailf:info
                "WORD;;VRF name";
            }
          }
          uses ip-wccp-grouping;
        }
      }
      leaf multicast-routing {
        tailf:info
          "Enable IPv6 multicast";
        type empty;
      }
      container multicast {
        tailf:info
          "Configure multicast related commands";
        container rpf {
          tailf:info
            "Configure multicast RPF related commands";
          container backoff {
            tailf:info
              "Backoff delay after unicast routing change";
            tailf:cli-compact-syntax;
            tailf:cli-sequence-commands {
              tailf:cli-reset-siblings;
            }
            leaf initial-delay {
              tailf:cli-drop-node-name;
              type uint16 {
                tailf:info
                  "<200-65535>;;Initial RPF backoff delay in milliseconds";
                range "200..65535";
              }
            }
            leaf max-delay {
              tailf:cli-drop-node-name;
              type uint16 {
                tailf:info
                  "<200-65535>;;Maximum RPF backoff delay in milliseconds";
                range "200..65535";
              }
            }
          }
          leaf use-bgp {
            tailf:info
              "Use BGP routes for multicast RPF lookup";
            type empty;
          }
        }
      }
      container spd {
        tailf:info
          "Selective Packet Discard (SPD)";
        container queue {
          tailf:info
            "SPD queue";
          leaf min-threshold {
            tailf:info
              "SPD minimum threshold";
            type uint16 {
              tailf:info
                "<1-65535>;;spd value";
              range "1..65535";
            }
          }
          leaf max-threshold {
            tailf:info
              "SPD maximum threshold";
            tailf:cli-diff-dependency "../min-threshold" {
              tailf:xpath-root 3;
            }
            type uint16 {
              tailf:info
                "<1-65535>;;spd value";
              range "1..65535";
            }
          }
        }
      }
      container route {
        tailf:info
          "Configure static routes";
        tailf:cli-diff-dependency "../../interface" {
          tailf:xpath-root 3;
        }
        container static {
          tailf:info
            "Configure static route attributes";
          list bfd {
            tailf:info
              "Configure a Static Route BFD neighbor";
            tailf:cli-suppress-mode;
            tailf:cli-delete-when-empty;
            tailf:cli-compact-syntax;
            key "interface ipv6-address";
            leaf interface {
              tailf:cli-diff-dependency "../../../../../interface" {
                tailf:xpath-root 3;
              }
              type string {
                tailf:info
                  "WORD;;Interface name";
              }
            }
            leaf ipv6-address {
              type inet:ipv6-address {
                tailf:info
                  "X:X:X:X::X;;IPv6 address of BFD neighbor";
              }
            }
            leaf unassociated {
              tailf:info
                "Unassociated Neighbor";
              type empty;
            }
          }
        }
        list vrf {
          tailf:info
            "Configure static route for a VPN Routing/Forwarding instance";
          tailf:cli-suppress-mode;
          tailf:cli-delete-when-empty;
          tailf:cli-compact-syntax;
          tailf:cli-incomplete-command;
          key "name";
          leaf name {
            tailf:cli-diff-dependency "../../../../vrf/definition" {
              tailf:xpath-root 3;
            }
            type string {
              tailf:info
                "WORD;;VRF name";
            }
          }
          uses ipv6-route-grouping;
        }
        container no-vrf {
          tailf:cli-drop-node-name;
          uses ipv6-route-grouping;
        }
      }
      container prefix-list {
        tailf:info
          "Build a prefix list";
        leaf sequence-number {
          tailf:info
            "Include/exclude sequence numbers in NVGEN";
          tailf:cli-boolean-no;
          tailf:cli-full-command;
          type boolean;
          default "true";
        }
        list prefixes {
          when "not(../sequence-number) or (../sequence-number = 'true')" {
            tailf:xpath-root 3;
            tailf:dependency "../sequence-number";
          }
          tailf:cli-drop-node-name;
          tailf:cli-suppress-mode;
          tailf:cli-delete-when-empty;
          tailf:cli-compact-syntax;
          tailf:cli-diff-dependency "../sequence-number" {
            tailf:xpath-root 3;
          }
          key "name";
          leaf name {
            tailf:cli-disallow-value "sequence-number";
            type string {
              tailf:info
                "WORD;;Name of a prefix list";
            }
          }
          leaf description {
            tailf:info
              "Prefix-list specific description";
            tailf:cli-multi-value;
            tailf:cli-preformatted;
            tailf:cli-full-command;
            type string {
              tailf:info
                "LINE;;Up to 80 characters describing this prefix-list";
              length "1..80";
            }
          }
          list seq {
            tailf:info
              "sequence number of an entry";
            tailf:cli-suppress-mode;
            tailf:cli-delete-when-empty;
            tailf:cli-compact-syntax;
            tailf:cli-remove-before-change;
            key "no";
            leaf no {
              type uint32 {
                tailf:info
                  "<1-4294967294>;;Sequence number";
                range "1..4294967294";
              }
            }
            container deny {
              tailf:info
                "Specify packets to reject";
              tailf:cli-compact-syntax;
              tailf:cli-sequence-commands {
                tailf:cli-reset-all-siblings;
              }
              leaf ip {
                tailf:cli-drop-node-name;
                type ios:ipv6-prefix {
                  tailf:info
                    "X:X:X:X::X/<0-128>;;IPv6 prefix";
                }
              }
              leaf ge {
                tailf:info
                  "Minimum prefix length to be matched";
                tailf:cli-break-sequence-commands;
                type uint16 {
                  tailf:info
                    "<1-128>;;Minimum prefix length";
                  range "1..128";
                }
              }
              leaf le {
                tailf:info
                  "Maximum prefix length to be matched";
                tailf:cli-full-command;
                type uint16 {
                  tailf:info
                    "<1-128>;;Maximum prefix length";
                  range "1..128";
                }
              }
            }
            container permit {
              tailf:info
                "Specify packets to forward";
              tailf:cli-compact-syntax;
              tailf:cli-sequence-commands {
                tailf:cli-reset-all-siblings;
              }
              leaf ip {
                tailf:cli-drop-node-name;
                tailf:cli-remove-before-change;
                type ios:ipv6-prefix {
                  tailf:info
                    "X:X:X:X::X/<0-128>;;IPv6 prefix";
                }
              }
              leaf ge {
                tailf:info
                  "Minimum prefix length to be matched";
                tailf:cli-break-sequence-commands;
                type uint16 {
                  tailf:info
                    "<1-128>;;Minimum prefix length";
                  range "1..128";
                }
              }
              leaf le {
                tailf:info
                  "Maximum prefix length to be matched";
                tailf:cli-full-command;
                type uint16 {
                  tailf:info
                    "<1-128>;;Maximum prefix length";
                  range "1..128";
                }
              }
            }
          }
        }
        list prefixes-no-seq {
          when "../sequence-number = 'false'" {
            tailf:xpath-root 3;
            tailf:dependency "../sequence-number";
          }
          tailf:cli-drop-node-name;
          tailf:cli-suppress-mode;
          tailf:cli-delete-when-empty;
          tailf:cli-compact-syntax;
          tailf:cli-diff-dependency "../sequence-number" {
            tailf:xpath-root 3;
          }
          key "name";
          leaf name {
            tailf:cli-disallow-value "sequence-number";
            type string {
              tailf:info
                "WORD;;Name of a prefix list";
            }
          }
          leaf description {
            tailf:info
              "Prefix-list specific description";
            tailf:cli-multi-value;
            tailf:cli-preformatted;
            tailf:cli-full-command;
            type string {
              tailf:info
                "LINE;;Up to 80 characters describing this prefix-list";
              length "1..80";
            }
          }
          list entry {
            tailf:cli-drop-node-name;
            tailf:cli-suppress-mode;
            tailf:cli-delete-when-empty;
            tailf:cli-show-long-obu-diffs;
            ordered-by user;
            key "rule";
            leaf rule {
              tailf:cli-multi-word-key;
              type string {
                tailf:info
                  "WORD;;permit <entry> | deny <entry>";
                pattern '(deny .*)|(permit .*)';
              }
            }
          }
        }
      }
      container access-list {
        tailf:info
          "Configure access lists";
        tailf:cli-incomplete-command;
        tailf:cli-compact-syntax;
        list named-acl {
          tailf:cli-drop-node-name;
          tailf:cli-full-command;
          tailf:cli-no-key-completion;
          tailf:cli-mode-name "config-ipv6-acl";
          key "name";
          leaf name {
            type string {
              tailf:info
                "User selected string identifying this access list";
            }
          }
          list access-list-rule {
            tailf:cli-suppress-mode;
            tailf:cli-delete-when-empty;
            tailf:cli-drop-node-name;
            tailf:cli-compact-syntax;
            tailf:cli-show-long-obu-diffs;
            tailf:cli-case-sensitive;
            ordered-by user;
            key "rule";
            leaf rule {
              tailf:cli-drop-node-name;
              tailf:cli-multi-word-key;
              type string {
                tailf:info
                  "deny;;Specify packets to reject
                   permit;;Specify packets to forwards
                   remark;;Access list entry comment
                   sequence;;Sequence number for this entry";
                pattern '(deny .*)|(permit .*)|(remark .*)|(sequence .*)|(evaluate .*)';
              }
            }
          }
        }
      }
      container router {
        tailf:info
          "Enable an IPV6 routing process";
        list rip {
          tailf:info
            "IPv6 Routing Information Protocol (RIPv6)";
          tailf:cli-mode-name "config-rtr";
          key "name";
          leaf name {
            type string {
              tailf:info
                "WORD;;User selected string identifying this process";
            }
          }
          container address-family {
            tailf:info
              "Enter Address Family command mode";
            container ipv6 {
              tailf:info
                "Address family";
              list vrf {
                tailf:cli-mode-name "config-ipv6-rtr-af";
                tailf:cli-exit-command "exit-address-family" {
                  tailf:info
                    "Exit Address Family command mode";
                }
                key "name";
                leaf name {
                  tailf:cli-diff-dependency "../../../../../../../ipv6/rip/vrf-mode/enable" {
                    tailf:xpath-root 3;
                  }
                  tailf:cli-diff-dependency "../../../../../../../vrf/definition" {
                    tailf:xpath-root 3;
                  }
                  type string {
                    tailf:info
                      "WORD;;VPN Routing/Forwarding instance name";
                  }
                }
              }
            }
          }
          container distribute-list {
            tailf:info
              "Filter networks in routing updates";
            list prefix-list {
              tailf:info
                "Filter connections based on an IPv6 prefix-list";
              tailf:cli-suppress-mode;
              tailf:cli-delete-when-empty;
              key "direction";
              leaf direction {
                type enumeration {
                  enum "in" {
                    tailf:info
                      "Filter incoming routing updates";
                  }
                  enum "out" {
                    tailf:info
                      "Filter outgoing routing updates";
                  }
                }
              }
              leaf prefix-list-name {
                tailf:cli-drop-node-name;
                tailf:cli-prefix-key;
                tailf:non-strict-leafref {
                  path "/ncs:devices/ncs:device/ncs:config/ios:ip/prefix-list/prefixes/name" {
                    tailf:xpath-root 3;
                  }
                }
                type string {
                  tailf:info
                    "WORD;;Prefix-list name";
                }
              }
            }
          }
        }
        list eigrp {
          tailf:info
            "Enhanced Interior Gateway Routing Protocol (EIGRP)";
          tailf:cli-mode-name "config-rtr";
          key "as-no";
          leaf as-no {
            type uint16 {
              tailf:info
                "<1-65535>;;Autonomous System";
              range "1..65535";
            }
          }
          container eigrp {
            tailf:info
              "EIGRP specific commands";
            leaf router-id {
              tailf:info
                "router id for this EIGRP process";
              type inet:ipv4-address {
                tailf:info
                  "A.B.C.D;;EIGRP Router-ID in IP address format";
              }
            }
          }
          leaf shutdown {
            tailf:info
              "Shutdown this instance of EIGRP";
            type empty;
          }
        }
        list ospf {
          tailf:info
            "Open Shortest Path First (OSPF)";
          tailf:cli-mode-name "config-rtr";
          key "id";
          leaf id {
            tailf:cli-suppress-range;
            type uint16 {
              tailf:info
                "<1-65535>;;Process ID";
              range "1..65535";
            }
          }
          uses router-ospf-common-grouping;
          uses router-ospf-common-af-grouping;
          uses router-ospf-grouping;
        }
      }
      container neighbor {
        tailf:info
          "Neighbor";
        list neighbor-list {
          tailf:cli-drop-node-name;
          tailf:cli-suppress-mode;
          tailf:cli-delete-when-empty;
          tailf:cli-incomplete-command;
          key "address interface";
          leaf address {
            type inet:ipv6-address {
              tailf:info
                "X:X:X:X::X;;IPv6 address";
            }
          }
          leaf interface {
            tailf:cli-diff-dependency "../../../../interface" {
              tailf:xpath-root 3;
            }
            type string {
              tailf:info
                "WORD;;Interface name";
            }
          }
          leaf hardware-address {
            tailf:cli-drop-node-name;
            type string {
              tailf:info
                "H.H.H;;48-bit hardware address";
            }
          }
        }
      }
      container dhcp {
        tailf:info
          "Configure IPv6 DHCP";
        list pool {
          tailf:info
            "Configure IPv6 DHCP pool";
          tailf:cli-mode-name "config-dhcpv6";
          tailf:cli-full-command;
          key "name";
          leaf name {
            type string {
              tailf:info
                "WORD;;DHCP pool name";
            }
          }
          leaf vrf {
            tailf:info
              "Associate pool with a VRF";
            tailf:cli-full-command;
            type string {
              tailf:info
                "WORD;;VRF name";
            }
          }
          leaf dns-server {
            tailf:info
              "DNS servers";
            tailf:cli-full-command;
            type inet:host {
              tailf:info
                "Hostname or X:X:X:X::X;;Server's name or IPv6 address";
            }
          }
          leaf domain-name {
            tailf:info
              "Domain name to complete unqualified host names";
            tailf:cli-full-command;
            type string {
              tailf:info
                "WORD;;A domain name";
            }
          }
        }
      }
      container rip {
        tailf:info
          "Configure ipv6 RIP settings";
        container vrf-mode {
          tailf:info
            "Enable RIPng VRF support";
          leaf enable {
            tailf:info
              "Enable RIPng VRF support";
            type empty;
          }
        }
      }
    }
    container subscriber {
      tailf:ncs-device-type "cli-ned";
      tailf:display-when "not(../../ncs:module) or ../../ncs:module[ncs:name='tailf-ned-cisco-ios']";
      tailf:info
        "Subscriber configuration";
      leaf templating {
        tailf:info
          "Configure subscriber templating";
        type empty;
      }
    }
    container multilink {
      tailf:ncs-device-type "cli-ned";
      tailf:display-when "not(../../ncs:module) or ../../ncs:module[ncs:name='tailf-ned-cisco-ios']";
      tailf:info
        "PPP multilink global configuration";
      leaf virtual-template {
        tailf:info
          "virtual-template interface";
        tailf:cli-full-command;
        type uint16 {
          tailf:info
            "<1-4095>;;virtual template number";
          range "1..4095";
        }
      }
      leaf bundle-name {
        tailf:info
          "Select method for naming multilink bundles";
        tailf:cli-full-command;
        type enumeration {
          enum "authenticated" {
            tailf:info
              "Use peer's authenticated name";
          }
          enum "both" {
            tailf:info
              "Use peer's authenticated name and endpoint discriminator";
          }
          enum "endpoint" {
            tailf:info
              "Use peer's endpoint discriminator";
          }
          enum "rfc" {
            tailf:info
              "Use peer and local authenticated name and endpoint discriminator";
          }
        }
      }
    }
    container flow {
      tailf:ncs-device-type "cli-ned";
      tailf:display-when "not(../../ncs:module) or ../../ncs:module[ncs:name='tailf-ned-cisco-ios']";
      tailf:info
        "Global Flow configuration subcommands";
      list exporter {
        tailf:info
          "Define a Flow Exporter";
        tailf:cli-mode-name "config-flow-exporter";
        key "name";
        leaf name {
          type string {
            tailf:info
              "WORD;;Flow Exporter name";
          }
        }
        leaf description {
          tailf:info
            "Provide a description for this Flow Exporter";
          tailf:cli-multi-value;
          tailf:cli-preformatted;
          tailf:cli-full-command;
          type string {
            tailf:info
              "LINE;;Flow Exporter description";
          }
        }
        container destination {
          tailf:info
            "Export destination configuration";
          tailf:cli-compact-syntax;
          tailf:cli-sequence-commands {
            tailf:cli-reset-siblings;
          }
          tailf:cli-case-insensitive;
          leaf address {
            tailf:cli-drop-node-name;
            type inet:host {
              tailf:info
                "Hostname, A.B.C.D or X:X:X:X::X;;Destination IPv4 address or hostname";
            }
          }
          leaf vrf {
            tailf:info
              "Optional VRF label";
            tailf:cli-diff-dependency "../../../../ip/vrf" {
              tailf:xpath-root 3;
            }
            tailf:cli-diff-dependency "../../../../vrf/definition" {
              tailf:xpath-root 3;
            }
            type string {
              tailf:info
                "WORD;;VRF Label";
            }
          }
        }
        container source {
          tailf:info
            "Originating interface";
          uses interface-name-grouping;
        }
        leaf dscp {
          tailf:info
            "Optional DSCP";
          tailf:cli-full-command;
          type uint8 {
            tailf:info
              "<0-63>;;Differentiated services codepoint value";
            range "0..63";
          }
        }
        container transport {
          tailf:info
            "Transport protocol";
          leaf udp {
            tailf:info
              "UDP transport protocol";
            type uint16 {
              tailf:info
                "<1-65535>;;Port value";
              range "1..65535";
            }
          }
        }
        leaf export-protocol {
          tailf:info
            "Export protocol version";
          tailf:cli-full-command;
          type enumeration {
            enum "ipfix" {
              tailf:info
                "IPFIX (Version 10)";
            }
            enum "netflow-v5" {
              tailf:info
                "NetFlow Version 5";
            }
            enum "netflow-v9" {
              tailf:info
                "NetFlow Version 9";
            }
          }
        }
        container template {
          tailf:info
            "Flow Exporter template configuration";
          container data {
            tailf:info
              "Flow Exporter data configuration";
            leaf timeout {
              tailf:info
                "Resend data based on a timeout";
              type uint32 {
                tailf:info
                  "<1-86400>;;Value given in seconds";
                range "1..86400";
              }
            }
          }
        }
        container option {
          tailf:info
            "Select an option for exporting";
          container interface-table {
            tailf:info
              "Interface SNMP-index-to-name Table Option";
            tailf:cli-reset-container;
            presence "true";
            leaf timeout {
              tailf:info
                "Option resend time";
              type uint32 {
                tailf:info
                  "<1-86400>;;Time in seconds";
                range "1..86400";
              }
            }
          }
          container exporter-stats {
            tailf:info
              "Exporter Statistics Option";
            tailf:cli-reset-container;
            presence "true";
            leaf timeout {
              tailf:info
                "Option resend time";
              type uint32 {
                tailf:info
                  "<1-86400>;;Time in seconds";
                range "1..86400";
              }
            }
          }
          container sampler-table {
            tailf:info
              "Export Sampler Option";
            tailf:cli-reset-container;
            presence "true";
            leaf timeout {
              tailf:info
                "Option resend time";
              type uint32 {
                tailf:info
                  "<1-86400>;;Time in seconds";
                range "1..86400";
              }
            }
          }
          container c3pl-class-table {
            tailf:info
              "C3PL class cce-id table";
            tailf:cli-reset-container;
            presence "true";
            leaf timeout {
              tailf:info
                "Option resend time";
              type uint32 {
                tailf:info
                  "<1-86400>;;Value given in seconds";
                range "1..86400";
              }
            }
          }
          container c3pl-policy-table {
            tailf:info
              "C3PL policy cce-id table";
            tailf:cli-reset-container;
            presence "true";
            leaf timeout {
              tailf:info
                "Option resend time";
              type uint32 {
                tailf:info
                  "<1-86400>;;Value given in seconds";
                range "1..86400";
              }
            }
          }
          container application-attributes {
            tailf:info
              "Application Attributes Table Option";
            tailf:cli-reset-container;
            presence "true";
            leaf timeout {
              tailf:info
                "Option resend time";
              type uint32 {
                tailf:info
                  "<1-86400>;;Time in seconds";
                range "1..86400";
              }
            }
          }
          container application-table {
            tailf:info
              "Application Table Option";
            tailf:cli-reset-container;
            presence "true";
            leaf timeout {
              tailf:info
                "Option resend time";
              type uint32 {
                tailf:info
                  "<1-86400>;;Time in seconds";
                range "1..86400";
              }
            }
          }
        }
      }
      list record {
        tailf:cli-mode-name "config-flow-record";
        tailf:cli-full-command;
        key "name";
        leaf name {
          type string {
            tailf:info
              "WORD;;Flow Record name";
          }
        }
        leaf type {
          tailf:info
            "Type of the Flow Record";
          tailf:cli-prefix-key;
          type enumeration {
            enum "mace" {
              tailf:info
                "Measurements Aggregation and Correlation Engine Metrics";
            }
            enum "performance-monitor" {
              tailf:info
                "Config media monitor flow record type";
            }
          }
        }
        leaf description {
          tailf:info
            "Provide a description for this Flow Record";
          tailf:cli-multi-value;
          tailf:cli-preformatted;
          tailf:cli-full-command;
          type string {
            tailf:info
              "LINE;;Flow Record description";
          }
        }
        container match {
          tailf:info
            "Specify a key field";
          container ipv4 {
            tailf:info
              "IPv4 fields";
            leaf tos {
              tailf:info
                "IPv4 type of service";
              type empty;
            }
            leaf ttl {
              tailf:info
                "IPv4 TTL";
              type empty;
            }
            leaf protocol {
              tailf:info
                "IPv4 protocol";
              type empty;
            }
            container source {
              tailf:info
                "IPv4 source address based fields";
              leaf address {
                tailf:info
                  "IPv4 source address";
                type empty;
              }
              container prefix {
                tailf:info
                  "IPv4 address prefix for the IPv4 source address";
                tailf:cli-reset-container;
                presence "true";
                leaf minimum-mask {
                  tailf:info
                    "Provide a minimum mask for this field";
                  type uint8 {
                    tailf:info
                      "<1-32>;;Specify optional minimum mask";
                    range "1..32";
                  }
                }
              }
              container mask {
                tailf:info
                  "IPv4 address mask for the IPv4 source address";
                tailf:cli-reset-container;
                presence "true";
                leaf minimum-mask {
                  tailf:info
                    "Provide a minimum mask for this field";
                  type uint8 {
                    tailf:info
                      "<1-32>;;Specify optional minimum mask";
                    range "1..32";
                  }
                }
              }
            }
            container destination {
              tailf:info
                "IPv4 destination address based fields";
              leaf address {
                tailf:info
                  "IPv4 destination address";
                type empty;
              }
            }
          }
          container ipv6 {
            tailf:info
              "IPv6 fields";
            leaf traffic-class {
              tailf:info
                "IPv6 traffic class";
              type empty;
            }
            leaf protocol {
              tailf:info
                "IPv6 payload protocol";
              type empty;
            }
            container source {
              tailf:info
                "IPv6 source address based fields";
              leaf address {
                tailf:info
                  "IPv6 source address";
                type empty;
              }
            }
            container destination {
              tailf:info
                "IPv6 destination address based fields";
              leaf address {
                tailf:info
                  "IPv6 destination address";
                type empty;
              }
            }
          }
          container connection {
            tailf:info
              "Connection fields";
            leaf transaction-id {
              tailf:info
                "An identifier for a transaction between client and server";
              type empty;
            }
            container client {
              tailf:info
                "Client side (flow initiator) related metrics";
              container ipv4 {
                tailf:info
                  "Client side IPv4 metrics";
                leaf address {
                  tailf:info
                    "IPv4 address of the flow initiator";
                  type empty;
                }
              }
              container ipv6 {
                tailf:info
                  "Client side IPv6 metrics";
                leaf address {
                  tailf:info
                    "IPv6 address of the flow initiator";
                  type empty;
                }
              }
            }
            container server {
              tailf:info
                "Server side (flow responder) related metrics";
              container ipv4 {
                tailf:info
                  "Server side IPv4 metrics";
                leaf address {
                  tailf:info
                    "IPv4 address of the flow responder";
                  type empty;
                }
              }
              container ipv6 {
                tailf:info
                  "Server side IPv6 metrics";
                leaf address {
                  tailf:info
                    "IPv6 address of the flow responder";
                  type empty;
                }
              }
              container transport {
                tailf:info
                  "Server side transport metrics";
                leaf port {
                  tailf:info
                    "Transport port of the flow responder";
                  type empty;
                }
              }
            }
          }
          container policy {
            tailf:info
              "policy fields";
            container qos {
              tailf:info
                "QoS policy related metrics";
              container classification {
                tailf:info
                  "Classification metrics";
                leaf hierarchy {
                  tailf:info
                    "QoS class hierarchy";
                  type empty;
                }
              }
              container queue {
                tailf:info
                  "Queue metrics";
                leaf drops {
                  tailf:info
                    "QoS queue drops";
                  type empty;
                }
                leaf index {
                  tailf:info
                    "QoS queue index";
                  type empty;
                }
              }
            }
          }
          container transport {
            tailf:info
              "Transport layer fields";
            leaf source-port {
              tailf:info
                "Transport source port";
              type empty;
            }
            leaf destination-port {
              tailf:info
                "Transport destination port";
              type empty;
            }
          }
          container interface {
            tailf:info
              "Interface fields";
            container input {
              tailf:info
                "The input interface";
              presence "true";
              leaf snmp {
                tailf:info
                  "SNMP Index of the input interface";
                type empty;
              }
            }
            container output {
              tailf:info
                "The output interface";
              presence "true";
              leaf snmp {
                tailf:info
                  "SNMP Index of the output interface";
                type empty;
              }
            }
          }
          container flow {
            tailf:info
              "Flow identifying fields";
            leaf direction {
              tailf:info
                "Direction the flow was monitored in";
              type empty;
            }
            container sampler {
              tailf:info
                "ID of the sampler";
              presence "true";
              container hash {
                tailf:info
                  "Flow sampler hash related fields";
                leaf digest-value {
                  tailf:info
                    "Result of the hash for hash-based sampling algorithm";
                  type empty;
                }
              }
            }
          }
          container application {
            tailf:info
              "Application fields";
            container name {
              tailf:info
                "Application name";
              tailf:cli-delete-when-empty;
              presence "true";
              leaf account-on-resolution {
                tailf:info
                  "Account on resolution";
                type empty;
              }
            }
          }
        }
        container collect {
          tailf:info
            "Specify a non-key field";
          container routing {
            tailf:info
              "Routing attributes";
            container source {
              tailf:info
                "Source routing attributes";
              container as {
                tailf:info
                  "AS number of the origin network";
                presence "true";
              }
            }
            container destination {
              tailf:info
                "Destination routing attributes";
              container as {
                tailf:info
                  "AS number of the destination network";
                presence "true";
              }
            }
            container vrf {
              tailf:info
                "VRF routing attributes";
              leaf input {
                tailf:info
                  "VRF ID for incoming packet";
                type empty;
              }
              leaf output {
                tailf:info
                  "VRF ID for outgoing packet";
                type empty;
              }
            }
            container next-hop {
              tailf:info
                "Information regarding the next hop";
              container address {
                tailf:info
                  "IP address of the next hop";
                container ipv4 {
                  tailf:info
                    "IPv4 address of the next hop";
                  presence "true";
                  leaf bgp {
                    tailf:info
                      "IPv4 address of the BGP next hop";
                    type empty;
                  }
                }
                container ipv6 {
                  tailf:info
                    "Ipv6 address of the next hop";
                  presence "true";
                  leaf bgp {
                    tailf:info
                      "Ipv6 address of the BGP next hop";
                    type empty;
                  }
                }
              }
            }
          }
          container ipv4 {
            tailf:info
              "IPv4 fields";
            leaf dscp {
              tailf:info
                "IPv4 DSCP (part of TOS)";
              type empty;
            }
            leaf id {
              tailf:info
                "IPv4 ID";
              type empty;
            }
            container source {
              tailf:info
                "IPv4 source address based fields";
              container mask {
                tailf:info
                  "IPv4 address mask for the IPv4 source address";
                presence "true";
              }
              container prefix {
                tailf:info
                  "IPv4 address prefix for the IPv4 source address";
                presence "true";
              }
            }
            container destination {
              tailf:info
                "IPv4 destination address based fields";
              container mask {
                tailf:info
                  "IPv4 address mask for the IPv4 destination address";
                presence "true";
              }
            }
          }
          container ipv6 {
            tailf:info
              "IPv6 fields";
            leaf dscp {
              tailf:info
                "IPv6 DSCP (part of Traffic Class)";
              type empty;
            }
            container source {
              tailf:info
                "IPv6 source address based fields";
              container mask {
                tailf:info
                  "IPv6 address mask for the IPv6 source address";
                presence "true";
              }
            }
            container destination {
              tailf:info
                "Ipv6 destination address based fields";
              container mask {
                tailf:info
                  "Ipv6 address mask for the Ipv6 destination address";
                presence "true";
              }
            }
          }
          container transport {
            tailf:info
              "Transport layer fields";
            container tcp {
              tailf:info
                "TCP fields";
              container flags {
                tailf:info
                  "TCP flags";
                presence "true";
              }
            }
          }
          container interface {
            tailf:info
              "Interface fields";
            leaf input {
              tailf:info
                "The input interface";
              type empty;
            }
            leaf output {
              tailf:info
                "The output interface";
              type empty;
            }
          }
          container flow {
            tailf:info
              "Flow identifying fields";
            leaf sampler {
              tailf:info
                "ID of the sampler";
              type empty;
            }
            leaf direction {
              tailf:info
                "Direction the flow was monitored in";
              type empty;
            }
          }
          container counter {
            tailf:info
              "Counter fields";
            container bytes {
              tailf:info
                "Total number of bytes";
              tailf:cli-delete-when-empty;
              presence "true";
              leaf long {
                tailf:info
                  "Total number of bytes (64 bit counter)";
                type empty;
              }
            }
            container packets {
              tailf:info
                "Total number of packets";
              tailf:cli-delete-when-empty;
              presence "true";
              leaf long {
                tailf:info
                  "Total number of packets (64 bit counter)";
                type empty;
              }
            }
            leaf flows {
              tailf:info
                "Total number of flows";
              type empty;
            }
          }
          container timestamp {
            tailf:info
              "Timestamp fields";
            container sys-uptime {
              tailf:info
                "Timestamps based on the sys-uptime";
              leaf first {
                tailf:info
                  "Time the first packet was seen";
                type empty;
              }
              leaf last {
                tailf:info
                  "Time the most recent packet was seen";
                type empty;
              }
            }
            container absolute {
              tailf:info
                "Timestamps based on the epoch of 00:00 UTC 1st Jan 1970";
              leaf first {
                tailf:info
                  "Absolute time the first packet was seen (milliseconds)";
                type empty;
              }
              leaf last {
                tailf:info
                  "Absolute time the most recent packet was seen (milliseconds)";
                type empty;
              }
            }
          }
          container application {
            tailf:info
              "Application fields";
            container name {
              tailf:info
                "Application name";
              presence "true";
            }
            container http {
              tailf:info
                "World Wide Web traffic";
              leaf host {
                tailf:info
                  "Host name of Origin Server containing resource";
                type empty;
              }
            }
          }
          container connection {
            tailf:info
              "Connection fields";
            leaf initiator {
              tailf:info
                "The direction of the flow";
              type empty;
            }
            leaf new-connections {
              tailf:info
                "The number of connection initiations observed";
              type empty;
            }
            container server {
              tailf:info
                "Server side (flow responder) related metrics";
              container counter {
                tailf:info
                  "Server side counter metrics";
                leaf responses {
                  tailf:info
                    "Number of responses sent by the server";
                  type empty;
                }
                container packets {
                  tailf:info
                    "Number of packets sent by the server";
                  leaf long {
                    tailf:info
                      "64 bits counter";
                    type empty;
                  }
                }
                container bytes {
                  tailf:info
                    "Number of bytes sent by the server";
                  container network {
                    tailf:info
                      "Number of bytes sent by the server";
                    leaf long {
                      tailf:info
                        "Total number of bytes transmitted by the server";
                      type empty;
                    }
                  }
                }
              }
            }
            container delay {
              tailf:info
                "Connection delay metrics";
              container response {
                tailf:info
                  "Response time metrics";
                container to-server {
                  tailf:info
                    "Response time as seen from observation point";
                  container histogram {
                    tailf:info
                      "Histogram for response time";
                    leaf bucket1 {
                      tailf:info
                        "Histogram bucket1 for response time";
                      type empty;
                    }
                    leaf bucket2 {
                      tailf:info
                        "Histogram bucket2 for response time";
                      type empty;
                    }
                    leaf bucket3 {
                      tailf:info
                        "Histogram bucket3 for response time";
                      type empty;
                    }
                    leaf bucket4 {
                      tailf:info
                        "Histogram bucket4 for response time";
                      type empty;
                    }
                    leaf bucket5 {
                      tailf:info
                        "Histogram bucket5 for response time";
                      type empty;
                    }
                    leaf bucket6 {
                      tailf:info
                        "Histogram bucket6 for response time";
                      type empty;
                    }
                    leaf bucket7 {
                      tailf:info
                        "Histogram bucket8 for response time";
                      type empty;
                    }
                    leaf late {
                      tailf:info
                        "Number of late responses";
                      type empty;
                    }
                  }
                }
                container client-to-server {
                  tailf:info
                    "Response time as seen by the client";
                  leaf sum {
                    tailf:info
                      "Total response time";
                    type empty;
                  }
                }
              }
              container network {
                tailf:info
                  "Network time metrics";
                container to-server {
                  tailf:info
                    "RTT from observation point to the server";
                  leaf sum {
                    tailf:info
                      "Total application response time";
                    type empty;
                  }
                }
                container to-client {
                  tailf:info
                    "RTT from observation point to the client";
                  leaf sum {
                    tailf:info
                      "Total network time";
                    type empty;
                  }
                }
              }
              container application {
                tailf:info
                  "Application time metrics";
                leaf sum {
                  tailf:info
                    "Total application response time";
                  type empty;
                }
              }
            }
            container transaction {
              tailf:info
                "Transaction related metrics";
              container counter {
                tailf:info
                  "Transaction counter metrics";
                leaf complete {
                  tailf:info
                    "Number of completed transactions";
                  type empty;
                }
              }
            }
            container client {
              tailf:info
                "Client side (flow initiator) related metrics";
              container counter {
                tailf:info
                  "Client side counter metrics";
                container packets {
                  tailf:info
                    "Number of packets sent by the client";
                  leaf retransmitted {
                    tailf:info
                      "Number of packets retransmitted by the client";
                    type empty;
                  }
                  leaf long {
                    tailf:info
                      "64 bits counter";
                    type empty;
                  }
                }
                container bytes {
                  tailf:info
                    "Number of bytes sent by the client";
                  container network {
                    tailf:info
                      "Number of bytes sent by the client";
                    leaf long {
                      tailf:info
                        "Total number of bytes transmitted by the client";
                      type empty;
                    }
                  }
                }
              }
            }
          }
          container policy {
            tailf:info
              "policy fields";
            container qos {
              tailf:info
                "QoS policy related metrics";
              container queue {
                tailf:info
                  "Queue metrics";
                leaf drops {
                  tailf:info
                    "QoS queue drops";
                  type empty;
                }
                leaf index {
                  tailf:info
                    "QoS queue index";
                  type empty;
                }
              }
              container classification {
                tailf:info
                  "Classification metrics";
                leaf hierarchy {
                  tailf:info
                    "QoS class hierarchy";
                  type empty;
                }
              }
            }
          }
        }
      }
      list monitor {
        tailf:info
          "Define a Flow Monitor";
        tailf:cli-mode-name "config-flow-monitor";
        tailf:cli-full-command;
        key "name";
        leaf name {
          type string {
            tailf:info
              "WORD;;Flow Monitor name";
          }
        }
        leaf type {
          tailf:info
            "Type of the Flow Monitor";
          tailf:cli-prefix-key;
          type enumeration {
            enum "mace" {
              tailf:info
                "Config mace flow monitor type";
            }
            enum "performance-monitor" {
              tailf:info
                "Config media monitor flow monitor type";
            }
          }
        }
        leaf description {
          tailf:info
            "Provide a description for this Flow Monitor";
          tailf:cli-multi-value;
          tailf:cli-preformatted;
          tailf:cli-full-command;
          type string {
            tailf:info
              "LINE;;Flow Monitor description";
          }
        }
        leaf record {
          tailf:info
            "Specify Flow Record";
          tailf:cli-full-command;
          tailf:non-strict-leafref {
            path "../../../flow/record/name";
          }
          type string {
            tailf:info
              "WORD;;record name";
          }
        }
        list exporter {
          tailf:info
            "Add an Exporter to use to export records";
          tailf:cli-suppress-mode;
          tailf:cli-delete-when-empty;
          key "name";
          leaf name {
            tailf:non-strict-leafref {
              path "../../../../flow/exporter/name";
            }
            type string {
              tailf:info
                "WORD;;Flow exporter name";
            }
          }
        }
        container cache {
          tailf:info
            "Configure MACE Flow Cache parameters";
          container timeout {
            tailf:info
              "Cache timeout";
            leaf inactive {
              tailf:info
                "Specify the active flow timeout";
              tailf:cli-full-command;
              type uint32 {
                tailf:info
                  "<1-604800>;;Active timeout in seconds";
                range "1..604800";
              }
            }
            leaf active {
              tailf:info
                "Specify the active flow timeout";
              tailf:cli-full-command;
              type uint32 {
                tailf:info
                  "<1-604800>;;Active timeout in seconds";
                range "1..604800";
              }
            }
            leaf update {
              tailf:info
                "Specify the update timeout for a MACE Flow Cache";
              type enumeration {
                enum "1" {
                  tailf:info
                    "timeout interval of 1 minute";
                }
                enum "10" {
                  tailf:info
                    "timeout interval of 10 minutes";
                }
                enum "15" {
                  tailf:info
                    "timeout interval of 15 minutes";
                }
                enum "2" {
                  tailf:info
                    "timeout interval of 2 minutes";
                }
                enum "5" {
                  tailf:info
                    "timeout interval of 5 minutes (default)";
                }
              }
            }
            leaf synchronized {
              tailf:info
                "Synchronized timeout";
              type uint16 {
                tailf:info
                  "Synchronized timeout value";
                range "1..300";
              }
            }
          }
          leaf type {
            tailf:info
              "Cache type";
            type enumeration {
              enum "immediate" {
                tailf:info
                  "Immediate cache type";
              }
              enum "normal" {
                tailf:info
                  "Normal cache type";
              }
              enum "permanent" {
                tailf:info
                  "Permanent cache type";
              }
              enum "synchronized" {
                tailf:info
                  "synchronized cache type";
              }
            }
          }
          leaf entries {
            tailf:info
              "Number of cache entries";
            type uint32 {
              tailf:info
                "<16-2000000>;;Number of cache entries";
              range "16..2000000";
            }
          }
        }
        container history {
          tailf:info
            "Monitor history intervals";
          leaf size {
            tailf:info
              "History size";
            type uint8 {
              tailf:info
                "<0-60>;;Number of intervals monitored";
              range "0..60";
            }
          }
        }
      }
    }
    list domain {
      tailf:ncs-device-type "cli-ned";
      tailf:display-when "not(../ncs:module) or ../ncs:module[ncs:name='tailf-ned-cisco-ios']";
      tailf:info
        "Domain Configuration Commands";
      tailf:cli-mode-name "config-domain";
      tailf:cli-explicit-exit;
      key "name";
      leaf name {
        type string {
          tailf:info
            "WORD;;Domain Name";
        }
      }
      list vrf {
        tailf:info
          "Specify vrf for domain";
        tailf:cli-mode-name "config-domain-vrf";
        key "name";
        leaf name {
          tailf:cli-diff-dependency "../../../ip/vrf" {
            tailf:xpath-root 3;
          }
          tailf:cli-diff-dependency "../../../vrf/definition" {
            tailf:xpath-root 3;
          }
          type string {
            tailf:info
              "WORD;;VRF name";
          }
        }
        uses domain-master-grouping;
        uses domain-border-grouping;
      }
      uses domain-master-grouping {
        refine "master" {
          tailf:cli-diff-dependency "../vrf" {
            tailf:xpath-root 3;
          }
          tailf:meta-data "suppress-delete-error-invalid";
        }
      }
      uses domain-border-grouping {
        refine "border" {
          tailf:cli-diff-dependency "../vrf" {
            tailf:xpath-root 3;
          }
          tailf:meta-data "suppress-delete-error-invalid";
        }
        augment "border" {
          container advanced {
            tailf:info
              "Advanced configuration submode";
            tailf:cli-add-mode;
            tailf:cli-mode-name "config-domain-br-advanced";
            presence "true";
            uses domain-advanced-smart-probes-grouping;
          }
        }
      }
    }
    container archive {
      tailf:ncs-device-type "cli-ned";
      tailf:display-when "not(../../ncs:module) or ../../ncs:module[ncs:name='tailf-ned-cisco-ios']";
      tailf:info
        "Archive the configuration";
      tailf:cli-add-mode;
      tailf:cli-mode-name "config-archive";
      container log {
        tailf:info
          "Logging commands";
        container config {
          tailf:info
            "Logging changes to the running configuration";
          tailf:cli-add-mode;
          tailf:cli-mode-name "config-archive-log-cfg";
          tailf:cli-full-command;
          container logging {
            tailf:info
              "Modify config logging parameters";
            leaf enable {
              tailf:info
                "Enable the config logger";
              tailf:cli-full-command;
              type empty;
            }
            leaf size {
              tailf:info
                "Maximum number of logged commands that will be kept by the config log";
              tailf:cli-full-command;
              type uint16 {
                tailf:info
                  "<1-1000>;;Queue length (default 100)";
                range "1..1000";
              }
              default "100";
            }
          }
          leaf hidekeys {
            tailf:info
              "suppress output (e.g. passwords) when displaying logged commands";
            tailf:cli-full-command;
            type empty;
          }
          container notify {
            tailf:info
              "Send logged commands to target applications";
            container syslog {
              tailf:info
                "Send logged commands as syslog messages";
              tailf:cli-delete-when-empty;
              presence "true";
              leaf contenttype {
                tailf:info
                  "Type of the syslog message content";
                type enumeration {
                  enum "plaintext" {
                    tailf:info
                      "Plain text content";
                  }
                  enum "xml" {
                    tailf:info
                      "XML content";
                  }
                }
              }
            }
          }
          container record {
            tailf:info
              "What to record in the config logger";
            leaf rc {
              tailf:info
                "Record the PRC result";
              type empty;
            }
          }
        }
      }
      leaf path {
        tailf:info
          "path for backups";
        tailf:cli-full-command;
        type string {
          tailf:info
            "WORD;;Write archive path";
        }
      }
      leaf maximum {
        tailf:info
          "maximum number of backup copies";
        type uint8 {
          tailf:info
            "<1-14>;;maximum number of backup copies";
          range "1..14";
        }
      }
      leaf write-memory {
        tailf:info
          "Enable automatic backup generation during write memory";
        type empty;
      }
    }
    container file {
      tailf:ncs-device-type "cli-ned";
      tailf:display-when "not(../../ncs:module) or ../../ncs:module[ncs:name='tailf-ned-cisco-ios']";
      tailf:info
        "Adjust file system parameters";
      leaf prompt {
        tailf:info
          "Prompt level for file operations";
        type enumeration {
          enum "alert" {
            tailf:info
              "Prompt only for destructive file operations";
          }
          enum "noisy" {
            tailf:info
              "Confirm all file operation parameters";
          }
          enum "quiet" {
            tailf:info
              "Seldom prompt for file operations";
          }
        }
        default "alert";
      }
      leaf verify {
        tailf:info
          "Verify compressed IOS image checksum";
        type enumeration {
          enum "auto" {
            tailf:info
              "Enable automatic checksum verification";
          }
        }
      }
    }
    container object-group {
      tailf:ncs-device-type "cli-ned";
      tailf:display-when "not(../../ncs:module) or ../../ncs:module[ncs:name='tailf-ned-cisco-ios']";
      tailf:info
        "Configure ACL Object Group";
      list network {
        tailf:info
          "network group";
        tailf:cli-mode-name "config-network-group";
        key "name";
        leaf name {
          type string {
            tailf:info
              "WORD;;object-group name";
          }
        }
        leaf description {
          tailf:info
            "Network object group description";
          tailf:cli-multi-value;
          tailf:cli-preformatted;
          tailf:cli-full-command;
          type string {
            tailf:info
              "LINE;;Description of this Object group";
          }
        }
        list host {
          tailf:info
            "Host address of the object-group member";
          tailf:cli-suppress-mode;
          tailf:cli-delete-when-empty;
          key "name";
          leaf name {
            type inet:host {
              tailf:info
                "Hostname or A.B.C.D;;Host address";
            }
          }
        }
        list subnet {
          tailf:cli-drop-node-name;
          tailf:cli-suppress-mode;
          tailf:cli-delete-when-empty;
          key "network-address network-mask";
          leaf network-address {
            type inet:ipv4-address {
              tailf:info
                "A.B.C.D;;Network address of the group members";
            }
          }
          leaf network-mask {
            type inet:ipv4-address {
              tailf:info
                "A.B.C.D;;Network mask";
            }
          }
        }
      }
      list service {
        tailf:info
          "service group";
        tailf:cli-mode-name "config-service-group";
        tailf:cli-full-command;
        key "name";
        leaf name {
          type string {
            tailf:info
              "WORD;;object-group name";
          }
        }
        leaf description {
          tailf:info
            "Service object group description";
          tailf:cli-multi-value;
          tailf:cli-preformatted;
          tailf:cli-full-command;
          type string {
            tailf:info
              "LINE;;Description of this Object group";
          }
        }
        leaf-list protocol {
          tailf:cli-drop-node-name;
          tailf:cli-list-syntax;
          type union {
            type uint8 {
              tailf:info
                "<0-255>;;An IP protocol number";
            }
            type enumeration {
              enum "icmp" {
                tailf:info
                  "Internet Control Message Protocol";
                value 1;
              }
              enum "tcp" {
                tailf:info
                  "Transmission Control Protocol";
                value 6;
              }
              enum "udp" {
                tailf:info
                  "User Datagram Protocol";
                value 17;
              }
            }
          }
        }
        container icmp-options {
          tailf:cli-drop-node-name;
          container icmp {
            tailf:info
              "Internet Control Message Protocol";
            tailf:cli-incomplete-command;
            tailf:cli-incomplete-no;
            list match {
              tailf:cli-drop-node-name;
              tailf:cli-suppress-mode;
              tailf:cli-delete-when-empty;
              key "port";
              leaf port {
                type object-group-service-icmp-type;
              }
              uses object-group-service-protocol-match;
            }
            list range {
              tailf:info
                "Match only packets in the range of port numbers";
              tailf:cli-suppress-mode;
              tailf:cli-delete-when-empty;
              key "begin end";
              leaf begin {
                type object-group-service-icmp-type;
              }
              leaf end {
                type object-group-service-icmp-type;
              }
            }
          }
        }
        container udp-options {
          tailf:cli-drop-node-name;
          container udp {
            tailf:info
              "User Datagram Protocol";
            tailf:cli-incomplete-command;
            tailf:cli-incomplete-no;
            list match {
              tailf:cli-drop-node-name;
              tailf:cli-suppress-mode;
              tailf:cli-delete-when-empty;
              key "port";
              leaf port {
                type object-group-service-udp-type;
              }
              uses object-group-service-protocol-match;
            }
            list range {
              tailf:info
                "Match only packets in the range of port numbers";
              tailf:cli-suppress-mode;
              tailf:cli-delete-when-empty;
              key "begin end";
              leaf begin {
                type object-group-service-udp-type;
              }
              leaf end {
                type object-group-service-udp-type;
              }
            }
          }
        }
        container tcp-options {
          tailf:cli-drop-node-name;
          container tcp {
            tailf:info
              "Transmission Control Protocol";
            tailf:cli-incomplete-command;
            tailf:cli-incomplete-no;
            list match {
              tailf:cli-drop-node-name;
              tailf:cli-suppress-mode;
              tailf:cli-delete-when-empty;
              key "port";
              leaf port {
                type object-group-service-tcp-type;
              }
              uses object-group-service-protocol-match;
            }
            list range {
              tailf:info
                "Match only packets in the range of port numbers";
              tailf:cli-suppress-mode;
              tailf:cli-delete-when-empty;
              key "begin end";
              leaf begin {
                type object-group-service-tcp-type;
              }
              leaf end {
                type object-group-service-tcp-type;
              }
            }
          }
        }
        container tcp-udp {
          tailf:info
            "TCP or UDP protocol";
          tailf:cli-incomplete-command;
          tailf:cli-incomplete-no;
          list match {
            tailf:cli-drop-node-name;
            tailf:cli-suppress-mode;
            tailf:cli-delete-when-empty;
            key "port";
            leaf port {
              type object-group-service-tcp-udp-type;
            }
            uses object-group-service-protocol-match;
          }
          list range {
            tailf:info
              "Match only packets in the range of port numbers";
            tailf:cli-suppress-mode;
            tailf:cli-delete-when-empty;
            key "begin end";
            leaf begin {
              type object-group-service-tcp-udp-type;
            }
            leaf end {
              type object-group-service-tcp-udp-type;
            }
          }
        }
      }
      list security {
        tailf:info
          "security group";
        tailf:cli-mode-name "config-security-group";
        key "name";
        leaf name {
          type string {
            tailf:info
              "WORD;;object-group name";
          }
        }
        leaf description {
          tailf:info
            "Security object group description";
          tailf:cli-multi-value;
          tailf:cli-preformatted;
          tailf:cli-full-command;
          type string {
            tailf:info
              "LINE;;Description of this Object group";
          }
        }
      }
    }
    container key {
      tailf:ncs-device-type "cli-ned";
      tailf:display-when "not(../../ncs:module) or ../../ncs:module[ncs:name='tailf-ned-cisco-ios']";
      tailf:info
        "Key management";
      container config-key {
        tailf:info
          "Set a private configuration key for general use";
        leaf password-encrypt {
          tailf:ned-ignore-compare-config;
          tailf:info
            "Set a private configuration key for password encryption";
          tailf:cli-no-value-on-delete;
          tailf:meta-data "support-encrypted-password";
          type tailf:aes-cfb-128-encrypted-string {
            tailf:info
              "LINE;;The config-key, minimum 8 characters not beginning with IOS special character(! # ;)";
          }
        }
      }
      list chain {
        tailf:info
          "Key-chain management";
        tailf:cli-mode-name "config-keychain";
        key "name";
        leaf name {
          type string {
            tailf:info
              "WORD;;Key-chain name";
          }
        }
        list key {
          tailf:info
            "Configure a key";
          tailf:cli-mode-name "config-keychain-key";
          tailf:cli-full-command;
          key "id";
          leaf id {
            type uint32 {
              tailf:info
                "<0-2147483647>;;Key identifier";
              range "0..2147483647";
            }
          }
          container key-string {
            tailf:info
              "Set key string";
            tailf:cli-compact-syntax;
            tailf:cli-sequence-commands {
              tailf:cli-reset-siblings;
            }
            uses password-grouping;
          }
          leaf cryptographic-algorithm {
            tailf:info
              "Set cryptographic authentication algorithm";
            type enumeration {
              enum "hmac-sha-1" {
                tailf:info
                  "HMAC-SHA-1 authentication algorithm";
              }
              enum "hmac-sha-256" {
                tailf:info
                  "HMAC-SHA-256 authentication algorithm";
              }
              enum "hmac-sha-384" {
                tailf:info
                  "HMAC-SHA-384 authentication algorithm";
              }
              enum "hmac-sha-512" {
                tailf:info
                  "HMAC-SHA-512 authentication algorithm";
              }
              enum "md5" {
                tailf:info
                  "MD5 authentication algorithm";
              }
            }
          }
          container accept-lifetime {
            tailf:info
              "Set accept lifetime of key";
            tailf:cli-compact-syntax;
            tailf:cli-sequence-commands {
              tailf:cli-reset-siblings;
            }
            choice accept-lifetime-choice {
              case global {
                uses lifetime-grouping;
              }
              container local {
                tailf:info
                  "Specify time in local timezone";
                tailf:cli-compact-syntax;
                tailf:cli-sequence-commands {
                  tailf:cli-reset-siblings;
                }
                uses lifetime-grouping;
              }
            }
          }
          container send-lifetime {
            tailf:info
              "Set send lifetime of key";
            tailf:cli-compact-syntax;
            tailf:cli-sequence-commands {
              tailf:cli-reset-siblings;
            }
            choice send-lifetime-choice {
              case global {
                uses lifetime-grouping;
              }
              container local {
                tailf:info
                  "Specify time in local timezone";
                tailf:cli-compact-syntax;
                tailf:cli-sequence-commands {
                  tailf:cli-reset-siblings;
                }
                uses lifetime-grouping;
              }
            }
          }
        }
      }
    }
    container flowspec {
      tailf:ncs-device-type "cli-ned";
      tailf:display-when "not(../../ncs:module) or ../../ncs:module[ncs:name='tailf-ned-cisco-ios']";
      tailf:info
        "FlowSpec configuration";
      tailf:cli-add-mode;
      tailf:cli-mode-name "config-flowspec";
      presence "true";
      container local-install {
        tailf:info
          "Local installation of flowspec policy";
        leaf interface-all {
          tailf:info
            "Install flowspec policy on all interfaces";
          type empty;
        }
      }
      container address-family {
        tailf:info
          "Address Family Identifier Type (IPv4/IPv6)";
        container ipv4 {
          tailf:info
            "IPv4 flow";
          tailf:cli-add-mode;
          tailf:cli-mode-name "config-flowspec-afi";
          container local-install {
            tailf:info
              "Local installation of flowspec policy";
            leaf interface-all {
              tailf:info
                "Install flowspec policy on all interfaces";
              type empty;
            }
          }
        }
        container ipv6 {
          tailf:info
            "IPv4 flow";
          tailf:cli-add-mode;
          tailf:cli-mode-name "config-flowspec-afi";
          container local-install {
            tailf:info
              "Local installation of flowspec policy";
            leaf interface-all {
              tailf:info
                "Install flowspec policy on all interfaces";
              type empty;
            }
          }
        }
      }
      list vrf {
        tailf:info
          "VRF configuration";
        tailf:cli-mode-name "config-flowspec-vrf";
        key "name";
        leaf name {
          tailf:cli-diff-dependency "../../../ip/vrf" {
            tailf:xpath-root 3;
          }
          tailf:cli-diff-dependency "../../../vrf/definition" {
            tailf:xpath-root 3;
          }
          type string {
            tailf:info
              "WORD;;VRF Name.";
          }
        }
        container address-family {
          tailf:info
            "Address Family Identifier Type (IPv4/IPv6)";
          container ipv4 {
            tailf:info
              "IPv4 flow";
            tailf:cli-add-mode;
            tailf:cli-mode-name "config-flowspec-vrf-afi";
            container local-install {
              tailf:info
                "Local installation of flowspec policy";
              leaf interface-all {
                tailf:info
                  "Install flowspec policy on all interfaces";
                type empty;
              }
            }
          }
          container ipv6 {
            tailf:info
              "IPv4 flow";
            tailf:cli-add-mode;
            tailf:cli-mode-name "config-flowspec-vrf-afi";
            container local-install {
              tailf:info
                "Local installation of flowspec policy";
              leaf interface-all {
                tailf:info
                  "Install flowspec policy on all interfaces";
                type empty;
              }
            }
          }
        }
      }
    }
    list username {
      tailf:ncs-device-type "cli-ned";
      tailf:display-when "not(../ncs:module) or ../ncs:module[ncs:name='tailf-ned-cisco-ios']";
      tailf:info
        "Establish User Name Authentication";
      tailf:cli-suppress-mode;
      tailf:cli-delete-when-empty;
      tailf:cli-compact-syntax;
      key "name";
      leaf name {
        type string {
          tailf:info
            "WORD;;User name";
        }
      }
      leaf privilege {
        tailf:info
          "Set user privilege level";
        type uint8 {
          tailf:info
            "<0-15>;;User privilege level";
          range "0..15";
        }
        default "1";
      }
      container secret {
        tailf:info
          "Specify the secret for the user";
        tailf:cli-flatten-container;
        tailf:cli-compact-syntax;
        tailf:cli-sequence-commands;
        leaf type {
          tailf:cli-optional-in-sequence;
          tailf:cli-drop-node-name;
          tailf:cli-incomplete-command;
          type enumeration {
            enum "0" {
              tailf:info
                "Specifies an UNENCRYPTED secret will follow";
            }
            enum "4" {
              tailf:info
                "Specifies a HIDDEN secret will follow";
            }
            enum "5" {
              tailf:info
                "Specifies a HIDDEN secret will follow";
            }
            enum "8" {
              tailf:info
                "Specifies a PBKDF2 HASHED secret will follow";
            }
            enum "9" {
              tailf:info
                "Specifies a SCRYPT HASHED secret will follow";
            }
          }
        }
        leaf secret {
          tailf:cli-drop-node-name;
          tailf:cli-reset-container;
          tailf:cli-full-command;
          tailf:cli-disallow-value "0|4|5|8|9|key-chain";
          tailf:meta-data "secret-password";
          type string {
            tailf:info
              "WORD;;The HIDDEN user secret string";
          }
        }
      }
      container password {
        tailf:info
          "Specify the password for the user";
        tailf:cli-flatten-container;
        tailf:cli-compact-syntax;
        tailf:cli-sequence-commands;
        uses password-grouping;
      }
    }
    list table-map {
      tailf:ncs-device-type "cli-ned";
      tailf:display-when "not(../ncs:module) or ../ncs:module[ncs:name='tailf-ned-cisco-ios']";
      tailf:info
        "Configure Table Map";
      tailf:cli-mode-name "config-tablemap";
      key "name";
      leaf name {
        type string {
          tailf:info
            "WORD;;table-map name";
        }
      }
      container map {
        tailf:info
          "map to_value from from_value";
        list from {
          tailf:info
            "map from value";
          tailf:cli-suppress-mode;
          tailf:cli-delete-when-empty;
          tailf:cli-incomplete-command;
          key "id";
          leaf id {
            type uint8 {
              tailf:info
                "<0-99>;;tablemap from value";
              range "0..99";
            }
          }
          leaf to {
            tailf:info
              "map to value";
            type uint8 {
              tailf:info
                "<0-99>;;tablemap to value";
              range "0..99";
            }
          }
        }
      }
      leaf default {
        tailf:info
          "the default behavior for setting value not found in the table map";
        type union {
          type uint8 {
            tailf:info
              "<0-99>;;tablemap default value";
            range "0..99";
          }
          type enumeration {
            enum "copy" {
              tailf:info
                "set the default behavior for value not found in the table map to copy";
            }
            enum "ignore" {
              tailf:info
                "set the default behavior for value not found in the table map to ignore";
            }
          }
        }
      }
    }
    container sdm {
      tailf:ncs-device-type "cli-ned";
      tailf:display-when "not(../../ncs:module) or ../../ncs:module[ncs:name='tailf-ned-cisco-ios']";
      tailf:info
        "Switch database management";
      container prefer {
        tailf:info
          "Config TCAM and ASIC RAM size. Warning: need to reset switch for configuration to take effect";
        tailf:cli-delete-when-empty;
        presence "true";
        choice sdm-prefer-choice {
          leaf access {
            tailf:info
              "Access bias";
            type empty;
          }
          leaf default {
            tailf:info
              "Default bias";
            type empty;
          }
          leaf dual-ipv4-and-ipv6 {
            tailf:info
              "Support both IPv4 and IPv6";
            type enumeration {
              enum "default" {
                tailf:info
                  "Default bias";
              }
              enum "routing" {
                tailf:info
                  "Unicast bias";
              }
              enum "vlan" {
                tailf:info
                  "VLAN bias";
              }
            }
          }
          leaf routing {
            tailf:info
              "Unicast bias";
            type empty;
          }
          leaf qos {
            type empty;
          }
          leaf vlan {
            tailf:info
              "VLAN bias";
            type empty;
          }
        }
      }
    }
    container mls {
      tailf:ncs-device-type "cli-ned";
      tailf:display-when "not(../../ncs:module) or ../../ncs:module[ncs:name='tailf-ned-cisco-ios']";
      tailf:info
        "mls global commands";
      tailf:cli-incomplete-no;
      container acl {
        tailf:info
          "MLS ACL operation";
        container tcam {
          tailf:info
            "ACL TCAM";
          leaf default-result {
            tailf:info
              "Default result to be used during tcam programming";
            type enumeration {
              enum "bridge" {
                tailf:info
                  "Bridge result";
              }
              enum "deny" {
                tailf:info
                  "Deny result";
              }
              enum "permit" {
                tailf:info
                  "Permit result";
              }
            }
          }
          container log-update {
            tailf:info
              "Log TCAM updates";
            presence "true";
            leaf rate-limit-msg {
              tailf:info
                "Enable/Disable syslog ratelimiting";
              type enumeration {
                enum "disable" {
                  tailf:info
                    "Disable ratelimiting syslog";
                }
                enum "enable" {
                  tailf:info
                    "Enable syslog ratelimiting at 1 per second";
                }
              }
            }
          }
          leaf share-global {
            tailf:info
              "share global deny or permit any entries";
            tailf:cli-boolean-no;
            tailf:cli-full-command;
            type boolean;
            default "true";
          }
        }
      }
      container cef {
        tailf:info
          "cef keyword";
        container error {
          leaf action {
            type enumeration {
              enum "reset";
              enum "freeze";
            }
          }
        }
      }
      container ip {
        tailf:info
          "ip keyword";
        container multicast {
          tailf:info
            "multicast keyword";
          tailf:cli-display-separated;
          presence "true";
          container consistency-check {
            tailf:info
              "Set consistency checking characteristics";
            presence "true";
            container type {
              tailf:info
                "Set consistency checker type";
              container rp-sp {
                tailf:info
                  "Scan mlsm for Route, Switch Processor consistency";
                presence "true";
              }
            }
            leaf settle-time {
              tailf:info
                "Settle time for entry/oif for consistancy-checker";
              type uint16 {
                tailf:info
                  "<2-3600>;;Settle time for entry/oif in seconds";
                range "2..3600";
              }
            }
          }
          leaf flow-stat-timer {
            tailf:info
              "timer for flow statistic used by mls-msc and mlsm";
            type uint8 {
              tailf:info
                "<1-100>;;#seconds between one batch and another";
              range "1..100";
            }
          }
        }
      }
      container ipv6 {
        tailf:info
          "Enable global ipv6 commands";
        leaf vrf {
          tailf:info
            "Enable IPv6 VRF";
          tailf:cli-full-command;
          type empty;
        }
      }
      container aging {
        tailf:info
          "L3 aging";
        container fast {
          tailf:info
            "L3 fast aging";
          tailf:cli-compact-syntax;
          tailf:cli-delete-when-empty;
          presence "true";
          leaf time {
            tailf:info
              "fast aging timeout value";
            type uint8 {
              tailf:info
                "<1-128>;;L3 fast aging time in seconds";
              range "1..128";
            }
          }
          leaf threshold {
            tailf:info
              "fast aging threshold";
            type uint8 {
              tailf:info
                "<1-128>;;L3 fast aging theshold packet count";
              range "1..128";
            }
          }
        }
        container normal {
          tailf:info
            "normal aging keyword";
          leaf seconds {
            tailf:cli-drop-node-name;
            type uint16 {
              tailf:info
                "<32-4092>;;L3 aging timeout in second";
              range "32..4092";
            }
          }
        }
        container long {
          tailf:info
            "long aging keyword";
          leaf timeout {
            tailf:cli-drop-node-name;
            type uint16 {
              tailf:info
                "<64-1920>;;long aging timeout";
              range "64..1920";
            }
          }
        }
      }
      container netflow {
        tailf:info
          "netflow keyword";
        tailf:cli-delete-when-empty;
        presence "true";
        leaf interface {
          type empty;
        }
        container usage {
          container notify {
            tailf:cli-compact-syntax;
            tailf:cli-sequence-commands {
              tailf:cli-reset-siblings;
            }
            leaf percentage {
              tailf:cli-drop-node-name;
              type uint8 {
                tailf:info
                  "<20-100>;;threshold percentage";
                range "20..100";
              }
            }
            leaf seconds {
              tailf:cli-drop-node-name;
              type uint32 {
                tailf:info
                  "<120-1000000>;;time interval in seconds";
                range "120..1000000";
              }
            }
          }
        }
      }
      container flow {
        tailf:info
          "flowmask keyword";
        leaf ip {
          tailf:info
            "flowmask ip keyword";
          type enumeration {
            enum "interface-destination" {
              tailf:info
                "interface-destination flow keyword";
            }
            enum "interface-destination-source" {
              tailf:info
                "interface-destination-source flow keyword";
            }
            enum "interface-full" {
              tailf:info
                "interface-full flow keyword";
            }
            enum "interface-source" {
              tailf:info
                "interface-source only flow keyword";
            }
          }
        }
        choice ipv6-choice {
          container no-ipv6 {
            tailf:cli-drop-node-name;
            leaf ipv6 {
              tailf:cli-boolean-no;
              tailf:cli-full-no;
              type boolean;
              default "true";
            }
          }
          container ipv6 {
            tailf:info
              "flowmask ipv6 keyword";
            tailf:cli-incomplete-command;
            tailf:cli-incomplete-no;
            choice ipv6-choice2 {
              leaf interface-destination {
                tailf:info
                  "interface-destination flow keyword";
                type empty;
              }
              leaf interface-destination-source {
                tailf:info
                  "interface-destination-source flow keyword";
                type empty;
              }
              leaf interface-full {
                tailf:info
                  "interface-full flow keyword";
                type empty;
              }
              leaf interface-source {
                tailf:info
                  "interface-source only flow keyword";
                type empty;
              }
            }
          }
        }
      }
      container sampling {
        tailf:info
          "sampling keyword";
        leaf time-based {
          type uint16;
        }
      }
      container mls-qos-conf {
        tailf:cli-drop-node-name;
        leaf qos {
          type empty;
        }
      }
      container qos {
        tailf:info
          "QoS parameters";
        tailf:cli-incomplete-command;
        tailf:cli-incomplete-no;
        list aggregate-policer {
          tailf:info
            "Assign aggregate policer";
          tailf:cli-suppress-mode;
          tailf:cli-delete-when-empty;
          tailf:cli-compact-syntax;
          tailf:cli-sequence-commands {
            tailf:cli-reset-all-siblings;
          }
          key "name";
          leaf name {
            type string {
              tailf:info
                "WORD;;aggregate policer name";
            }
          }
          leaf target-bit-rate {
            tailf:cli-drop-node-name;
            type uint64 {
              tailf:info
                "<32000-60000000000>;;Target Bit Rate (bits per second) (postfix k, m, g optional; decimal point allowed)";
              range "32000..60000000000";
            }
          }
          leaf burst-normal {
            tailf:cli-drop-node-name;
            tailf:cli-optional-in-sequence;
            type uint32 {
              tailf:info
                "<1000-31250000>;;Normal burst bytes";
              range "1000..31250000";
            }
          }
          leaf burst-max {
            tailf:cli-drop-node-name;
            tailf:cli-optional-in-sequence;
            when "../burst-normal" {
              tailf:xpath-root 3;
              tailf:dependency "../burst-normal";
            }
            type uint32 {
              tailf:info
                "<1000-31250000>;;Maximum burst bytes";
              range "1000..31250000";
            }
          }
          leaf pir {
            tailf:info
              "PIR";
            tailf:cli-optional-in-sequence;
            type uint64 {
              tailf:info
                "<32000-60000000000>;;Target Bit Rate (bits per second) (postfix k, m, g optional; decimal point allowed)";
              range "32000..60000000000";
            }
          }
          container conform-action {
            tailf:info
              "action when rate is not exceeded";
            tailf:cli-optional-in-sequence;
            tailf:cli-flatten-container;
            tailf:cli-compact-syntax;
            choice action-choice {
              leaf drop {
                tailf:info
                  "drop packet";
                type empty;
              }
              leaf set-dscp-transmit {
                tailf:info
                  "set dscp and send it";
                type dscp-type;
              }
              leaf set-mpls-exp-imposition-transmit {
                tailf:info
                  "set exp at tag imposition and send it";
                type uint8 {
                  tailf:info
                    "<0-7>;;new exp";
                  range "0..7";
                }
              }
              leaf set-prec-transmit {
                tailf:info
                  "rewrite packet precedence and send it";
                type uint8 {
                  tailf:info
                    "<0-7>;;new precedence";
                  range "0..7";
                }
              }
              leaf transmit {
                tailf:info
                  "transmit packet";
                type empty;
              }
            }
          }
          leaf exceed-action {
            tailf:info
              "action when rate is exceeded";
            tailf:cli-optional-in-sequence;
            type enumeration {
              enum "drop" {
                tailf:info
                  "drop packet";
              }
              enum "policed-dscp-transmit" {
                tailf:info
                  "change dscp per policed-dscp map and send it";
              }
              enum "transmit" {
                tailf:info
                  "transmit packet";
              }
            }
          }
          leaf violate-action {
            tailf:info
              "action when rate violated";
            type enumeration {
              enum "drop" {
                tailf:info
                  "drop packet";
              }
              enum "policed-dscp-transmit" {
                tailf:info
                  "change dscp per policed-dscp map and send it";
              }
              enum "transmit" {
                tailf:info
                  "transmit packet";
              }
            }
          }
        }
        container cos {
          tailf:info
            "Configure CoS setting";
          leaf policy-map {
            tailf:info
              "Set by Policy-Map";
            type empty;
          }
        }
        container rewrite {
          tailf:info
            "packet qos rewrite enable/disable";
          container ip {
            tailf:info
              "ip packet qos rewrite enable/disable";
            container dscp {
              tailf:info
                "packet ip dscp rewrite enable/disable";
              presence "true";
              leaf slot {
                tailf:info
                  "slot number";
                type string {
                  tailf:info
                    "WORD;;Slots seperated by commas. Valid slots: 1,2,3,4,5,6,7,8,9";
                }
              }
            }
          }
        }
        container map {
          tailf:info
            "Define QoS mapping";
          list dscp-mutation {
            tailf:info
              "Configure dscp-mutation map";
            tailf:cli-suppress-mode;
            tailf:cli-delete-when-empty;
            tailf:cli-compact-syntax;
            tailf:cli-sequence-commands {
              tailf:cli-reset-siblings;
            }
            tailf:cli-incomplete-command;
            key "name";
            leaf name {
              type string {
                tailf:info
                  "WORD;;DSCP mutation map name";
              }
            }
            leaf mutated-dscp1 {
              tailf:cli-drop-node-name;
              tailf:cli-incomplete-command;
              type uint8 {
                tailf:info
                  "<0-63>;;dscp values separated by spaces (8 values total)";
                range "0..63";
              }
            }
            leaf mutated-dscp2 {
              tailf:cli-drop-node-name;
              tailf:cli-optional-in-sequence;
              tailf:cli-incomplete-command;
              type uint8 {
                tailf:info
                  "<0-63>;;dscp values separated by spaces (8 values total)";
                range "0..63";
              }
            }
            leaf mutated-dscp3 {
              tailf:cli-drop-node-name;
              tailf:cli-optional-in-sequence;
              tailf:cli-incomplete-command;
              type uint8 {
                tailf:info
                  "<0-63>;;dscp values separated by spaces (8 values total)";
                range "0..63";
              }
            }
            leaf mutated-dscp4 {
              tailf:cli-drop-node-name;
              tailf:cli-optional-in-sequence;
              tailf:cli-incomplete-command;
              type uint8 {
                tailf:info
                  "<0-63>;;dscp values separated by spaces (8 values total)";
                range "0..63";
              }
            }
            leaf mutated-dscp5 {
              tailf:cli-drop-node-name;
              tailf:cli-optional-in-sequence;
              tailf:cli-incomplete-command;
              type uint8 {
                tailf:info
                  "<0-63>;;dscp values separated by spaces (8 values total)";
                range "0..63";
              }
            }
            leaf mutated-dscp6 {
              tailf:cli-drop-node-name;
              tailf:cli-optional-in-sequence;
              tailf:cli-incomplete-command;
              type uint8 {
                tailf:info
                  "<0-63>;;dscp values separated by spaces (8 values total)";
                range "0..63";
              }
            }
            leaf mutated-dscp7 {
              tailf:cli-drop-node-name;
              tailf:cli-optional-in-sequence;
              tailf:cli-incomplete-command;
              type uint8 {
                tailf:info
                  "<0-63>;;dscp values separated by spaces (8 values total)";
                range "0..63";
              }
            }
            leaf mutated-dscp8 {
              tailf:cli-drop-node-name;
              tailf:cli-optional-in-sequence;
              tailf:cli-incomplete-command;
              type uint8 {
                tailf:info
                  "<0-63>;;dscp values separated by spaces (8 values total)";
                range "0..63";
              }
            }
            leaf to {
              tailf:info
                "Specify egress DSCPs";
              type uint16 {
                tailf:info
                  "<0-63>;;dscp value";
                range "0..63";
              }
            }
          }
          leaf-list cos-dscp {
            tailf:info
              "cos-dscp map: eight dscp values for cos 0-7";
            tailf:cli-flat-list-syntax;
            tailf:cli-no-value-on-delete;
            type uint8 {
              tailf:info
                "<0-63>;;8 dscp values separated by spaces";
              range "0..63";
            }
          }
          leaf-list ip-prec-dscp {
            tailf:info
              "dscp values for ip precedences 0 - 7";
            tailf:cli-flat-list-syntax;
            tailf:cli-no-value-on-delete;
            type uint8 {
              tailf:info
                "<0-63>;;8 dscp values separated by spaces";
              range "0..63";
            }
          }
          list exp-mutation {
            tailf:info
              "exp-mutation map keyword";
            tailf:cli-suppress-mode;
            tailf:cli-delete-when-empty;
            tailf:cli-compact-syntax;
            tailf:cli-sequence-commands {
              tailf:cli-reset-siblings;
            }
            tailf:cli-incomplete-command;
            key "name";
            leaf name {
              type string {
                tailf:info
                  "WORD;;exp-mutation map name";
              }
            }
            leaf mutated-exp1 {
              tailf:cli-drop-node-name;
              tailf:cli-incomplete-command;
              type uint8 {
                tailf:info
                  "<0-7>;;exp values separated by spaces (8 values total)";
                range "0..7";
              }
            }
            leaf mutated-exp2 {
              tailf:cli-drop-node-name;
              tailf:cli-incomplete-command;
              type uint8 {
                tailf:info
                  "<0-7>;;exp values separated by spaces (8 values total)";
                range "0..7";
              }
            }
            leaf mutated-exp3 {
              tailf:cli-drop-node-name;
              tailf:cli-incomplete-command;
              type uint8 {
                tailf:info
                  "<0-7>;;exp values separated by spaces (8 values total)";
                range "0..7";
              }
            }
            leaf mutated-exp4 {
              tailf:cli-drop-node-name;
              tailf:cli-incomplete-command;
              type uint8 {
                tailf:info
                  "<0-7>;;exp values separated by spaces (8 values total)";
                range "0..7";
              }
            }
            leaf mutated-exp5 {
              tailf:cli-drop-node-name;
              tailf:cli-incomplete-command;
              type uint8 {
                tailf:info
                  "<0-7>;;exp values separated by spaces (8 values total)";
                range "0..7";
              }
            }
            leaf mutated-exp6 {
              tailf:cli-drop-node-name;
              tailf:cli-incomplete-command;
              type uint8 {
                tailf:info
                  "<0-7>;;exp values separated by spaces (8 values total)";
                range "0..7";
              }
            }
            leaf mutated-exp7 {
              tailf:cli-drop-node-name;
              tailf:cli-incomplete-command;
              type uint8 {
                tailf:info
                  "<0-7>;;exp values separated by spaces (8 values total)";
                range "0..7";
              }
            }
            leaf mutated-exp8 {
              tailf:cli-drop-node-name;
              type uint8 {
                tailf:info
                  "<0-7>;;exp values separated by spaces (8 values total)";
                range "0..7";
              }
            }
          }
        }
        container srr-queue {
          tailf:info
            "Configure SRR receive queues";
          list cos-dscp-list {
            tailf:cli-drop-node-name;
            tailf:cli-suppress-mode;
            tailf:cli-delete-when-empty;
            tailf:cli-compact-syntax;
            tailf:meta-data "replace-mls-qos-srr-queue";
            tailf:ned-data "." {
              tailf:xpath-root 3;
              tailf:transaction to;
            }
            key "direction maptype";
            leaf direction {
              type enumeration {
                enum "input" {
                  tailf:info
                    "input keyword";
                }
                enum "output" {
                  tailf:info
                    "output keyword";
                }
              }
            }
            leaf maptype {
              type enumeration {
                enum "cos-map" {
                  tailf:info
                    "Configure cos-map for a queue id";
                }
                enum "dscp-map" {
                  tailf:info
                    "Configure dscp-map for a queue id";
                }
              }
            }
            list queue-threshold-list {
              tailf:cli-drop-node-name;
              tailf:cli-suppress-mode;
              tailf:cli-delete-when-empty;
              tailf:cli-compact-syntax;
              tailf:cli-incomplete-command;
              key "queue threshold";
              leaf queue {
                tailf:info
                  "Assign COS|DSCP values to a queue";
                tailf:cli-expose-key-name;
                type uint8 {
                  tailf:info
                    "<num>;;enter <cos|dscp>-map queue id";
                }
              }
              leaf threshold {
                tailf:info
                  "Assign COS|DSCP values to a queue threshold";
                tailf:cli-expose-key-name;
                type uint8 {
                  tailf:info
                    "<num>;;enter <cos|dscp>-map threshold id";
                }
              }
              leaf-list values {
                tailf:cli-drop-node-name;
                tailf:cli-flat-list-syntax;
                type uint8 {
                  tailf:info
                    "cos|dscp values separated by spaces";
                }
              }
            }
          }
          container input {
            tailf:cli-incomplete-no;
            list priority-queue {
              tailf:info
                "Configure priority scheduling";
              tailf:cli-suppress-mode;
              tailf:cli-delete-when-empty;
              tailf:cli-compact-syntax;
              key "queue";
              leaf queue {
                type uint8 {
                  tailf:info
                    "<1-2>;;enter priority queue number [1-2]";
                }
              }
              leaf bandwidth {
                tailf:info
                  "ingress priority queue bandwidth % of stack ring";
                tailf:cli-no-name-on-delete;
                tailf:cli-no-value-on-delete;
                type uint8 {
                  tailf:info
                    "<0-40>;;enter bandwidth number [0-40]";
                }
              }
            }
            container bandwidth {
              tailf:info
                "Configure SRR bandwidth";
              tailf:cli-compact-syntax;
              tailf:cli-sequence-commands {
                tailf:cli-reset-siblings;
              }
              leaf weight1 {
                tailf:cli-drop-node-name;
                tailf:cli-no-value-on-delete;
                type uint8 {
                  tailf:info
                    "<1-100>;;enter bandwidth weight for queue id 1";
                }
              }
              leaf weight2 {
                tailf:cli-drop-node-name;
                tailf:cli-no-value-on-delete;
                type uint8 {
                  tailf:info
                    "<1-100>;;enter bandwidth weight for queue id 2";
                }
              }
            }
            list threshold {
              tailf:info
                "Configure queue tail-drop thresholds";
              tailf:cli-suppress-mode;
              tailf:cli-delete-when-empty;
              tailf:cli-compact-syntax;
              key "queue";
              leaf queue {
                type uint8 {
                  tailf:info
                    "<1-2>;;enter threshold queue id (1-2)";
                }
              }
              leaf threshold-percentage1 {
                tailf:cli-drop-node-name;
                tailf:cli-no-value-on-delete;
                type uint8 {
                  tailf:info
                    "<1-100>;;enter percent of queue size for threshold 1";
                }
              }
              leaf threshold-percentage2 {
                tailf:cli-drop-node-name;
                tailf:cli-no-value-on-delete;
                type uint8 {
                  tailf:info
                    "<1-100>;;enter percent of queue size for threshold 2";
                }
              }
            }
            container buffers {
              tailf:info
                "Configure buffer allocation";
              tailf:cli-compact-syntax;
              tailf:cli-sequence-commands {
                tailf:cli-reset-siblings;
              }
              leaf percentage1 {
                tailf:cli-drop-node-name;
                tailf:cli-no-value-on-delete;
                type uint8 {
                  tailf:info
                    "<0-100>;;enter percent of buffers for queue 1";
                }
              }
              leaf percentage2 {
                tailf:cli-drop-node-name;
                tailf:cli-no-value-on-delete;
                type uint8 {
                  tailf:info
                    "<0-100>;;enter percent of buffers for queue 2";
                }
              }
            }
          }
        }
        container queue-set {
          tailf:info
            "Choose a queue set for this queue";
          container output {
            tailf:info
              "Direction the command applies for this command";
            list threshold-list {
              tailf:cli-drop-node-name;
              tailf:cli-suppress-mode;
              tailf:cli-delete-when-empty;
              tailf:cli-compact-syntax;
              key "queue threshold";
              leaf queue {
                type uint8 {
                  tailf:info
                    "<1-2>;;queue-set id";
                }
              }
              leaf threshold {
                tailf:info
                  "Assign threshold values to a queue";
                tailf:cli-expose-key-name;
                type uint8 {
                  tailf:info
                    "<1-4>;;enter queue id in this queue set";
                }
              }
              leaf drop-threshold1 {
                tailf:cli-drop-node-name;
                tailf:cli-no-value-on-delete;
                type uint16 {
                  tailf:info
                    "<1-3200>;;enter drop threshold1 1-3200";
                }
              }
              leaf drop-threshold2 {
                tailf:cli-drop-node-name;
                tailf:cli-no-value-on-delete;
                type uint16 {
                  tailf:info
                    "<1-3200>;;enter drop threshold2 1-3200";
                }
              }
              leaf reserved-threshold {
                tailf:cli-drop-node-name;
                tailf:cli-no-value-on-delete;
                type uint16 {
                  tailf:info
                    "<1-100>;;enter reserved threshold 1-100";
                }
              }
              leaf maximum-threshold {
                tailf:cli-drop-node-name;
                tailf:cli-no-value-on-delete;
                type uint16 {
                  tailf:info
                    "<1-3200>;;enter maximum threshold 1-3200";
                }
              }
            }
            list buffers-list {
              tailf:cli-drop-node-name;
              tailf:cli-suppress-mode;
              tailf:cli-delete-when-empty;
              tailf:cli-compact-syntax;
              key "queue";
              leaf queue {
                type uint8 {
                  tailf:info
                    "<1-2>;;queue-set id";
                }
              }
              container buffers {
                tailf:info
                  "mls qos queue-set output buffers";
                tailf:cli-compact-syntax;
                tailf:cli-sequence-commands {
                  tailf:cli-reset-siblings;
                }
                leaf allocation1 {
                  tailf:cli-drop-node-name;
                  tailf:cli-no-value-on-delete;
                  type uint8 {
                    tailf:info
                      "<0-99>;;enter buffer percentage for queue 1 0-";
                  }
                }
                leaf allocation2 {
                  tailf:cli-drop-node-name;
                  tailf:cli-no-value-on-delete;
                  type uint8 {
                    tailf:info
                      "<1-100>;;enter buffer percentage for queue 2 1-100 (includes CPU buffer";
                  }
                }
                leaf allocation3 {
                  tailf:cli-drop-node-name;
                  tailf:cli-no-value-on-delete;
                  type uint8 {
                    tailf:info
                      "<0-99>;;enter buffer percentage for queue 3 0-99";
                  }
                }
                leaf allocation4 {
                  tailf:cli-drop-node-name;
                  tailf:cli-no-value-on-delete;
                  type uint8 {
                    tailf:info
                      "<0-99>;;enter buffer percentage for queue 4 0-99";
                  }
                }
              }
            }
          }
        }
        list min-reserve {
          tailf:info
            "Configure min-reserve buffers";
          tailf:cli-suppress-mode;
          tailf:cli-delete-when-empty;
          tailf:cli-incomplete-command;
          key "level";
          leaf level {
            type uint8 {
              tailf:info
                "<1-8>;;Configure min-reserve level";
              range "1..8";
            }
          }
          leaf buffersize {
            tailf:cli-drop-node-name;
            type uint8 {
              tailf:info
                "<10-170>;;Configure min-reserve buffers";
              range "10..170";
            }
          }
        }
      }
      container rate-limit {
        tailf:info
          "Rate limit different behaviors";
        container multicast {
          tailf:info
            "Rate limiting for Multicast packets";
          list ipv4 {
            tailf:info
              "Rate limiters for IPv4 traffic";
            tailf:cli-suppress-mode;
            tailf:cli-delete-when-empty;
            tailf:cli-compact-syntax;
            tailf:cli-sequence-commands {
              tailf:cli-reset-siblings;
            }
            key "name";
            leaf name {
              type enumeration {
                enum "fib-miss" {
                  tailf:info
                    "Rate limiting of fib-missed multicast packets";
                }
                enum "connected" {
                  tailf:info
                    "Rate limiting of multicast packets from directly connected source";
                }
                enum "ip-options" {
                  tailf:info
                    "rate limiting of multicast packets with ip options";
                }
                enum "igmp" {
                  tailf:info
                    "Rate limiting of the IGMP protocol packets";
                }
                enum "partial" {
                  tailf:info
                    "rate limiting of multicast packets during partial-SC state";
                }
                enum "pim" {
                  tailf:info
                    "Rate limiting of the PIM protocol packets";
                }
                enum "tiny-fragment" {
                  tailf:info
                    "packets with fragment offset equal to 1";
                }
                enum "non-rpf" {
                  tailf:info
                    "Rate limiting of non-rpf multicast packets";
                }
              }
            }
            leaf pps {
              tailf:cli-drop-node-name;
              type uint32 {
                tailf:info
                  "<10-1000000>;;packets per second";
                range "10..1000000";
              }
            }
            leaf packets-in-burst {
              tailf:cli-drop-node-name;
              type uint8 {
                tailf:info
                  "<1-255>;;packets in burst";
                range "1..255";
              }
            }
          }
        }
        container all {
          tailf:info
            "Rate Limiting for both Unicast and Multicast packets";
          container mtu-failure {
            tailf:info
              "MTU failure cases";
            tailf:cli-compact-syntax;
            tailf:cli-sequence-commands {
              tailf:cli-reset-siblings;
            }
            leaf pps {
              tailf:cli-drop-node-name;
              type uint32 {
                tailf:info
                  "<10-1000000>;;packets per second";
                range "10..1000000";
              }
            }
            leaf packets-in-burst {
              tailf:cli-drop-node-name;
              type uint8 {
                tailf:info
                  "<1-255>;;packets in burst";
                range "1..255";
              }
            }
          }
          container ttl-failure {
            tailf:info
              "TTL failure cases";
            tailf:cli-compact-syntax;
            tailf:cli-sequence-commands {
              tailf:cli-reset-siblings;
            }
            leaf pps {
              tailf:cli-drop-node-name;
              type uint32 {
                tailf:info
                  "<10-1000000>;;packets per second";
                range "10..1000000";
              }
            }
            leaf packets-in-burst {
              tailf:cli-drop-node-name;
              type uint8 {
                tailf:info
                  "<1-255>;;packets in burst";
                range "1..255";
              }
            }
          }
        }
        container layer2 {
          tailf:info
            "layer2 protocol cases";
          container l2pt {
            tailf:info
              "layer2 protocol tunnelling packets";
            tailf:cli-compact-syntax;
            tailf:cli-sequence-commands {
              tailf:cli-reset-siblings;
            }
            leaf packets-per-second {
              tailf:cli-drop-node-name;
              type uint32 {
                tailf:info
                  "<10-1000000>;;packets per second";
                range "10..1000000";
              }
            }
            leaf packets-in-burst {
              tailf:cli-drop-node-name;
              type uint32 {
                tailf:info
                  "<1-255>;;packets in burst";
                range "1..255";
              }
            }
          }
          container pdu {
            tailf:info
              "layer2 protocol data unit packets";
            tailf:cli-compact-syntax;
            tailf:cli-sequence-commands {
              tailf:cli-reset-siblings;
            }
            leaf packets-per-second {
              tailf:cli-drop-node-name;
              type uint32 {
                tailf:info
                  "<10-1000000>;;packets per second";
                range "10..1000000";
              }
            }
            leaf packets-in-burst {
              tailf:cli-drop-node-name;
              type uint32 {
                tailf:info
                  "<1-255>;;packets in burst";
                range "1..255";
              }
            }
          }
          container mac-security {
            tailf:info
              "Mac security traffics";
            tailf:cli-compact-syntax;
            tailf:cli-sequence-commands {
              tailf:cli-reset-siblings;
            }
            leaf packets-per-second {
              tailf:cli-drop-node-name;
              type uint32 {
                tailf:info
                  "<10-1000000>;;packets per second";
                range "10..1000000";
              }
            }
            leaf packets-in-burst {
              tailf:cli-drop-node-name;
              type uint32 {
                tailf:info
                  "<1-255>;;packets in burst";
                range "1..255";
              }
            }
          }
        }
      }
      container verify {
        tailf:info
          "enable hardware packet parsing error checks";
        container ip {
          tailf:info
            "check on IP packets";
          leaf checksum {
            tailf:info
              "check for packet checksum errors";
            tailf:cli-boolean-no;
            type boolean;
            default "true";
          }
          container length {
            tailf:info
              "check for packet length errors";
            leaf consistent {
              tailf:info
                "check length in header against physical frame length";
              tailf:cli-boolean-no;
              tailf:cli-full-command;
              type boolean;
              default "true";
            }
            leaf minimum {
              tailf:info
                "check for minimum packet length";
              tailf:cli-boolean-no;
              type boolean;
              default "true";
            }
          }
          leaf same-address {
            tailf:info
              "check for packet having equal source and destination IP addresses";
            type empty;
          }
          leaf syslog {
            tailf:info
              "syslog packet parse errors";
            type empty;
          }
        }
      }
      container mpls {
        tailf:info
          "configure global MPLS params";
        leaf tunnel-recir {
          tailf:info
            "Recirculate Tunnel packets";
          type empty;
        }
      }
    }
    container policer {
      tailf:ncs-device-type "cli-ned";
      tailf:display-when "not(../../ncs:module) or ../../ncs:module[ncs:name='tailf-ned-cisco-ios']";
      tailf:info
        "Switch policer";
      list aggregate {
        tailf:info
          "Named aggregate policer";
        tailf:cli-suppress-mode;
        tailf:cli-delete-when-empty;
        tailf:cli-compact-syntax;
        tailf:cli-sequence-commands {
          tailf:cli-reset-siblings;
        }
        key "name";
        leaf name {
          type string {
            tailf:info
              "WORD;;aggregate policer Name";
          }
        }
        leaf cir {
          tailf:info
            "Committed information rate";
          type uint32 {
            tailf:info
              "<8000-1000000000>;;Bits per second";
            range "8000..1000000000";
          }
        }
        leaf bc {
          tailf:info
            "Conform burst";
          tailf:cli-optional-in-sequence;
          type uint32 {
            tailf:info
              "<8000-1000000000>;;Burst bytes";
            range "8000..1000000000";
          }
        }
        leaf conform-action {
          tailf:info
            "action when rate is within conform and conform + exceed burst";
          tailf:cli-optional-in-sequence;
          type empty;
        }
        leaf set-qos-transmit {
          tailf:info
            "set qos-group and send it";
          when "../conform-action" {
            tailf:xpath-root 3;
            tailf:dependency "../conform-action";
          }
          tailf:cli-optional-in-sequence;
          type uint8 {
            tailf:info
              "<0-99>;;new qos-group";
            range "0..99";
          }
        }
        leaf set-dot1ad-dei-transmit {
          tailf:info
            "set dei and send it";
          when "../conform-action" {
            tailf:xpath-root 3;
            tailf:dependency "../conform-action";
          }
          tailf:cli-optional-in-sequence;
          type uint8 {
            tailf:info
              "<0-1>;;new dei value";
            range "0..1";
          }
        }
        leaf set-prec-transmit {
          tailf:info
            "rewrite packet precedence and send it";
          when "../conform-action" {
            tailf:xpath-root 3;
            tailf:dependency "../conform-action";
          }
          tailf:cli-optional-in-sequence;
          type prec_value-type;
        }
        container set-prec-transmit-table {
          when "../set-prec-transmit" {
            tailf:xpath-root 3;
            tailf:dependency "../set-prec-transmit";
          }
          tailf:cli-no-keyword;
          tailf:cli-drop-node-name;
          tailf:cli-optional-in-sequence;
          tailf:cli-flatten-container;
          leaf table {
            tailf:info
              "Set packet cos from cos based on table map";
            tailf:cli-optional-in-sequence;
            tailf:non-strict-leafref {
              path "../../../../table-map/name";
            }
            type string {
              tailf:info
                "WORD;;table-map name";
            }
          }
        }
        leaf set-dscp-transmit {
          tailf:info
            "set dscp and send it";
          when "../conform-action" {
            tailf:xpath-root 3;
            tailf:dependency "../conform-action";
          }
          tailf:cli-optional-in-sequence;
          type dscp-type;
        }
        container set-dscp-transmit-table {
          when "../set-dscp-transmit" {
            tailf:xpath-root 3;
            tailf:dependency "../set-dscp-transmit";
          }
          tailf:cli-no-keyword;
          tailf:cli-drop-node-name;
          tailf:cli-optional-in-sequence;
          tailf:cli-flatten-container;
          leaf table {
            tailf:info
              "Set packet cos from cos based on table map";
            tailf:cli-optional-in-sequence;
            tailf:non-strict-leafref {
              path "../../../../table-map/name";
            }
            type string {
              tailf:info
                "WORD;;table-map name";
            }
          }
        }
        leaf set-cos-transmit {
          tailf:info
            "set cos and send it";
          when "../conform-action" {
            tailf:xpath-root 3;
            tailf:dependency "../conform-action";
          }
          tailf:cli-optional-in-sequence;
          type cos_value-type;
        }
        container set-cos-transmit-table {
          when "../set-cos-transmit" {
            tailf:xpath-root 3;
            tailf:dependency "../set-cos-transmit";
          }
          tailf:cli-no-keyword;
          tailf:cli-drop-node-name;
          tailf:cli-optional-in-sequence;
          tailf:cli-flatten-container;
          leaf table {
            tailf:info
              "Set packet cos from cos based on table map";
            tailf:cli-optional-in-sequence;
            tailf:non-strict-leafref {
              path "../../../../table-map/name";
            }
            type string {
              tailf:info
                "WORD;;table-map name";
            }
          }
        }
        leaf transmit {
          tailf:info
            "transmit packet";
          when "../conform-action" {
            tailf:xpath-root 3;
            tailf:dependency "../conform-action";
          }
          tailf:cli-optional-in-sequence;
          type empty;
        }
        leaf exceed-action {
          tailf:info
            "action when rate is within conform and conform + exceed burst";
          type empty;
        }
        leaf drop {
          tailf:info
            "drop packet";
          when "../exceed-action" {
            tailf:xpath-root 3;
            tailf:dependency "../exceed-action";
          }
          tailf:cli-optional-in-sequence;
          tailf:cli-full-command;
          type empty;
        }
        container exceed-transmit {
          tailf:cli-no-keyword;
          tailf:cli-drop-node-name;
          tailf:cli-optional-in-sequence;
          tailf:cli-flatten-container;
          leaf transmit {
            tailf:info
              "transmit packet";
            when "../../exceed-action" {
              tailf:xpath-root 3;
              tailf:dependency "../../exceed-action";
            }
            tailf:cli-optional-in-sequence;
            type empty;
          }
        }
      }
    }
    container redundancy {
      tailf:ncs-device-type "cli-ned";
      tailf:display-when "not(../../ncs:module) or ../../ncs:module[ncs:name='tailf-ned-cisco-ios']";
      tailf:info
        "Enter redundancy mode";
      tailf:cli-add-mode;
      tailf:cli-mode-name "config-red";
      presence "true";
      leaf maintenance-mode {
        tailf:info
          "Enable/Disable maintenance mode ";
        type empty;
      }
      leaf mode {
        tailf:info
          "redundancy mode for this chassis";
        type enumeration {
          enum "rpr" {
            tailf:info
              "Route Processor Redundancy";
          }
          enum "rpr-plus" {
            tailf:info
              "Route Processor Redundancy Plus";
          }
          enum "sso" {
            tailf:info
              "Stateful Switchover";
          }
          enum "none" {
            tailf:info
              "None";
          }
        }
      }
      list linecard-group {
        tailf:info
          "Enter linecard redundancy submode";
        tailf:cli-mode-name "config-red-lc";
        tailf:cli-incomplete-command;
        tailf:cli-recursive-delete;
        key "id";
        leaf id {
          type uint32 {
            tailf:info
              "ID;;linecard-group identifier";
          }
        }
        leaf cable {
          tailf:info
            "CMTS LC Redundancy type";
          tailf:cli-hide-in-submode;
          tailf:cli-full-command;
          type empty;
        }
        leaf internal-switch {
          tailf:info
            "Internal Switch Redundancy type";
          tailf:cli-hide-in-submode;
          tailf:cli-full-command;
          type empty;
        }
        leaf description {
          tailf:info
            "Assign linecard group description";
          tailf:cli-multi-value;
          tailf:cli-preformatted;
          tailf:cli-full-command;
          type string {
            tailf:info
              "LINE;;Linecard group description";
          }
        }
        leaf class {
          tailf:info
            "assign a class (1:N, 1:1) to this group";
          tailf:cli-full-command;
          type enumeration {
            enum "1:1" {
              tailf:info
                "One to One Class";
            }
            enum "1:N" {
              tailf:info
                "One to N Class";
            }
          }
        }
        container reserve {
          tailf:info
            "Reserve card type for redundancy group";
          leaf cardtype {
            tailf:info
              "Reserve card type for redundancy group";
            type string {
              tailf:info
                "<0-4294967295>;;Enter reserve cardtype in Hex or Decimal";
            }
          }
        }
        container rf-switch {
          tailf:info
            "Specify/Change RF-switch parameters (Optional Command)";
          leaf snmp-community {
            tailf:info
              "SNMP community name";
            type string {
              tailf:info
                "WORD;;snmp community name";
            }
          }
        }
        container member {
          tailf:info
            "Add or remove a member from this LC redundancy";
          list slot {
            tailf:info
              "slot number to be added or removed from this linecard group";
            tailf:cli-suppress-mode;
            tailf:cli-delete-when-empty;
            tailf:cli-compact-syntax;
            tailf:cli-incomplete-command;
            key "id";
            leaf id {
              type uint8 {
                tailf:info
                  "<3-12>;;primary/secondary slot number";
                range "3..12";
              }
            }
            choice primary-secondary-choice {
              leaf primary {
                tailf:info
                  "primary slot of the linecard group";
                type empty;
              }
              leaf secondary {
                tailf:info
                  "secondary slot of the linecard group";
                type empty;
              }
            }
          }
          list subslot {
            tailf:info
              "subslot number to be added or removed from this linecard group";
            tailf:cli-suppress-mode;
            tailf:cli-delete-when-empty;
            tailf:cli-incomplete-command;
            tailf:cli-compact-syntax;
            tailf:cli-suppress-list-no;
            key "id";
            leaf id {
              type string {
                tailf:info
                  "<5-8>/<0-1>";
              }
            }
            leaf working {
              tailf:info
                "working slot in this linecard group";
              type empty;
            }
            container protect {
              tailf:info
                "protect slot of this linecard group";
              tailf:cli-display-separated;
              presence "true";
              choice config-choice {
                leaf config {
                  tailf:info
                    "Specifiy the subslot for cable upstream config";
                  tailf:cli-incomplete-no;
                  type string {
                    tailf:info
                      "<5-8>/<0-1>;;Slot/Subslot";
                  }
                }
                container no-config {
                  tailf:cli-drop-node-name;
                  leaf config {
                    tailf:cli-boolean-no;
                    tailf:cli-full-command;
                    type boolean;
                    default "true";
                  }
                }
              }
            }
          }
        }
        container conf {
          tailf:cli-drop-node-name;
          leaf revertive {
            tailf:info
              "Make redundancy relationship revertive";
            type empty;
          }
        }
      }
      container main-cpu {
        tailf:info
          "Enter main-cpu mode";
        tailf:cli-add-mode;
        tailf:cli-mode-name "config-r-mc";
        container auto-sync {
          tailf:info
            "Sync elements";
          leaf running-config {
            type empty;
          }
          leaf config-register {
            type empty;
          }
          leaf bootvar {
            type empty;
          }
          leaf startup-config {
            type empty;
          }
          leaf standard {
            type empty;
          }
        }
        container switchover {
          tailf:info
            "Configuration of switchover";
          container pxf {
            tailf:info
              "PXF switchover options";
            container restart {
              tailf:info
                "PXF restarts";
              tailf:cli-compact-syntax;
              tailf:cli-sequence-commands;
              leaf number-of-crashes {
                tailf:cli-drop-node-name;
                tailf:cli-incomplete-command;
                type uint8 {
                  tailf:info
                    "<1-25>;;Number of PXF restarts before a switchover";
                  range "1..25";
                }
              }
              leaf time-period {
                tailf:cli-drop-node-name;
                type uint8 {
                  tailf:info
                    "<0-120>;;Interval (in hours) over which restart count is accumulated";
                  range "0..120";
                }
              }
            }
          }
        }
      }
      container interchassis {
        tailf:info
          "Enter interchassis mode";
        list group {
          tailf:info
            "Enter the redundancy group number";
          tailf:cli-mode-name "conppfig-r-ic";
          key "id";
          leaf id {
            type uint32 {
              tailf:info
                "<1-4294967295>;;The redundancy group number";
              range "1..4294967295";
            }
          }
          container member {
            tailf:info
              "specify a redundancy group member";
            leaf ip {
              tailf:info
                "specify the redundancy group member using an ip address";
              type inet:ipv4-address {
                tailf:info
                  "A.B.C.D;;the ip address of the remote redundancy group member";
              }
            }
          }
          container mlacp {
            tailf:info
              "mLACP interchassis redundancy group subcommands";
            leaf system-mac {
              tailf:info
                "mLACP redundancy group mac address";
              type string {
                tailf:info
                  "H.H.H;;mLACP redundancy group mac address";
              }
            }
            leaf system-priority {
              tailf:info
                "mLACP system priority";
              type uint16 {
                tailf:info
                  "<0-65535>;;Priority value";
              }
            }
            leaf node-id {
              tailf:info
                "mLACP node-id, appended to LACP port ids";
              type uint8 {
                tailf:info
                  "<0-7>;;mLACP node-id";
                range "0..7";
              }
            }
          }
        }
      }
    }
    container bfd-template {
      tailf:ncs-device-type "cli-ned";
      tailf:display-when "not(../../ncs:module) or ../../ncs:module[ncs:name='tailf-ned-cisco-ios']";
      tailf:info
        "BFD template configuration";
      list single-hop {
        tailf:info
          "Single-hop template";
        tailf:cli-mode-name "config-bfd";
        key "name";
        leaf name {
          type string {
            tailf:info
              "WORD;;BFD template name";
          }
        }
        container interval {
          tailf:info
            "Transmit interval between BFD packets";
          tailf:cli-compact-syntax;
          tailf:cli-sequence-commands {
            tailf:cli-reset-siblings;
          }
          leaf min-tx {
            tailf:info
              "Minimum transmit interval capability";
            tailf:cli-incomplete-command;
            type uint16 {
              tailf:info
                "<4-999>;;Milliseconds";
              range "4..999";
            }
          }
          leaf min-rx {
            tailf:info
              "Minimum receive interval capability";
            tailf:code-name "bfd-template-min-rx";
            type uint16 {
              tailf:info
                "<4-999>;;Milliseconds";
              range "4..999";
            }
          }
          leaf multiplier {
            tailf:info
              "Multiplier value used to compute holddown";
            type uint8 {
              tailf:info
                "<3-50>;;value used to multiply the interval";
              range "3..50";
            }
          }
        }
      }
    }
    leaf process-max-time {
      tailf:ncs-device-type "cli-ned";
      tailf:display-when "not(../../ncs:module) or ../../ncs:module[ncs:name='tailf-ned-cisco-ios']";
      tailf:info
        "Maximum time for process to run before voluntarily relinquishing processor";
      type uint8 {
        tailf:info
          "<20-200>;;The number of millisecs before voluntary suspend";
        range "20..200";
      }
    }
    container map-class {
      tailf:ncs-device-type "cli-ned";
      tailf:display-when "not(../../ncs:module) or ../../ncs:module[ncs:name='tailf-ned-cisco-ios']";
      tailf:info
        "Configure static map class";
      list frame-relay {
        tailf:info
          "Frame Relay";
        tailf:cli-mode-name "config-map-class";
        key "name";
        leaf name {
          type string {
            tailf:info
              "WORD;;Static map class name";
          }
        }
        container frame-relay {
          tailf:info
            "Configure Map parameters";
          leaf fragment {
            tailf:info
              "Requires Frame Relay traffic-shaping to be configured at the interface level";
            type uint16 {
              tailf:info
                "<16-1600>;;Define fragment size, Bytes";
              range "16..1600";
            }
          }
        }
        container service-policy {
          tailf:info
            "class-based service policy";
          uses service-policy-grouping;
        }
      }
    }
    container class {
      tailf:ncs-device-type "cli-ned";
      tailf:display-when "not(../../ncs:module) or ../../ncs:module[ncs:name='tailf-ned-cisco-ios']";
      tailf:info
        "Configure cem class parameters";
      list cem {
        tailf:info
          "Circuit emulation template";
        tailf:cli-mode-name "config-cem-class";
        key "name";
        leaf name {
          type string {
            tailf:info
              "WORD;;cem class name";
          }
        }
        leaf payload-size {
          tailf:info
            "IP payload size in bytes";
          type uint16 {
            tailf:info
              "<32-1312>;;IP payload size";
            range "32..1312";
          }
        }
        leaf dejitter-buffer {
          tailf:info
            "dejitter in ms";
          type uint16 {
            tailf:info
              "<1-500>;;1-500ms";
            range "1..500";
          }
        }
        leaf idle-pattern {
          tailf:info
            "Set 8 bit idle pattern";
          type string {
            tailf:info
              "<0x0-0xFF>;;8 bit hex number";
          }
        }
      }
    }
    list class-map {
      tailf:ncs-device-type "cli-ned";
      tailf:display-when "not(../ncs:module) or ../ncs:module[ncs:name='tailf-ned-cisco-ios']";
      tailf:info
        "Configure QoS Class Map";
      tailf:cli-mode-name "config-cmap";
      tailf:cli-no-key-completion;
      tailf:cli-compact-syntax;
      tailf:cli-sequence-commands;
      tailf:cli-full-command;
      tailf:cli-diff-dependency "../mls" {
        tailf:xpath-root 3;
      }
      key "name";
      leaf name {
        tailf:cli-disallow-value "type|match-any|match-all";
        type string {
          tailf:info
            "WORD;;class-map name";
        }
      }
      leaf type {
        tailf:info
          "type of the class-map";
        tailf:cli-optional-in-sequence;
        tailf:cli-prefix-key;
        tailf:cli-incomplete-command;
        type enumeration {
          enum "access-control" {
            tailf:info
              "access-control specific class-map";
          }
          enum "inspect" {
            tailf:info
              "Configure Firewall Class Map";
          }
          enum "logging" {
            tailf:info
              "Class map for control-plane packet logging";
          }
          enum "port-filter" {
            tailf:info
              "Class map for port filter";
          }
          enum "queue-threshold" {
            tailf:info
              "Class map for queue threshold";
          }
          enum "stack" {
            tailf:info
              "class-map for protocol header stack specification";
          }
          enum "traffic" {
            tailf:info
              "Configure a subscriber policy traffic classmap";
          }
          enum "appnav" {
            tailf:info
              "Configure a APPNAV Class Map";
          }
          enum "multicast-flows" {
            tailf:info
              "multicast class-maps";
          }
        }
      }
      leaf protocol {
        when "(../type) and (../type = 'inspect')" {
          tailf:xpath-root 3;
          tailf:dependency "../type";
        }
        tailf:cli-drop-node-name;
        tailf:cli-prefix-key;
        tailf:cli-optional-in-sequence;
        tailf:cli-incomplete-command;
        type enumeration {
          enum "aol" {
            tailf:info
              "Configure CBAC class-map for IM-AOL protocol";
          }
          enum "edonkey" {
            tailf:info
              "eDonkey";
          }
          enum "fasttrack" {
            tailf:info
              "FastTrack Traffic - KaZaA, Morpheus, Grokster...";
          }
          enum "gnutella" {
            tailf:info
              "Gnutella Version2 Traffic - BearShare, Shareeza, Morpheus ...";
          }
          enum "http" {
            tailf:info
              "Configure CBAC class-map for HTTP protocol";
          }
          enum "imap" {
            tailf:info
              "Configure CBAC class-map for IMAP protocol";
          }
          enum "kazaa2" {
            tailf:info
              "Kazaa Version 2";
          }
          enum "msnmsgr" {
            tailf:info
              "Configure CBAC class-map for IM-MSN protocol";
          }
          enum "pop3" {
            tailf:info
              "Configure CBAC class-map for POP3 protocol";
          }
          enum "smtp" {
            tailf:info
              "Configure CBAC class-map for SMTP protocol";
          }
          enum "sunrpc" {
            tailf:info
              "Configure CBAC class-map for RPC protocol";
          }
          enum "ymsgr" {
            tailf:info
              "Configure CBAC class-map for IM-YAHOO protocol";
          }
        }
      }
      leaf prematch {
        tailf:cli-drop-node-name;
        tailf:cli-no-keyword;
        tailf:cli-prefix-key;
        type enumeration {
          enum "match-all" {
            tailf:info
              "Logical-AND all matching statements under this classmap";
          }
          enum "match-any" {
            tailf:info
              "Logical-OR all matching statements under this classmap";
          }
        }
      }
      leaf description {
        tailf:info
          "Class-Map description";
        tailf:cli-break-sequence-commands;
        tailf:cli-multi-value;
        tailf:cli-preformatted;
        tailf:cli-full-command;
        type string {
          tailf:info
            "LINE;;Description of this class-map (up to 200 characters)";
        }
      }
      container match {
        tailf:info
          "classification criteria";
        uses class-map-match-grouping;
        container not {
          tailf:info
            "Negate this match result";
          uses class-map-match-grouping;
        }
      }
    }
    container class-map-filter-control {
      tailf:ncs-device-type "cli-ned";
      tailf:display-when "not(../../ncs:module) or ../../ncs:module[ncs:name='tailf-ned-cisco-ios']";
      tailf:cli-drop-node-name;
      list class-map {
        tailf:info
          "Configure QoS Class Map";
        tailf:cli-mode-name "config-filter-control-classmap";
        tailf:cli-suppress-list-no;
        tailf:cli-no-key-completion;
        tailf:cli-compact-syntax;
        tailf:cli-sequence-commands;
        tailf:cli-full-command;
        key "name";
        leaf name {
          type string {
            tailf:info
              "WORD;;class-map name";
          }
        }
        leaf type {
          tailf:info
            "type of the policy-map";
          tailf:cli-prefix-key;
          type enumeration {
            enum "control" {
              tailf:info
                "Configure control policies";
            }
          }
        }
        leaf domain {
          tailf:cli-drop-node-name;
          tailf:cli-prefix-key;
          type enumeration {
            enum "subscriber" {
              tailf:info
                "Domain name of the class map";
            }
          }
        }
        leaf prematch {
          tailf:cli-drop-node-name;
          tailf:cli-prefix-key;
          type enumeration {
            enum "match-all" {
              tailf:info
                "TRUE if everything matches in the class-map";
            }
            enum "match-any" {
              tailf:info
                "TRUE if anything matches in the class-map";
            }
            enum "match-none" {
              tailf:info
                "TRUE if nothing matches in the class-map";
            }
          }
        }
        container match {
          tailf:info
            "match filter";
          container method {
            tailf:info
              "match the type of authentication method from an event";
            leaf webauth {
              tailf:info
                "webauth";
              type empty;
            }
            leaf mab {
              tailf:info
                "mab";
              type empty;
            }
            leaf dot1x {
              tailf:info
                "dot1x";
              type empty;
            }
          }
          container result-type {
            tailf:info
              "match the result type, optionally for a specific method";
            container method {
              tailf:info
                "match the result of a particular method";
              container dot1x {
                tailf:info
                  "dot1x result";
                uses result-type-method-grouping;
              }
              container mab {
                tailf:info
                  "mab result";
                uses result-type-method-grouping;
              }
              container webauth {
                tailf:info
                  "webauth result";
                uses result-type-method-grouping;
              }
            }
          }
        }
      }
    }
    list policy-map {
      tailf:ncs-device-type "cli-ned";
      tailf:display-when "not(../ncs:module) or ../ncs:module[ncs:name='tailf-ned-cisco-ios']";
      tailf:info
        "Configure QoS Policy Map";
      tailf:cli-mode-name "config-pmap";
      tailf:cli-diff-dependency "../mls/qos/aggregate-policer" {
        tailf:xpath-root 3;
      }
      tailf:cli-diff-dependency "../policer/aggregate" {
        tailf:xpath-root 3;
      }
      tailf:cli-diff-dependency "../tailfned/police" {
        tailf:xpath-root 3;
      }
      key "name";
      leaf name {
        tailf:cli-disallow-value "(type)|(http)|(im)|(imap)|(p2p)|(pop3)|(smtp)|(sunrpc)";
        type string {
          tailf:info
            "WORD;;policy-map name";
        }
      }
      leaf type {
        tailf:info
          "type of the policy-map";
        tailf:cli-prefix-key;
        type enumeration {
          enum "inspect" {
            tailf:info
              "Configure Firewall Policy Map";
          }
          enum "performance-monitor" {
            tailf:info
              "Performance monitoring policy-map type";
          }
          enum "mace" {
            tailf:info
              "Configure MACE Policy Map";
          }
          enum "packet-service" {
            tailf:info
              "Configure Packet Service Policy Map";
          }
          enum "appnav" {
            tailf:info
              "Configure a APPNAV Policy Map";
          }
        }
      }
      leaf protocol {
        tailf:cli-drop-node-name;
        tailf:cli-prefix-key;
        type enumeration {
          enum "http" {
            tailf:info
              "Configure CBAC policy-map for HTTP protocol";
          }
          enum "im" {
            tailf:info
              "Configure CBAC policy-map for IM protocol";
          }
          enum "imap" {
            tailf:info
              "Configure CBAC policy-map for IMAP protocol";
          }
          enum "p2p" {
            tailf:info
              "Configure CBAC policy-map for P2P protocols";
          }
          enum "pop3" {
            tailf:info
              "Configure CBAC policy-map for POP3 protocol";
          }
          enum "smtp" {
            tailf:info
              "Configure CBAC policy-map for SMTP protocol";
          }
          enum "sunrpc" {
            tailf:info
              "Configure CBAC policy-map for RPC protocol";
          }
        }
      }
      leaf description {
        tailf:info
          "Policy-Map description";
        tailf:cli-multi-value;
        tailf:cli-preformatted;
        tailf:cli-full-command;
        type string {
          tailf:info
            "LINE;;Description of this policy-map (up to 200 characters)";
          length "1..200";
        }
      }
      list class {
        tailf:info
          "policy criteria";
        tailf:cli-mode-name "config-pmap-c";
        tailf:cli-show-long-obu-diffs;
        tailf:cli-diff-dependency "../../class-map" {
          tailf:xpath-root 3;
        }
        ordered-by user;
        key "name";
        leaf type {
          tailf:info
            "type of the class-map";
          tailf:cli-prefix-key;
          type enumeration {
            enum "inspect" {
              tailf:info
                "Configure CBAC Class Map";
            }
          }
        }
        leaf name {
          tailf:cli-disallow-value "type|class-default";
          tailf:non-strict-leafref {
            path "../../../class-map/name";
          }
          type string {
            tailf:info
              "WORD;;class-map name";
          }
        }
        uses policy-map-class-grouping;
      }
      container class-default {
        tailf:cli-drop-node-name;
        list class {
          tailf:info
            "policy criteria";
          tailf:cli-mode-name "config-pmap-c";
          key "name";
          leaf name {
            type enumeration {
              enum "class-default" {
                tailf:info
                  "System default class matching otherwise unclassified packets";
              }
            }
          }
          uses policy-map-class-grouping;
        }
      }
    }
    container policy-map-event-control {
      tailf:ncs-device-type "cli-ned";
      tailf:display-when "not(../../ncs:module) or ../../ncs:module[ncs:name='tailf-ned-cisco-ios']";
      tailf:cli-drop-node-name;
      list policy-map {
        tailf:info
          "Configure QoS Policy Map";
        tailf:cli-mode-name "config-event-control-policymap";
        tailf:cli-sequence-commands;
        key "name";
        leaf name {
          tailf:cli-disallow-value "type";
          tailf:cli-diff-dependency "../../../class-map" {
            tailf:xpath-root 3;
          }
          tailf:cli-diff-dependency "../../../class-map-filter-control/class-map" {
            tailf:xpath-root 3;
          }
          type string {
            tailf:info
              "WORD;;policy-map name";
          }
        }
        leaf type {
          tailf:info
            "type of the policy-map";
          tailf:cli-prefix-key;
          type enumeration {
            enum "control" {
              tailf:info
                "Configure control policies";
            }
          }
        }
        leaf domain {
          tailf:cli-drop-node-name;
          tailf:cli-prefix-key;
          type enumeration {
            enum "subscriber" {
              tailf:info
                "subscriber control policy domain";
            }
          }
        }
        list event {
          tailf:info
            "The event type this control class-map triggers upon";
          tailf:cli-mode-name "config-class-control-policymap";
          tailf:cli-show-long-obu-diffs;
          ordered-by user;
          key "name match";
          leaf name {
            tailf:cli-suppress-range;
            type enumeration {
              enum "aaa-available" {
                tailf:info
                  "aaa-available event";
              }
              enum "absolute-timeout" {
                tailf:info
                  "absolute timeout event";
              }
              enum "agent-found" {
                tailf:info
                  "agent found event";
              }
              enum "authentication-failure" {
                tailf:info
                  "authentication failure event";
              }
              enum "authentication-success" {
                tailf:info
                  "authentication success event";
              }
              enum "authorization-failure" {
                tailf:info
                  "authorization failure event";
              }
              enum "authorization-success" {
                tailf:info
                  "authorization success event";
              }
              enum "identity-update" {
                tailf:info
                  "identity update event";
              }
              enum "inactivity-timeout" {
                tailf:info
                  "inactivity timeout event";
              }
              enum "remote-authentication-failure" {
                tailf:info
                  "authentication failure event";
              }
              enum "remote-authentication-success" {
                tailf:info
                  "authentication remote success event";
              }
              enum "session-disconnected" {
                tailf:info
                  "session disconnected event";
              }
              enum "session-started" {
                tailf:info
                  "session started event";
              }
              enum "tag-added" {
                tailf:info
                  "tag to apply event";
              }
              enum "tag-removed" {
                tailf:info
                  "tag to remove event";
              }
              enum "template-activated" {
                tailf:info
                  "template activated event";
              }
              enum "template-activation-failed" {
                tailf:info
                  "template activation failed event";
              }
              enum "template-deactivated" {
                tailf:info
                  "template deactivated event";
              }
              enum "template-deactivation-failed" {
                tailf:info
                  "template deactivation failed event";
              }
              enum "timer-expiry" {
                tailf:info
                  "timer-expiry event";
              }
              enum "violation" {
                tailf:info
                  "session violation event";
              }
            }
          }
          leaf match {
            tailf:key-default "match-all";
            type enumeration {
              enum "match-all" {
                tailf:info
                  "Evaluate all the classes";
              }
              enum "match-first" {
                tailf:info
                  "Evaluate the first class";
              }
            }
          }
          list class-list {
            tailf:cli-drop-node-name;
            tailf:cli-mode-name "config-class-control-policymap";
            tailf:cli-incomplete-command;
            key "id";
            leaf id {
              type uint8 {
                tailf:info
                  "<1-254>;;class number, 1 for 1st class, 2 for 2nd...";
              }
            }
            leaf class {
              tailf:info
                "The class type this control policy-map triggers upon";
              tailf:cli-hide-in-submode;
              type union {
                type string {
                  tailf:info
                    "WORD;;Name of control class-map to reference";
                }
                type enumeration {
                  enum "always" {
                    tailf:info
                      "This control class-map always matches";
                  }
                }
              }
            }
            leaf execute {
              tailf:cli-drop-node-name;
              tailf:cli-hide-in-submode;
              type enumeration {
                enum "do-all" {
                  tailf:info
                    "Execute all the actions";
                }
                enum "do-until-failure" {
                  tailf:info
                    "Execute actions until one of them fails";
                }
                enum "do-until-success" {
                  tailf:info
                    "Execute actions until one of them is successful";
                }
              }
            }
            list action-list {
              tailf:cli-drop-node-name;
              tailf:cli-suppress-mode;
              tailf:cli-delete-when-empty;
              tailf:cli-compact-syntax;
              tailf:cli-sequence-commands {
                tailf:cli-reset-siblings;
              }
              tailf:cli-incomplete-command;
              key "id";
              leaf id {
                type uint8 {
                  tailf:info
                    "<1-254>;;action number, 1 for 1st action, 2 for 2nd...";
                }
              }
              leaf action {
                tailf:cli-drop-node-name;
                type enumeration {
                  enum "activate" {
                    tailf:info
                      "activate template or policy ";
                  }
                  enum "authenticate" {
                    tailf:info
                      "authenticate a session";
                  }
                  enum "authentication-restart";
                  enum "authorize" {
                    tailf:info
                      "authorize session";
                  }
                  enum "notify" {
                    tailf:info
                      "notifies the session attributes";
                  }
                  enum "set-domain" {
                    tailf:info
                      "set domain";
                  }
                  enum "set-timer" {
                    tailf:info
                      "set abs timer to pop N seconds from now";
                  }
                  enum "unauthorize" {
                    tailf:info
                      "unauthorize session";
                  }
                  enum "terminate";
                }
              }
              leaf action-string {
                tailf:cli-drop-node-name;
                tailf:cli-multi-value;
                type string {
                  tailf:info
                    "WORD;;action string";
                }
              }
            }
          }
        }
      }
    }
    container dot11 {
      tailf:ncs-device-type "cli-ned";
      tailf:display-when "not(../../ncs:module) or ../../ncs:module[ncs:name='tailf-ned-cisco-ios']";
      tailf:info
        "IEEE 802.11 config commands";
      leaf syslog {
        tailf:info
          "Enable syslog";
        tailf:cli-show-no;
        tailf:cli-full-command;
        type empty;
      }
      list ssid {
        tailf:info
          "Configure radio service set parameters";
        tailf:cli-mode-name "config-ssid";
        key "id";
        leaf id {
          type string {
            tailf:info
              "LINE;;radio Service Set ID (Up to 32 characters";
            length "0..32";
          }
        }
        leaf vlan {
          tailf:info
            "bind ssid to vlan";
          tailf:cli-full-command;
          type string {
            tailf:info
              "WORD;;vlan ID number or name string";
          }
        }
        container authentication {
          tailf:info
            "authentication method";
          container open {
            tailf:info
              "open method";
            tailf:cli-delete-when-empty;
            tailf:cli-compact-syntax;
            tailf:cli-reset-container;
            presence "true";
            choice open-choice {
              leaf mac-address {
                tailf:info
                  "mac-address authentication method";
                type string {
                  tailf:info
                    "WORD;;mac address list-name (1 -- 31 characters)";
                }
              }
              leaf eap {
                tailf:info
                  "eap method";
                type string {
                  tailf:info
                    "WORD;;eap list name (1 -- 31 characters)";
                }
              }
            }
          }
          leaf network-eap {
            tailf:info
              "leap method";
            tailf:cli-full-command;
            type string {
              tailf:info
                "WORD;;leap list name (1 -- 31 characters)";
            }
          }
          container key-management {
            tailf:info
              "key management";
            container wpa {
              tailf:info
                "allow WPA clients";
              tailf:cli-delete-when-empty;
              tailf:cli-compact-syntax;
              tailf:cli-reset-container;
              presence "true";
              leaf version {
                tailf:info
                  "Specify WPA version";
                type enumeration {
                  enum "1" {
                    tailf:info
                      "WPA version 1";
                  }
                  enum "2" {
                    tailf:info
                      "WPA version 2";
                  }
                }
              }
              leaf optional {
                tailf:info
                  "allow legacy clients";
                type empty;
              }
            }
          }
        }
        leaf guest-mode {
          tailf:info
            "guest ssid";
          tailf:cli-full-command;
          type empty;
        }
        container mbssid {
          tailf:info
            "Multiple BSSID";
          leaf guest-mode {
            tailf:info
              "guest ssid";
            type empty;
          }
        }
        container wpa-psk {
          tailf:info
            "Configure Wi-Fi Protected Access pre-shared key";
          choice wpa-psk-choice {
            container ascii {
              tailf:info
                "Key entered as ascii chars";
              tailf:cli-compact-syntax;
              tailf:cli-sequence-commands;
              uses password-grouping;
            }
            container hex {
              tailf:info
                "Key entered as hex chars";
              tailf:cli-compact-syntax;
              tailf:cli-sequence-commands;
              uses password-grouping;
            }
          }
        }
      }
      container arp-cache {
        tailf:info
          "Enable DOT11 ARP cache";
        tailf:cli-delete-when-empty;
        presence "true";
        leaf optional {
          tailf:info
            "Disable ARP Cache until all associated client IP addresses are learned";
          type empty;
        }
      }
    }
    container bridge {
      tailf:ncs-device-type "cli-ned";
      tailf:display-when "not(../../ncs:module) or ../../ncs:module[ncs:name='tailf-ned-cisco-ios']";
      tailf:info
        "Bridge Group.";
      leaf irb {
        tailf:info
          "Integrated routing and bridging";
        tailf:cli-full-command;
        type empty;
      }
      list bridge-list {
        tailf:cli-drop-node-name;
        tailf:cli-suppress-mode;
        tailf:cli-delete-when-empty;
        tailf:cli-incomplete-command;
        key "id";
        leaf id {
          type uint8 {
            tailf:info
              "<1-255>;;Bridge Group number for Bridging.";
            range "1..255";
          }
        }
        leaf protocol {
          tailf:info
            "Specify spanning tree protocol";
          type enumeration {
            enum "dec" {
              tailf:info
                "DEC protocol";
            }
            enum "ibm" {
              tailf:info
                "IBM protocol";
            }
            enum "ieee" {
              tailf:info
                "IEEE 802.1 protocol";
            }
            enum "vlan-bridge" {
              tailf:info
                "vlan-bridge protocol";
            }
          }
        }
        container route {
          tailf:info
            "Specify a protocol to be routed in this bridge group";
          leaf ip {
            tailf:info
              "IP";
            type empty;
          }
        }
      }
    }
    container bridge-domain {
      tailf:ncs-device-type "cli-ned";
      tailf:display-when "not(../../ncs:module) or ../../ncs:module[ncs:name='tailf-ned-cisco-ios']";
      tailf:info
        "Bridge-domain global configuration commands";
      list bridge-domain-list {
        tailf:cli-drop-node-name;
        tailf:cli-mode-name "config-bdomain";
        tailf:cli-full-command;
        tailf:cli-diff-dependency "../../vlan/vlan-list" {
          tailf:xpath-root 3;
        }
        key "id";
        leaf id {
          type uint16 {
            tailf:info
              "<1-16384>;;bridge-domain ID";
            range "1..16384";
          }
        }
        container member {
          tailf:info
            "bridge-domain member";
          leaf vfi {
            tailf:info
              "Configure the Virtual Forwarding Instance (VFI) member";
            tailf:non-strict-leafref {
              path "../../../../l2vpn-vfi/l2vpn/vfi/context/name";
            }
            type string {
              tailf:info
                "WORD;;Enter VFI name (Max Size 31)";
            }
          }
          list interface-list {
            tailf:cli-drop-node-name;
            tailf:cli-suppress-mode;
            tailf:cli-delete-when-empty;
            key "name service-instance";
            leaf name {
              tailf:cli-disallow-value "vfi";
              tailf:cli-diff-dependency "../../../../../interface" {
                tailf:xpath-root 3;
              }
              type string {
                tailf:info
                  "WORD;;Interface name";
              }
            }
            leaf service-instance {
              tailf:info
                "ethernet service instance";
              tailf:cli-expose-key-name;
              type uint16 {
                tailf:info
                  "<1-8000>;;Service Instance Identifier";
                range "1..8000";
              }
            }
          }
          list ip-list {
            tailf:cli-drop-node-name;
            tailf:cli-suppress-mode;
            tailf:cli-delete-when-empty;
            tailf:cli-compact-syntax;
            key "address";
            leaf address {
              type inet:ipv4-address {
                tailf:info
                  "A.B.C.D;;IP address of the peer";
              }
            }
            leaf vcid {
              tailf:cli-drop-node-name;
              tailf:cli-incomplete-command;
              type uint32 {
                tailf:info
                  "<1-4294967295>;;Enter VC ID value";
                range "1..4294967295";
              }
            }
            choice encapsulation-template-choice {
              container encapsulation {
                tailf:info
                  "Data encapsulation method";
                tailf:cli-flatten-container;
                tailf:cli-compact-syntax;
                leaf mpls {
                  tailf:info
                    "Use MPLS encapsulation";
                  type empty;
                }
              }
              leaf template {
                tailf:info
                  "Template to use for encapsulation and protocol configuration";
                type string {
                  tailf:info
                    "WORD;;template name (Max size 32)";
                }
              }
            }
          }
        }
        container mac {
          tailf:info
            "MAC Address related commands";
          container limit {
            tailf:info
              "Limit the MAC Addresses learnt";
            container maximum {
              tailf:info
                "Maximum";
              leaf addresses {
                tailf:info
                  "Addresses";
                type uint16 {
                  tailf:info
                    "<1-10000>;;Number of addresses that can be learnt";
                  range "1..10000";
                }
              }
            }
          }
          leaf aging-time {
            tailf:info
              "Set age time of mac addresses per bridge domain";
            type uint16 {
              tailf:info
                "<10-600>;;Aging time in seconds, default 300 seconds (or 1800 seconds for overlay bridge domains)";
            }
          }
        }
      }
    }
    list service-group {
      tailf:ncs-device-type "cli-ned";
      tailf:display-when "not(../ncs:module) or ../ncs:module[ncs:name='tailf-ned-cisco-ios']";
      tailf:info
        "service-group global command";
      key "id";
      leaf id {
        type uint32 {
          tailf:info
            "<1-32768>;;Service Group ID Number";
          range "1..32768";
        }
      }
      leaf description {
        tailf:cli-multi-value;
        tailf:cli-preformatted;
        tailf:cli-full-command;
        type string {
          tailf:info
            "LINE;;Description string";
        }
      }
      container service-policy {
        tailf:info
          "Configure Service Policy";
        uses service-policy-grouping;
      }
    }
    container service-instance {
      tailf:ncs-device-type "cli-ned";
      tailf:display-when "not(../../ncs:module) or ../../ncs:module[ncs:name='tailf-ned-cisco-ios']";
      tailf:info
        "Configure service-instance";
      container mdns-sd {
        tailf:info
          "Static Service MDNS configuration";
        list service {
          tailf:info
            "Provide only Service Instance Name";
          tailf:cli-mode-name "config-mdns-sd-si";
          key "name regtype domain";
          leaf name {
            type string {
              tailf:info
                "WORD;;Specify Service instance name";
            }
          }
          leaf regtype {
            tailf:cli-expose-key-name;
            type string {
              tailf:info
                "Service Type: Specify in the form or _xxx._yyy";
              pattern '_[a-z]{3}._[a-z]{3}';
            }
          }
          leaf domain {
            tailf:info
              "Domain: Specify domain";
            tailf:cli-expose-key-name;
            type string {
              tailf:info
                "WORD;;Domain";
            }
          }
          leaf target-hostname {
            tailf:info
              "Enter FQDN of target host";
            type string {
              tailf:info
                "WORD;;Enter FQDN of target host";
            }
          }
          leaf priority {
            tailf:info
              "Specify Priority";
            type uint16 {
              tailf:info
                "<0-360>;;Specify Priority for this service";
              range "0..360";
            }
          }
          leaf weight {
            tailf:info
              "Specify Weight";
            type uint16 {
              tailf:info
                "<0-360>;;Specify Weight for the service";
              range "0..360";
            }
          }
          leaf port {
            tailf:info
              "Specify Port on which service is running";
            type uint32 {
              tailf:info
                "<0-65535>;;Specify Port for the service";
              range "0..65535";
            }
          }
          leaf txt {
            tailf:info
              "Text record string with type=name pairs separated using <\\>";
            type string {
              tailf:info
                "WORD;;TEXT Record for the Service. Maximum 1024 characters";
              length "0..1024";
            }
          }
          leaf ipv4addr {
            tailf:info
              "IPV4 address";
            type inet:ipv4-address {
              tailf:info
                "A.B.C.D;;IPV4 address of service";
            }
          }
          leaf ipv6addr {
            tailf:info
              "IPV6 address";
            type inet:ipv6-address {
              tailf:info
                "X:X:X:X::X;;IPV6 address of service";
            }
          }
        }
      }
    }
    container service-insertion {
      tailf:ncs-device-type "cli-ned";
      tailf:display-when "not(../../ncs:module) or ../../ncs:module[ncs:name='tailf-ned-cisco-ios']";
      tailf:info
        "Service Insertion mode";
      tailf:cli-diff-dependency "../interface/Loopback" {
        tailf:xpath-root 3;
      }
      tailf:cli-diff-dependency "../interface/Tunnel" {
        tailf:xpath-root 3;
      }
      list service-node-group {
        tailf:info
          "service node Group";
        tailf:cli-mode-name "config-service-insertion-sng";
        key "name";
        leaf name {
          type string {
            tailf:info
              "WORD;;service node Group Name";
          }
        }
        leaf description {
          tailf:info
            "Group Description";
          tailf:cli-full-command;
          type string {
            tailf:info
              "WORD;;Group Description";
          }
        }
        list service-node {
          tailf:info
            "service node";
          tailf:cli-suppress-mode;
          tailf:cli-delete-when-empty;
          key "ip-address";
          leaf ip-address {
            type inet:ipv4-address {
              tailf:info
                "A.B.C.D;;service node IP ADDRESS";
            }
          }
        }
        leaf node-discovery {
          tailf:cli-full-command;
          type enumeration {
            enum "enable";
          }
        }
      }
      list appnav-controller-group {
        tailf:info
          "AppNav Controller Group";
        tailf:cli-mode-name "config-service-insertion-acg";
        key "name";
        leaf name {
          type string {
            tailf:info
              "WORD;;AppNav Controller Group Name";
          }
        }
        leaf description {
          tailf:info
            "Group Description";
          tailf:cli-full-command;
          type string {
            tailf:info
              "WORD;;Group Description";
          }
        }
        list appnav-controller {
          tailf:info
            "AppNav controller";
          tailf:cli-suppress-mode;
          tailf:cli-delete-when-empty;
          key "ip-address";
          leaf ip-address {
            tailf:cli-diff-dependency "/ios:interface/Loopback/ip/address/primary" {
              tailf:xpath-root 3;
              tailf:cli-trigger-on-set;
            }
            type inet:ipv4-address {
              tailf:info
                "A.B.C.D;;AppNav controller IP address";
            }
          }
        }
      }
      list service-context {
        tailf:info
          "Service Context";
        tailf:cli-mode-name "config-service-insertion-context";
        key "name";
        leaf name {
          type string {
            tailf:info
              "WORD;;service controller, e.g. waas/1";
          }
        }
        leaf appnav-controller-group {
          tailf:info
            "AppNav Controller Group";
          tailf:cli-full-command;
          tailf:non-strict-leafref {
            path "../../appnav-controller-group/name";
          }
          type string {
            tailf:info
              "WORD;;AppNav Controller Group";
          }
        }
        leaf service-node-group {
          tailf:info
            "Service node Group";
          tailf:cli-full-command;
          tailf:non-strict-leafref {
            path "../../service-node-group/name";
          }
          type string {
            tailf:info
              "WORD;;service node Group";
          }
        }
        leaf service-policy {
          tailf:info
            "Specify a service policy for the service context";
          tailf:cli-remove-before-change;
          tailf:cli-full-command;
          tailf:non-strict-leafref {
            path "../../../policy-map/name";
          }
          type string {
            tailf:info
              "WORD;;Name of the preconfigured service policy";
          }
        }
        container vrf {
          tailf:info
            "Configure forwarding table";
          choice c-type {
            leaf name {
              tailf:info
                "vrf name";
              type string {
                tailf:info
                  "WORD;;vrf name";
              }
            }
            leaf default {
              tailf:info
                "default";
              type empty;
            }
            leaf global {
              tailf:info
                "global";
              type empty;
            }
          }
        }
        leaf enable {
          tailf:info
            "service context enable";
          tailf:cli-suppress-no;
          type empty;
        }
      }
    }
    container vtp {
      tailf:ncs-device-type "cli-ned";
      tailf:display-when "not(../../ncs:module) or ../../ncs:module[ncs:name='tailf-ned-cisco-ios']";
      tailf:info
        "Configure global VTP state";
      leaf file {
        tailf:info
          "Configure IFS filesystem file where VTP configuration is stored.";
        type string {
          tailf:info
            "WORD;;The ascii name of the IFS filesystem file where VTP configuration is stored.";
        }
      }
      leaf interface {
        tailf:info
          "Configure interface as the preferred source for the VTP IP updater address.";
        tailf:cli-diff-dependency "../../interface" {
          tailf:xpath-root 3;
        }
        type string {
          tailf:info
            "WORD;;The name of the interface providing the VTP updater ID for this device.";
        }
      }
      leaf password {
        tailf:info
          "Set the password for the VTP administrative domain";
        type string {
          tailf:info
            "WORD;;The ascii password for the VTP administrative domain.";
        }
      }
      leaf pruning {
        tailf:info
          "Set the adminstrative domain to permit pruning";
        type empty;
      }
      leaf version {
        tailf:info
          "Set the adminstrative domain to VTP version";
        type uint8 {
          tailf:info
            "<1-3>;;Set the adminstrative domain VTP version number";
          range "1..3";
        }
      }
      leaf domain {
        tailf:info
          "Set the name of the VTP administrative domain.";
        type string {
          tailf:info
            "WORD;;The ascii name for the VTP administrative domain.";
        }
      }
      leaf mode {
        tailf:info
          "Configure VTP device mode";
        type enumeration {
          enum "client" {
            tailf:info
              "Set the device to client mode.";
          }
          enum "off" {
            tailf:info
              "Set the device to off mode.";
          }
          enum "server" {
            tailf:info
              "Set the device to server mode.";
          }
          enum "transparent" {
            tailf:info
              "Set the device to transparent mode.";
          }
        }
      }
    }
    container link {
      tailf:ncs-device-type "cli-ned";
      tailf:display-when "not(../../ncs:module) or ../../ncs:module[ncs:name='tailf-ned-cisco-ios']";
      tailf:info
        "Enable Link State Tracking feature";
      container state {
        tailf:info
          "Enable link state tracking feature";
        leaf-list track {
          tailf:info
            "Enable link state tracking for the group";
          tailf:cli-list-syntax;
          type uint8 {
            tailf:info
              "<1-10>;;Link state group number to trac";
            range "1..8";
          }
        }
      }
    }
    container vlan {
      tailf:ncs-device-type "cli-ned";
      tailf:display-when "not(../../ncs:module) or ../../ncs:module[ncs:name='tailf-ned-cisco-ios']";
      tailf:info
        "VLAN commands";
      choice vlan-accounting-choice {
        leaf accounting {
          tailf:info
            "VLAN accounting configuration";
          tailf:cli-boolean-no;
          tailf:cli-full-command;
          type boolean;
          default "true";
        }
        container accounting-input {
          tailf:cli-drop-node-name;
          container accounting {
            leaf input {
              tailf:cli-boolean-no;
              tailf:cli-full-command;
              type boolean;
              default "true";
            }
          }
        }
        container accounting-output {
          tailf:cli-drop-node-name;
          container accounting {
            leaf output {
              tailf:cli-boolean-no;
              tailf:cli-full-command;
              type boolean;
              default "true";
            }
          }
        }
      }
      container internal {
        tailf:info
          "internal VLAN";
        container allocation {
          tailf:info
            "internal VLAN allocation";
          leaf policy {
            type enumeration {
              enum "ascending" {
                tailf:info
                  "Allocates internal VLANs from 1006 to 4094";
              }
              enum "descending" {
                tailf:info
                  "Allocates internal VLANs from 4094 to 1006.";
              }
            }
          }
        }
      }
      container dot1q {
        tailf:info
          "dot1q parameters";
        container tag {
          tailf:info
            "tag parameters";
          leaf native {
            tailf:info
              "tag native vlan";
            type empty;
          }
        }
      }
      container access-log {
        tailf:info
          "Configure VACL logging";
        leaf maxflow {
          tailf:info
            "Set vacl logging maximum flow number";
          type uint16 {
            tailf:info
              "<0-2048>;;Maximum flow number";
            range "0..2048";
          }
        }
        leaf ratelimit {
          tailf:info
            "Set vacl logging rate limiter";
          type uint16 {
            tailf:info
              "<10-5000>;;Maximum number of packets logged per second";
            range "10..5000";
          }
        }
        leaf threshold {
          tailf:info
            "Set vacl log-update threshold";
          type uint32 {
            tailf:info
              "<0-2147483647>;;log-update threshold (number of hits)";
            range "0..2147483647";
          }
        }
      }
      list filter {
        tailf:cli-suppress-mode;
        tailf:cli-delete-when-empty;
        tailf:cli-compact-syntax;
        tailf:cli-incomplete-command;
        key "name";
        leaf name {
          type string {
            tailf:info
              "WORD;;VLAN map name";
          }
        }
        leaf-list vlan-list {
          tailf:info
            "VLANs to apply filter to";
          tailf:cli-replace-all;
          tailf:cli-range-list-syntax;
          type uint16 {
            tailf:info
              "<1-4094>;;VLAN id";
            range "1..4094";
          }
        }
      }
      list vlan-list {
        tailf:cli-drop-node-name;
        tailf:cli-mode-name "config-vlan";
        tailf:cli-range-list-syntax;
        tailf:meta-data "range-list-syntax-mode" {
          tailf:meta-value "vlan <ID>";
        }
        tailf:meta-data "max-values-mode" {
          tailf:meta-value "1 :: 32 :: ,";
        }
        key "id";
        leaf id {
          type uint16 {
            tailf:info
              "<1-3967,4048-4094>;;VLAN ID 1-4094 or range(s): 1-5, 10 or 2-5,7-19";
            range "1..4094";
          }
        }
        leaf name {
          tailf:info
            "Ascii name of the VLAN";
          tailf:cli-multi-value;
          tailf:cli-full-command;
          tailf:cli-diff-dependency "../../vlan-list/name" {
            tailf:xpath-root 3;
            tailf:cli-trigger-on-set;
          }
          type string {
            tailf:info
              "The ascii name for the VLAN (Max Size 32)";
            length "1..32";
          }
        }
        leaf state {
          tailf:info
            "Operational state of the VLAN";
          type enumeration {
            enum "active" {
              tailf:info
                "VLAN Active State";
            }
            enum "suspend" {
              tailf:info
                "VLAN Suspended State";
            }
          }
        }
        leaf mtu {
          tailf:info
            "VLAN Maximum Transmission Unit";
          type uint16 {
            tailf:info
              "<576-18190>;;Value of VLAN Maximum Tranmission Unit";
            range "576..18190";
          }
        }
        leaf remote-span {
          tailf:info
            "Configure as Remote SPAN VLAN";
          tailf:cli-full-command;
          type empty;
        }
        leaf uni-vlan {
          tailf:info
            "Configure a UNI VLAN";
          tailf:cli-full-command;
          type enumeration {
            enum "community" {
              tailf:info
                "UNI/ENI community VLAN";
            }
            enum "isolated" {
              tailf:info
                "UNI/ENI isolated VLAN";
            }
          }
        }
      }
      list configuration {
        tailf:info
          "Apply service policy to VLANs";
        tailf:cli-range-list-syntax;
        tailf:cli-mode-name "config-vlan-config";
        key "id";
        leaf id {
          type uint16 {
            tailf:info
              "<1-3967,4048-4094>;;VLAN ID 1-4094 or range(s): 1-5, 10 or 2-5,7-19";
            range "1..4094";
          }
        }
        container service-policy {
          tailf:info
            "Configure Service Policy";
          tailf:cli-compact-syntax;
          uses service-policy-grouping;
        }
      }
      list access-map {
        tailf:info
          "Create vlan access-map or enter vlan access-map command mode";
        tailf:cli-mode-name "config-access-map";
        key "name number";
        leaf name {
          type string {
            tailf:info
              "WORD;;Vlan access map tag";
          }
        }
        leaf number {
          type uint16 {
            tailf:info
              "<0-65535>;;Sequence to insert to/delete from existing vlan access-map entry";
          }
        }
        leaf action {
          tailf:info
            "Take the action";
          type enumeration {
            enum "drop" {
              tailf:info
                "Drop packets";
            }
            enum "forward" {
              tailf:info
                "Forward packets";
            }
          }
        }
        container match {
          tailf:info
            "Match values.";
          container mac {
            tailf:info
              "MAC based match";
            leaf-list address {
              tailf:info
                "Match MAC address to access control.";
              tailf:cli-flat-list-syntax;
              tailf:non-strict-leafref {
                path "../../../../../mac/access-list/extended/id";
              }
              type string {
                tailf:info
                  "WORD;;Access-list name";
              }
            }
          }
          container ip {
            tailf:info
              "IP based match";
            leaf-list address {
              tailf:info
                "Match IP address to access control.";
              tailf:cli-flat-list-syntax;
              type exp-ip-acl-type;
            }
          }
        }
      }
    }
    container lldp {
      tailf:ncs-device-type "cli-ned";
      tailf:display-when "not(../../ncs:module) or ../../ncs:module[ncs:name='tailf-ned-cisco-ios']";
      tailf:info
        "Global LLDP configuration subcommands";
      leaf run {
        tailf:info
          "Enable LLDP";
        type empty;
      }
    }
    container EXEC {
      tailf:ncs-device-type "cli-ned";
      tailf:display-when "not(../../ncs:module) or ../../ncs:module[ncs:name='tailf-ned-cisco-ios']";
      tailf:cli-drop-node-name;
      tailf:action default {
        tailf:actionpoint ncsproxy {
          tailf:internal;
        }
        tailf:info
          "Set a command to its defaults";
        // NCS drop tailf:actionpoint
        input {
          leaf-list args {
            tailf:cli-drop-node-name;
            tailf:cli-flat-list-syntax;
            type string {
              tailf:info
                "ACTION:;;default <argument(s)>";
            }
          }
        }
        output {
          leaf result {
            type string;
          }
        }
      }
      tailf:action exec {
        tailf:actionpoint ncsproxy {
          tailf:internal;
        }
        tailf:info
          "Execute config exec-commands, e.g. 'crypto key generate'";
        // NCS drop tailf:actionpoint
        input {
          leaf-list args {
            tailf:cli-drop-node-name;
            tailf:cli-flat-list-syntax;
            type string {
              tailf:info
                "ACTION:;;exec \"<command> <argument(s)> [options]\"";
            }
          }
        }
        output {
          leaf result {
            type string;
          }
        }
      }
    }
    container pm-agent {
      tailf:ncs-device-type "cli-ned";
      tailf:display-when "not(../../ncs:module) or ../../ncs:module[ncs:name='tailf-ned-cisco-ios']";
      tailf:info
        "pm-agent Configuration Commands";
      tailf:cli-run-template-enter "pm-agent\\n ! meta-data :: $(.ipath) :: shutdown-container-before-change :: pm-agent\\n";
      tailf:cli-exit-command "! exit-meta-data-pm-agent";
      tailf:ned-data "." {
        tailf:xpath-root 3;
        tailf:transaction to;
      }
      tailf:cli-add-mode;
      presence "true";
      container tenant {
        tailf:info
          "enter the tenant configuration";
        tailf:cli-compact-syntax;
        tailf:cli-sequence-commands {
          tailf:cli-reset-siblings;
        }
        leaf id {
          tailf:info
            "specify the tenant id";
          tailf:cli-incomplete-command;
          type uint32 {
            tailf:info
              "<1-4294967295>;;specify the tenant-id value";
            range "1..4294967295";
          }
        }
        leaf name {
          tailf:info
            "specify the tenant name";
          type string {
            tailf:info
              "WORD;;tenant Name";
          }
        }
      }
      container region {
        tailf:info
          "Enter the region ID";
        tailf:cli-compact-syntax;
        tailf:cli-sequence-commands {
          tailf:cli-reset-siblings;
        }
        leaf id {
          tailf:info
            "Specify the region ID";
          type uint32 {
            tailf:info
              "<1-4294967295>;;Specify the region-id value";
            range "1..4294967295";
          }
        }
        leaf name {
          tailf:info
            "Specify the region name";
          type string {
            tailf:info
              "WORD;;region Name";
          }
        }
      }
      container site {
        tailf:info
          "Enter the site configuration";
        tailf:cli-compact-syntax;
        tailf:cli-sequence-commands {
          tailf:cli-reset-siblings;
        }
        leaf id {
          tailf:info
            "Specify the site ID";
          type uint32 {
            tailf:info
              "<1-4294967295>;;Specify the site-id value";
            range "1..4294967295";
          }
        }
        leaf name {
          tailf:info
            "Specify the site name";
          type string {
            tailf:info
              "WORD;;Site Name";
          }
        }
      }
      container device {
        tailf:info
          "Enter the device ID";
        container id {
          tailf:info
            "Specify the device ID";
          tailf:cli-compact-syntax;
          tailf:cli-sequence-commands {
            tailf:cli-reset-siblings;
          }
          leaf id {
            tailf:cli-drop-node-name;
            type uint32 {
              tailf:info
                "<1-4294967295>;;Specify the device-id value";
              range "1..4294967295";
            }
          }
          leaf name {
            tailf:info
              "Specify the device name";
            type string {
              tailf:info
                "WORD;;device name";
            }
          }
        }
        leaf type {
          tailf:info
            "Enter the device type";
          tailf:cli-full-command;
          type enumeration {
            enum "ntr" {
              tailf:info
                "ntr device type";
            }
            enum "pxtr" {
              tailf:info
                "pxtr device type";
            }
            enum "rtr" {
              tailf:info
                "rtr device type";
            }
            enum "xtr" {
              tailf:info
                "xtr device type";
            }
          }
        }
      }
      container pmcs {
        tailf:info
          "Enter the pmcs configuration";
        list ipv4 {
          tailf:info
            "Enter the IPv4 address";
          tailf:cli-suppress-mode;
          tailf:cli-delete-when-empty;
          key "address";
          leaf address {
            type inet:ipv4-address {
              tailf:info
                "A.B.C.D;;IPv4 pmcs address e.g 10.10.0.0";
            }
          }
        }
        list ipv6 {
          tailf:info
            "Enter the IPv6 address";
          tailf:cli-suppress-mode;
          tailf:cli-delete-when-empty;
          key "address";
          leaf address {
            type inet:ipv6-address {
              tailf:info
                "X:X:X:X::X;;IPv6 pmcs Addr, e.g abcd:1234";
            }
          }
        }
      }
      list instance-id {
        tailf:info
          "Enter the instance ID";
        tailf:cli-mode-name "config-pm-agent-instance";
        key "id";
        leaf id {
          type uint32 {
            tailf:info
              "<0-4294967295>;;Specify the instance-id value";
          }
        }
        container enterprise-prefix {
          tailf:info
            "Enterprise prefix configuration";
          leaf prefix-list {
            tailf:cli-remove-before-change;
            tailf:cli-full-command;
            type string {
              tailf:info
                "WORD;;prefix-list containing list of site targets";
            }
          }
          container ipv4 {
            tailf:info
              "IPv4 enterprise prefix-list";
            leaf prefix-list {
              tailf:cli-remove-before-change;
              type string {
                tailf:info
                  "WORD;;prefix-list containing list of site targets";
              }
            }
          }
          container ipv6 {
            tailf:info
              "IPv6 enterprise prefix-list";
            leaf prefix-list {
              tailf:cli-remove-before-change;
              type string {
                tailf:info
                  "WORD;;prefix-list containing list of site targets";
              }
            }
          }
        }
      }
      leaf shutdown {
        tailf:info
          "shut the device";
        type empty;
      }
    }
    container crypto {
      tailf:ncs-device-type "cli-ned";
      tailf:display-when "not(../../ncs:module) or ../../ncs:module[ncs:name='tailf-ned-cisco-ios']";
      tailf:info
        "Encryption module";
      list keyring {
        tailf:info
          "Key ring commands";
        tailf:cli-mode-name "conf-keyring";
        key "name";
        leaf name {
          type string {
            tailf:info
              "WORD;;name of the key ring";
          }
        }
        leaf vrf {
          tailf:info
            "Mention a vrf it belongs to";
          tailf:cli-hide-in-submode;
          tailf:cli-diff-dependency "../../../ip/vrf" {
            tailf:xpath-root 3;
          }
          tailf:cli-diff-dependency "../../../vrf/definition" {
            tailf:xpath-root 3;
          }
          type string {
            tailf:info
              "WORD;;the VRF name";
          }
        }
        container pre-shared-key {
          tailf:info
            "Pre-Shared Key";
          list address {
            tailf:info
              "pre shared key by address";
            tailf:cli-suppress-mode;
            tailf:cli-delete-when-empty;
            tailf:cli-compact-syntax;
            tailf:cli-remove-before-change;
            key "address";
            leaf address {
              type inet:ipv4-address {
                tailf:info
                  "A.B.C.D;;address prefix";
              }
            }
            leaf mask {
              tailf:cli-drop-node-name;
              type inet:ipv4-address {
                tailf:info
                  "A.B.C.D;;address prefix mask";
              }
            }
            container key {
              tailf:info
                "specify the key";
              tailf:cli-flatten-container;
              tailf:cli-compact-syntax;
              tailf:cli-sequence-commands;
              uses crypto-key-grouping;
            }
          }
        }
      }
      container logging {
        tailf:info
          "logging messages";
        leaf session {
          tailf:info
            "logging up/down session";
          type empty;
        }
        leaf ikev2 {
          tailf:info
            "logging IKEv2 sessions";
          type empty;
        }
      }
      container ikev2 {
        tailf:info
          "Configure IKEv2 Options";
        list name-mangler {
          tailf:info
            "Name mangler";
          tailf:cli-mode-name "config-ikev2-name-mangler";
          key "name";
          leaf name {
            type string {
              tailf:info
                "WORD;;Name of the mangler";
            }
          }
          leaf fqdn {
            tailf:info
              "Derive name from FQDN identity";
            type enumeration {
              enum "all" {
                tailf:info
                  "entire portion of fqdn identity";
              }
              enum "domain" {
                tailf:info
                  "domain portion of fqdn identity";
              }
              enum "hostname" {
                tailf:info
                  "hostname portion of fqdn identity";
              }
            }
          }
        }
        container authorization {
          tailf:info
            "IKEv2 authorization";
          list policy {
            tailf:info
              "IKEv2 authorization policy";
            tailf:cli-mode-name "config-ikev2-author-policy";
            tailf:cli-full-command;
            key "name";
            leaf name {
              type string {
                tailf:info
                  "WORD;;Name of the policy";
              }
            }
            leaf pool {
              tailf:info
                "Specify local address pool";
              tailf:cli-full-command;
              type string {
                tailf:info
                  "WORD;;address pool name";
              }
            }
            leaf netmask {
              tailf:info
                "Specify netmask of the config address";
              tailf:cli-full-command;
              type inet:ipv4-address {
                tailf:info
                  "A.B.C.D;;netmask";
              }
            }
            container aaa {
              tailf:info
                "Specify aaa attribute list";
              container attribute {
                tailf:info
                  "AAA attribute list";
                leaf list {
                  tailf:info
                    "AAA attribute list";
                  type string {
                    tailf:info
                      "WORD;;AAA attribute list name";
                  }
                }
              }
            }
            container route {
              tailf:info
                "specify route parameters";
              container set {
                tailf:info
                  "Specify route set parameters";
                container access-list {
                  tailf:info
                    "Specify the route access-list";
                  leaf ipv4 {
                    tailf:cli-drop-node-name;
                    type std-ip-acl-type;
                  }
                  leaf ipv6 {
                    tailf:info
                      "ipv6 access-list";
                    type string {
                      tailf:info
                        "WORD;;access-list name";
                    }
                  }
                }
                container interface {
                  tailf:info
                    "Specify the route interface [interface-name]";
                  tailf:cli-display-separated;
                  presence "true";
                  list interface-list {
                    tailf:cli-drop-node-name;
                    tailf:cli-suppress-mode;
                    tailf:cli-delete-when-empty;
                    key "name";
                    leaf name {
                      type string {
                        tailf:info
                          "WORD;;Interface name";
                      }
                    }
                  }
                }
              }
              container accept {
                tailf:info
                  "Route accept parameters";
                container any {
                  tailf:info
                    "Accept all subnets from peer";
                  choice any-choice {
                    leaf distance {
                      tailf:info
                        "Specify distance for routes to remote subnets";
                      type uint8 {
                        tailf:info
                          "<1-255>;;Routing distance";
                        range "1..255";
                      }
                      default "1";
                    }
                    leaf tag {
                      tailf:info
                        "Specify tag for routes to remote subnets";
                      type uint32 {
                        tailf:info
                          "<1-497777>;;Routing tag ID";
                        range "1..497777";
                      }
                    }
                  }
                }
              }
            }
            leaf session-lifetime {
              tailf:info
                "Specify maximum session lifetime";
              type uint32 {
                tailf:info
                  "<120-25920000>;;maximum session lifetime in seconds";
                range "120..25920000";
              }
            }
          }
        }
        container redirect {
          tailf:info
            "IKEv2 Redirect Mechanism for load-balancing";
          container client {
            tailf:info
              "Enables Redirect Mechanism on Client";
            tailf:cli-delete-when-empty;
            presence "true";
            leaf max-redirects {
              tailf:info
                "Redirect loop detection";
              type uint8 {
                tailf:info
                  "<1-255>;;Max no. of Redirects per session, Default value is 5";
                range "1..255";
              }
              default "5";
            }
          }
        }
        list keyring {
          tailf:info
            "Define IKEv2 Keyring";
          tailf:cli-mode-name "config-ikev2-keyring";
          key "name";
          leaf name {
            type string {
              tailf:info
                "WORD;;Name of IKEv2 Keyring";
            }
          }
          list peer {
            tailf:info
              "Configure a Peer and associated keys";
            tailf:cli-mode-name "config-ikev2-keyring-peer";
            key "name";
            leaf name {
              type string {
                tailf:info
                  "WORD;;Name of the peer block";
              }
            }
            leaf description {
              tailf:info
                "Specify a description of this peer";
              tailf:cli-multi-value;
              tailf:cli-preformatted;
              tailf:cli-full-command;
              type string {
                tailf:info
                  "LINE;;description of the peer";
              }
            }
            container address {
              tailf:info
                "Specify IPv4/IPv6 address of peer";
              tailf:cli-compact-syntax;
              tailf:cli-sequence-commands {
                tailf:cli-reset-siblings;
              }
              choice address-choice {
                case ipv4 {
                  leaf ipv4-address {
                    tailf:cli-drop-node-name;
                    type inet:ipv4-address {
                      tailf:info
                        "A.B.C.D;;IPv4 Address";
                    }
                  }
                  leaf ipv4-mask {
                    tailf:cli-drop-node-name;
                    type inet:ipv4-address {
                      tailf:info
                        "A.B.C.D;;specify mask";
                    }
                    default "255.255.255.255";
                  }
                }
                case ipv6 {
                  leaf ipv6-address {
                    tailf:cli-drop-node-name;
                    type ipv6-prefix {
                      tailf:info
                        "X:X:X:X::X/<0-128>;;IPv6 address/prefix";
                    }
                  }
                }
              }
            }
            container identity {
              tailf:info
                "Specify IKE identity to use";
              choice identity-choice {
                leaf key-id {
                  tailf:info
                    "proprietary types of identification (ID KEY ID)";
                  type string {
                    tailf:info
                      "WORD;;ID_KEY_ID <string>";
                  }
                }
                container fqdn {
                  tailf:info
                    "Use FQDN";
                  tailf:cli-compact-syntax;
                  tailf:cli-sequence-commands {
                    tailf:cli-reset-siblings;
                  }
                  leaf domain {
                    tailf:info
                      "email Domain Name";
                    tailf:cli-optional-in-sequence;
                    tailf:cli-incomplete-command;
                    type empty;
                  }
                  leaf name {
                    tailf:cli-drop-node-name;
                    type string {
                      tailf:info
                        "WORD;;Specify the name string";
                    }
                  }
                }
              }
            }
            container pre-shared-key {
              tailf:info
                "specify the pre-shared key";
              tailf:cli-flatten-container;
              tailf:cli-compact-syntax;
              tailf:cli-sequence-commands;
              choice pre-shared-key-choice {
                case one-case {
                  uses crypto-key-grouping;
                }
                case local-remote-case {
                  container local {
                    tailf:cli-optional-in-sequence;
                    tailf:cli-compact-syntax;
                    tailf:cli-sequence-commands;
                    uses crypto-key-grouping;
                  }
                  container remote {
                    tailf:cli-compact-syntax;
                    tailf:cli-sequence-commands;
                    uses crypto-key-grouping;
                  }
                }
              }
            }
          }
        }
        list proposal {
          tailf:info
            "Define IKEV2 proposals";
          tailf:cli-mode-name "config-ikev2-proposal";
          key "name";
          leaf name {
            type string {
              tailf:info
                "WORD;;Name of IKEv2 proposal";
            }
          }
          leaf-list encryption {
            tailf:info
              "Set encryption algorithm(s) for proposal";
            tailf:cli-replace-all;
            tailf:cli-flat-list-syntax;
            type enumeration {
              enum "aes-cbc-128" {
                tailf:info
                  "AES-CBC-128";
              }
              enum "3des" {
                tailf:info
                  "3DES";
              }
              enum "aes-cbc-192" {
                tailf:info
                  "AES-CBC-192";
              }
              enum "aes-cbc-256" {
                tailf:info
                  "AES-CBC-256";
              }
              enum "des" {
                tailf:info
                  "DES";
              }
            }
          }
          leaf-list integrity {
            tailf:info
              "Set integrity hash algorithm(s) for proposal";
            tailf:cli-replace-all;
            tailf:cli-flat-list-syntax;
            type enumeration {
              enum "md5" {
                tailf:info
                  "Message Digest 5";
              }
              enum "sha1" {
                tailf:info
                  "Secure Hash Standard";
              }
              enum "sha256" {
                tailf:info
                  "Secure Hash Standard 2 (256 bit)";
              }
              enum "sha384" {
                tailf:info
                  "Secure Hash Standard 2 (384 bit)";
              }
              enum "sha512" {
                tailf:info
                  "Secure Hash Standard 2 (512 bit)";
              }
            }
          }
          leaf-list group {
            tailf:info
              "Set the Diffie-Hellman group(s)";
            tailf:cli-replace-all;
            tailf:cli-flat-list-syntax;
            ordered-by user;
            type enumeration {
              enum "1" {
                tailf:info
                  "DH 768 MODP";
              }
              enum "14" {
                tailf:info
                  "DH 2048 MODP";
              }
              enum "15" {
                tailf:info
                  "DH 3072 MODP";
              }
              enum "16" {
                tailf:info
                  "DH 4096 MODP";
              }
              enum "19" {
                tailf:info
                  "DH 256 ECP";
              }
              enum "2" {
                tailf:info
                  "DH 1024 MODP";
              }
              enum "20" {
                tailf:info
                  "DH 384 ECP";
              }
              enum "21" {
                tailf:info
                  "DH 521 ECP";
              }
              enum "24" {
                tailf:info
                  "DH 2048 (256 subgroup) MODP";
              }
              enum "5" {
                tailf:info
                  "DH 1536 MODP";
              }
            }
          }
        }
        list policy {
          tailf:info
            "Define IKEV2 policies";
          tailf:cli-mode-name "config-ikev2-policy";
          key "name";
          leaf name {
            type string {
              tailf:info
                "WORD;;Name of IKEv2 policy";
            }
          }
          leaf proposal {
            tailf:info
              "Specify Proposal";
            tailf:non-strict-leafref {
              path "../../../../crypto/ikev2/proposal/name";
            }
            type string {
              tailf:info
                "WORD;;Specify the name of proposal to be attached";
            }
          }
          container match {
            tailf:info
              "Match values of local fields";
            leaf fvrf {
              tailf:info
                "fvrf of the profile";
              tailf:cli-diff-dependency "../../../../../vrf/definition" {
                tailf:xpath-root 3;
              }
              type union {
                type string {
                  tailf:info
                    "WORD;;fvrf name (default: global)";
                }
                type enumeration {
                  enum "any" {
                    tailf:info
                      "any fvrf";
                  }
                }
              }
            }
            container address {
              tailf:info
                "Specify the address to match";
              list local {
                tailf:info
                  "Local address";
                tailf:cli-suppress-mode;
                tailf:cli-delete-when-empty;
                key "address";
                leaf address {
                  type union {
                    type inet:ipv4-address {
                      tailf:info
                        "A.B.C.D;;IPv4 address";
                    }
                    type inet:ipv6-address {
                      tailf:info
                        "X:X:X:X::X;;IPv6 address";
                    }
                  }
                }
              }
            }
          }
        }
        list profile {
          tailf:info
            "Define IKEv2 Profiles";
          tailf:cli-mode-name "config-ikev2-profile";
          key "name";
          leaf name {
            type string {
              tailf:info
                "WORD;;Name of IKEv2 Profile";
            }
          }
          leaf description {
            tailf:info
              "Specify a description of this profile";
            tailf:cli-multi-value;
            tailf:cli-preformatted;
            tailf:cli-full-command;
            type string {
              tailf:info
                "LINE;;a 1 line description of the profile";
            }
          }
          container match {
            tailf:info
              "Match values of peer";
            container address {
              tailf:info
                "IP address";
              list local {
                tailf:info
                  "Local address";
                tailf:cli-suppress-mode;
                tailf:cli-delete-when-empty;
                key "address";
                leaf address {
                  type inet:host {
                    tailf:info
                      "Hostname, A.B.C.D or X:X:X:X::X;;Address";
                  }
                }
              }
            }
            leaf fvrf {
              tailf:info
                "fvrf of the profile";
              tailf:cli-diff-dependency "../../../../../vrf/definition" {
                tailf:xpath-root 3;
              }
              type union {
                type string {
                  tailf:info
                    "WORD;;fvrf name (default: global)";
                }
                type enumeration {
                  enum "any" {
                    tailf:info
                      "any fvrf";
                  }
                }
              }
            }
            container identity {
              tailf:info
                "IKE identity";
              container remote {
                tailf:info
                  "Remote identity";
                leaf any {
                  tailf:info
                    "match any peer identity";
                  tailf:cli-full-command;
                  type empty;
                }
                list key-id {
                  tailf:info
                    "key-id opaque string ";
                  tailf:cli-suppress-mode;
                  tailf:cli-delete-when-empty;
                  key "name";
                  leaf name {
                    type string {
                      tailf:info
                        "WORD;;Specify the key-id string";
                    }
                  }
                }
                container fqdn {
                  tailf:info
                    "Fully qualified domain name string";
                  list fqdn-list {
                    tailf:cli-drop-node-name;
                    tailf:cli-suppress-mode;
                    tailf:cli-delete-when-empty;
                    key "name";
                    leaf name {
                      type string {
                        tailf:info
                          "WORD;;Specify the name string";
                      }
                    }
                  }
                  list domain {
                    tailf:info
                      "match domain instead of exact";
                    tailf:cli-suppress-mode;
                    tailf:cli-delete-when-empty;
                    key "name";
                    leaf name {
                      type string {
                        tailf:info
                          "WORD;;Specify the name string";
                      }
                    }
                  }
                }
                list address {
                  tailf:info
                    "match address";
                  tailf:cli-suppress-mode;
                  tailf:cli-delete-when-empty;
                  tailf:cli-compact-syntax;
                  key "name";
                  leaf name {
                    type union {
                      type inet:ipv4-address {
                        tailf:info
                          "A.B.C.D;;IP address";
                      }
                      type ipv6-prefix {
                        tailf:info
                          "X:X:X:X::X/<0-128>;;IPv6 prefix x:x::y/<z>";
                      }
                    }
                  }
                  leaf mask {
                    tailf:cli-drop-node-name;
                    type inet:ipv4-address {
                      tailf:info
                        "A.B.C.D;;IP mask";
                    }
                  }
                }
              }
            }
          }
          container identity {
            tailf:info
              "Specify IKE identity to use";
            container local {
              tailf:info
                "Specify the local IKE identity to use for the negotiation";
              choice local-choice {
                leaf dn {
                  tailf:info
                    "Distinguished Name";
                  type empty;
                }
                leaf email {
                  tailf:info
                    "Fully qualified email string";
                  type string {
                    tailf:info
                      "WORD;;email <user@domain>";
                  }
                }
                leaf fqdn {
                  tailf:info
                    "Fully qualified domain name string";
                  type string {
                    tailf:info
                      "WORD;;FQDN <host.domain>";
                  }
                }
                leaf address {
                  tailf:info
                    "address";
                  type union {
                    type inet:ipv4-address {
                      tailf:info
                        "A.B.C.D;;IPv4 address";
                    }
                    type inet:ipv6-address {
                      tailf:info
                        "X:X:X:X::X;;IPv6 address";
                    }
                  }
                }
              }
            }
          }
          container authentication {
            tailf:info
              "Set authentication method";
            container local {
              tailf:info
                "Set local authentication method";
              choice method-choice {
                container eap {
                  tailf:info
                    "Extended Authentication Protocol";
                  presence "true";
                }
                leaf ecdsa-sig {
                  tailf:info
                    "ECDSA Signature";
                  type empty;
                }
                container pre-share {
                  tailf:info
                    "Pre-Shared Key";
                  tailf:cli-flatten-container;
                  tailf:cli-compact-syntax;
                  tailf:cli-delete-when-empty;
                  presence "true";
                  container key {
                    tailf:cli-flatten-container;
                    tailf:cli-compact-syntax;
                    tailf:cli-sequence-commands;
                    uses crypto-key-grouping;
                  }
                }
                leaf rsa-sig {
                  tailf:info
                    "Rivest-Shamir-Adleman Signature";
                  type empty;
                }
              }
            }
            container remote {
              tailf:info
                "Set remote authentication method";
              tailf:cli-delete-when-empty;
              presence "true";
              choice method-choice {
                container eap {
                  tailf:info
                    "Extended Authentication Protocol";
                  tailf:cli-delete-when-empty;
                  presence "true";
                  leaf query-identity {
                    tailf:info
                      "query EAP identity from peer ";
                    type empty;
                  }
                }
                leaf ecdsa-sig {
                  tailf:info
                    "ECDSA Signature";
                  type empty;
                }
                container pre-share {
                  tailf:info
                    "Pre-Shared Key";
                  tailf:cli-flatten-container;
                  tailf:cli-compact-syntax;
                  tailf:cli-delete-when-empty;
                  presence "true";
                  container key {
                    tailf:cli-flatten-container;
                    tailf:cli-compact-syntax;
                    tailf:cli-sequence-commands;
                    uses crypto-key-grouping;
                  }
                }
                leaf rsa-sig {
                  tailf:info
                    "Rivest-Shamir-Adleman Signature";
                  type empty;
                }
              }
            }
          }
          container pki {
            tailf:info
              "Specify certificate authorities to trust";
            leaf-list trustpoint {
              tailf:info
                "Cert authority trustpoint for RSA sig";
              tailf:cli-list-syntax;
              tailf:non-strict-leafref {
                path "../../../../../crypto/pki/trustpoint/id";
              }
              type string {
                tailf:info
                  "WORD;;Specify the trustpoint label to use";
              }
            }
          }
          container keyring {
            tailf:info
              "Specify keyring to use";
            choice keyring-choice {
              container aaa {
                tailf:info
                  "AAA based keyring";
                tailf:cli-compact-syntax;
                tailf:cli-sequence-commands {
                  tailf:cli-reset-siblings;
                }
                leaf name {
                  tailf:cli-drop-node-name;
                  type string {
                    tailf:info
                      "WORD;;AAA list name";
                  }
                }
                leaf name-mangler {
                  tailf:info
                    "Specify the name-mangler to derive username";
                  tailf:non-strict-leafref {
                    path "../../../../../../crypto/ikev2/name-mangler/name";
                  }
                  type string {
                    tailf:info
                      "WORD;;mangler name";
                  }
                }
              }
              leaf local {
                tailf:info
                  "Local keyring";
                tailf:non-strict-leafref {
                  path "../../../../../crypto/ikev2/keyring/name";
                }
                type string {
                  tailf:info
                    "WORD;;Keyring name";
                }
              }
            }
          }
          container nat {
            tailf:info
              "NAT-transparency";
            leaf keepalive {
              tailf:info
                "NAT keepalive interval";
              type uint16 {
                tailf:info
                  "<5-3600>;;NAT keepalive interval in seconds";
                range "5..3600";
              }
            }
          }
          container aaa {
            tailf:info
              "Specify AAA related configs";
            container authentication {
              tailf:info
                "AAA authentication";
              leaf eap {
                tailf:info
                  "AAA EAP authentication";
                type string {
                  tailf:info
                    "WORD;;AAA list name";
                }
              }
            }
            container authorization {
              tailf:info
                "AAA authorization";
              container group {
                tailf:info
                  "AAA group authorization";
                container psk {
                  tailf:info
                    "AAA list to use when IKEv2 remote auth method is PSK";
                  uses crypto-ikev2-profile-aaa-authorization-group-list {
                    refine "list/password/secret" {
                      tailf:meta-data "secret-password" {
                        tailf:meta-value "crypto ikev2 profile <profile><NL><*> ::  aaa authorization group psk list <list> password <PASSWORD>";
                      }
                    }
                  }
                }
                container eap {
                  tailf:info
                    "AAA list to use when IKEv2 remote auth method is EAP";
                  uses crypto-ikev2-profile-aaa-authorization-group-list {
                    refine "list/password/secret" {
                      tailf:meta-data "secret-password" {
                        tailf:meta-value "crypto ikev2 profile <profile><NL><*> ::  aaa authorization group eap list <list> password <PASSWORD>";
                      }
                    }
                  }
                }
              }
              container user {
                tailf:info
                  "AAA user authorization";
                container psk {
                  tailf:info
                    "AAA list to use when IKEv2 remote auth method is PSK";
                  leaf cached {
                    tailf:info
                      "Use cached attributes from EAP authentication or AAA pre-shared key fetch";
                    type empty;
                  }
                  leaf list {
                    tailf:info
                      "AAA method list";
                    type string {
                      tailf:info
                        "WORD;;AAA list name";
                    }
                  }
                }
              }
            }
          }
          container virtual-template {
            tailf:info
              "Specify the virtual-template for dynamic interface creation";
            tailf:cli-compact-syntax;
            tailf:cli-sequence-commands;
            leaf number {
              tailf:cli-drop-node-name;
              type uint16 {
                tailf:info
                  "<1-4095>;;Virtual-template number";
                range "1..4095";
              }
            }
            leaf mode {
              tailf:info
                "Enabling Tunnel Auto Mode";
              type enumeration {
                enum "auto" {
                  tailf:info
                    "Auto - Enable Auto feature on the ike profile";
                }
              }
            }
          }
          leaf lifetime {
            tailf:info
              "Set lifetime for ISAKMP security association";
            type uint32 {
              tailf:info
                "<120-86400>;;lifetime in seconds";
              range "120..86400";
            }
            default "86400";
          }
          container dpd {
            tailf:info
              "Enable IKE liveness check for peers";
            tailf:cli-compact-syntax;
            tailf:cli-sequence-commands;
            leaf interval {
              tailf:cli-drop-node-name;
              tailf:cli-incomplete-command;
              type uint16 {
                tailf:info
                  "<10-3600>;;DPD R-U-THERE interval";
                range "10..3600";
              }
            }
            leaf retry-interval {
              tailf:cli-drop-node-name;
              tailf:cli-incomplete-command;
              type uint8 {
                tailf:info
                  "<2-60>;;DPD Retry Interval";
              }
            }
            leaf queries {
              tailf:cli-drop-node-name;
              type enumeration {
                enum "on-demand" {
                  tailf:info
                    "Send DPD queries only as needed";
                }
                enum "periodic" {
                  tailf:info
                    "Send DPD queries at regular intervals";
                }
              }
            }
          }
        }
        container fragmentation {
          tailf:info
            "Enable fragmentation of ikev2 packets";
          tailf:cli-reset-container;
          tailf:cli-delete-when-empty;
          presence "true";
          leaf mtu {
            tailf:info
              "MTU size for fragmentation";
            type uint16 {
              tailf:info
                "<68-1500>;;ikev2 MTU including IP and UDP header size";
              range "68..1500";
            }
          }
        }
        container http-url {
          tailf:info
            "Enable http URL lookup";
          leaf cert {
            tailf:info
              "Enable certificate lookup based on HTTP-based URL";
            tailf:cli-boolean-no;
            type boolean;
            default "true";
          }
        }
        container client {
          tailf:info
            "IKEv2 client configuration";
          list flexvpn {
            tailf:info
              "Configure an IKEv2 FlexVPN client";
            tailf:cli-mode-name "config-ikev2-flexvpn";
            key "name";
            leaf name {
              type string {
                tailf:info
                  "WORD;;IKEv2 FlexVPN name";
              }
            }
            container peer {
              tailf:info
                "Allowed Encryption/Decryption Peer";
              list peer-list {
                tailf:cli-drop-node-name;
                tailf:cli-suppress-mode;
                tailf:cli-delete-when-empty;
                tailf:cli-compact-syntax;
                tailf:cli-sequence-commands {
                  tailf:cli-reset-siblings;
                }
                key "sequence";
                leaf sequence {
                  type uint8 {
                    tailf:info
                      "<1-255>;;peer sequence number";
                    range "1..255";
                  }
                }
                choice address-choice {
                  leaf ipv4-address {
                    tailf:cli-drop-node-name;
                    type inet:ipv4-address {
                      tailf:info
                        "A.B.C.D;;ip address";
                    }
                  }
                  leaf ipv6-address {
                    tailf:cli-drop-node-name;
                    type inet:ipv6-address {
                      tailf:info
                        "X:X:X:X::X;;IPv6 address";
                    }
                  }
                  case fqdn {
                    leaf fqdn {
                      tailf:info
                        "Peer host name";
                      type string {
                        tailf:info
                          "WORD;;Peer Hostname";
                      }
                    }
                    leaf dynamic {
                      tailf:info
                        "Dynamic host name";
                      tailf:cli-optional-in-sequence;
                      type empty;
                    }
                    leaf ipv6 {
                      tailf:info
                        "IPv6 host name";
                      tailf:cli-optional-in-sequence;
                      type empty;
                    }
                  }
                }
                leaf track {
                  tailf:info
                    "Peer track object";
                  type uint16 {
                    tailf:info
                      "<1-1000>;;Track object number";
                    range "1..1000";
                  }
                }
              }
              leaf reactivate {
                tailf:info
                  "Re-activate peer enabled";
                tailf:cli-full-command;
                type empty;
              }
            }
            list source {
              tailf:cli-suppress-mode;
              tailf:cli-delete-when-empty;
              tailf:cli-compact-syntax;
              tailf:cli-sequence-commands {
                tailf:cli-reset-siblings;
              }
              tailf:cli-remove-before-change;
              key "seq";
              leaf seq {
                type uint8 {
                  tailf:info
                    "<1-255>;;source sequence number";
                  range "1..255";
                }
              }
              container interface {
                tailf:cli-drop-node-name;
                tailf:cli-flatten-container;
                tailf:cli-compact-syntax;
                tailf:cli-incomplete-command;
                uses interface-name-grouping;
              }
              leaf track {
                tailf:info
                  "source track object";
                type uint16 {
                  tailf:info
                    "<1-1000>;;track object number";
                  range "1..1000";
                }
              }
            }
            container client {
              tailf:info
                "Client interface";
              container connect {
                tailf:info
                  "tunnel interface";
                leaf Tunnel {
                  tailf:info
                    "Tunnel interface";
                  tailf:cli-allow-join-with-value {
                    tailf:cli-display-joined;
                  }
                  tailf:non-strict-leafref {
                    path "../../../../../../../interface/Tunnel/name";
                  }
                  type uint32 {
                    tailf:info
                      "<0-2147483647>;;Tunnel interface number";
                    range "0..2147483647";
                  }
                }
              }
            }
          }
        }
        container dpd {
          tailf:info
            "Enable IKE liveness check for peers";
          tailf:cli-compact-syntax;
          tailf:cli-sequence-commands {
            tailf:cli-reset-siblings;
          }
          leaf interval {
            tailf:cli-drop-node-name;
            type uint32;
          }
          leaf retry-interval {
            tailf:cli-drop-node-name;
            type uint32;
          }
          leaf mode {
            tailf:cli-drop-node-name;
            type enumeration {
              enum "on-demand";
              enum "periodic";
            }
          }
        }
      }
      container pki {
        tailf:info
          "Public Key components";
        list server {
          tailf:info
            "Enable IOS Certificate server";
          tailf:cli-mode-name "cs-server";
          tailf:cli-compact-syntax;
          tailf:cli-full-command;
          max-elements 1;
          key "cs-label";
          leaf cs-label {
            type string {
              tailf:info
                "WORD;;Certificate Server Name";
            }
          }
          leaf shutdown {
            tailf:info
              "Shutdown the Certificate Server";
            type empty;
          }
          container database {
            tailf:info
              "Certificate Server database config parameters";
            container archive {
              tailf:info
                "Backup Certificate Server Signing Certificate and Keys";
              tailf:cli-compact-syntax;
              tailf:cli-sequence-commands;
              leaf format {
                tailf:cli-drop-node-name;
                type enumeration {
                  enum "pem" {
                    tailf:info
                      "PEM format";
                  }
                  enum "pkcs12" {
                    tailf:info
                      "PKCS12 format";
                  }
                }
              }
              container password {
                tailf:info
                  "Passphrase to protect the private key archive";
                tailf:cli-flatten-container;
                tailf:cli-compact-syntax;
                tailf:cli-sequence-commands {
                  tailf:cli-reset-siblings;
                }
                leaf type {
                  tailf:cli-drop-node-name;
                  tailf:cli-optional-in-sequence;
                  type uint8 {
                    tailf:info
                      "<0-9>;;Encryption type";
                    range "0..9";
                  }
                }
                leaf secret {
                  tailf:cli-drop-node-name;
                  type string {
                    tailf:info
                      "LINE;;Password";
                  }
                }
              }
            }
          }
          leaf grant {
            tailf:info
              "Certificate granting options";
            type enumeration {
              enum "auto" {
                tailf:info
                  "Automatically grant incoming SCEP enrollment requests";
              }
              enum "none" {
                tailf:info
                  "Automatically reject any incoming SCEP enrollment request";
              }
              enum "ra-auto" {
                tailf:info
                  "Automatically grant RA-authorized incoming SCEP enrollment request";
              }
            }
          }
          leaf hash {
            tailf:info
              "Hash algorithm";
            type enumeration {
              enum "md5" {
                tailf:info
                  "use md5 hash algorithm";
              }
              enum "sha1" {
                tailf:info
                  "use sha1 hash algorithm";
              }
              enum "sha256" {
                tailf:info
                  "use sha256 hash algorithm";
              }
              enum "sha384" {
                tailf:info
                  "use sha384 hash algorithm";
              }
              enum "sha512" {
                tailf:info
                  "use sha512 hash algorithm";
              }
            }
          }
        }
        list trustpoint {
          tailf:info
            "Define a CA trustpoint";
          tailf:cli-mode-name "ca-trustpoint";
          key "id";
          leaf id {
            type string {
              tailf:info
                "WORD;;CA Server Name";
            }
          }
          container serial-number {
            tailf:info
              "include serial number";
            tailf:cli-reset-container;
            presence "true";
            leaf none {
              tailf:info
                "do not include serial number";
              type empty;
            }
          }
          leaf ip-address {
            tailf:info
              "include ip address";
            tailf:cli-diff-dependency "../../../../interface" {
              tailf:xpath-root 3;
            }
            type union {
              type string {
                tailf:info
                  "LINE;;interface name or ip address";
              }
              type enumeration {
                enum "none" {
                  tailf:info
                    "do not include ip address";
                }
              }
            }
          }
          container enrollment {
            tailf:info
              "Enrollment parameters";
            leaf http-proxy {
              tailf:info
                "HTTP proxy server for enrollment";
              type string {
                tailf:info
                  "WORD;;host-name";
              }
            }
            container mode {
              tailf:info
                "Mode supported by the Certificate Authority";
              leaf ra {
                tailf:info
                  "Registration Authority mode";
                type empty;
              }
            }
            leaf pkcs12 {
              tailf:info
                "";
              type empty;
            }
            leaf profile {
              tailf:info
                "Specify an profile for enrollment";
              type string {
                tailf:info
                  "WORD;;Profile name";
              }
            }
            container retry {
              tailf:info
                "Polling parameters";
              leaf count {
                tailf:info
                  "How many times to poll CA for our certificate";
                type uint8 {
                  tailf:info
                    "<1-100>;;Number of times to poll a CA for a certificate";
                  range "1..100";
                }
              }
              leaf period {
                tailf:info
                  "How long to wait between requests to CA for our certificate";
                type uint8 {
                  tailf:info
                    "<1-60>;;Period in minutes between attempts to contact a CA";
                  range "1..60";
                }
              }
            }
            leaf selfsigned {
              tailf:info
                "Generate a Self Signed Certificate";
              type empty;
            }
            container terminal {
              tailf:info
                "Enroll via the terminal (cut-and-paste)";
              tailf:cli-delete-when-empty;
              presence "true";
              leaf pem {
                tailf:info
                  "Include PEM encapsulation boundaries";
                type empty;
              }
            }
            leaf url {
              tailf:info
                "CA server enrollment URL";
              type string {
                tailf:info
                  "WORD;;HTTP URL";
              }
            }
          }
          container password {
            tailf:info
              "revocation password";
            tailf:cli-compact-syntax;
            tailf:cli-sequence-commands;
            uses password-grouping;
          }
          leaf subject-name {
            tailf:info
              "Subject Name";
            tailf:cli-full-command;
            type string {
              tailf:info
                "LINE;;Subject Name";
            }
          }
          leaf fqdn {
            tailf:info
              "include fully-qualified domain name";
            tailf:cli-full-command;
            type union {
              type enumeration {
                enum "none" {
                  tailf:info
                    "do not include fully-qualified domain name";
                }
              }
              type string {
                tailf:info
                  "LINE;;fully-qualified domain name";
              }
            }
          }
          container usage {
            tailf:info
              "Certificate Usage";
            leaf ike {
              tailf:info
                "IKE certificate";
              type empty;
            }
            leaf ssl-server {
              tailf:info
                "SSL server certificate";
              type empty;
            }
            leaf ssl-client {
              tailf:info
                "SSL client certificate";
              type empty;
            }
          }
          leaf-list revocation-check {
            tailf:info
              "Revocation checking options";
            tailf:cli-flat-list-syntax;
            tailf:cli-replace-all;
            ordered-by user;
            type enumeration {
              enum "crl" {
                tailf:info
                  "Revocation check by CRL";
              }
              enum "none" {
                tailf:info
                  "Ignore revocation check";
              }
              enum "ocsp" {
                tailf:info
                  "Revocation check by OCSP";
              }
            }
          }
          container source {
            tailf:info
              "Specify source";
            container interface {
              tailf:info
                "Interface used as source address";
              uses interface-name-grouping;
            }
          }
          container rsakeypair {
            tailf:info
              "Specify rsakeypair for this identity";
            tailf:cli-compact-syntax;
            tailf:cli-sequence-commands {
              tailf:cli-reset-siblings;
            }
            leaf key-label {
              tailf:cli-drop-node-name;
              type string {
                tailf:info
                  "WORD;;RSA keypair label";
              }
            }
            leaf key-size {
              tailf:cli-drop-node-name;
              type uint16 {
                tailf:info
                  "<360-4096>;;General Purpose or Signature Key length";
                range "360..4096";
              }
            }
            leaf encryption-key-size {
              tailf:cli-drop-node-name;
              type uint16 {
                tailf:info
                  "<360-4096>;;Encryption Key length";
                range "360..4096";
              }
            }
          }
          container auto-enroll {
            tailf:info
              "Automatically enroll this router identity";
            tailf:cli-compact-syntax;
            tailf:cli-delete-when-empty;
            presence "true";
            leaf percent {
              tailf:cli-drop-node-name;
              type uint8 {
                tailf:info
                  "<0-100>;;renewal percentage";
                range "0..100";
              }
            }
            leaf regenerate {
              tailf:info
                "Regenerate keys on re-enrollment";
              type empty;
            }
          }
        }
        container certificate {
          tailf:info
            "Actions on certificates";
          list chain {
            tailf:info
              "Identify certificates";
            tailf:cli-mode-name "config-cert-chain";
            key "name";
            leaf name {
              tailf:cli-diff-dependency "../../../trustpoint" {
                tailf:xpath-root 3;
              }
              type string {
                tailf:info
                  "WORD;;CA Server Name";
              }
            }
            list certificate {
              tailf:info
                "Certificate issued by the CA";
              tailf:cli-mode-name "config-pki-hexmode-quotedstring";
              tailf:cli-delete-when-empty;
              tailf:cli-exit-command "quit";
              tailf:cli-compact-syntax;
              tailf:cli-sequence-commands;
              tailf:cli-full-command;
              tailf:cli-reset-container;
              key "serial";
              leaf serial {
                tailf:cli-disallow-value "rollover|ca|ra-encrypt|ra-general|ra-sign|self-signed";
                type string {
                  tailf:info
                    "WORD;;Certificate serial number";
                }
              }
              leaf cert-type {
                tailf:cli-optional-in-sequence;
                tailf:cli-drop-node-name;
                tailf:cli-prefix-key;
                type enumeration {
                  enum "ca" {
                    tailf:info
                      "A certificate";
                  }
                  enum "ra-encrypt" {
                    tailf:info
                      "A encryption certificate";
                  }
                  enum "ra-general" {
                    tailf:info
                      "A general purpose certificate";
                  }
                  enum "ra-sign" {
                    tailf:info
                      "A signing certificate";
                  }
                  enum "rollover" {
                    tailf:info
                      "Shadow rollover certificate";
                  }
                  enum "self-signed" {
                    tailf:info
                      "Self-signed certificate";
                  }
                }
              }
              leaf rollover {
                tailf:info
                  "Shadow rollover certificate";
                tailf:cli-optional-in-sequence;
                tailf:cli-prefix-key;
                type empty;
              }
              leaf cert {
                tailf:cli-drop-node-name;
                tailf:cli-disallow-value "rollover|ca|ra-encrypt|ra-general|ra-sign|self-signed";
                type string {
                  tailf:info
                    "WORD;;file specification";
                }
              }
            }
          }
        }
        container token {
          tailf:info
            "Configure cryptographic token";
          list token-name {
            tailf:cli-suppress-mode;
            tailf:cli-delete-when-empty;
            tailf:cli-drop-node-name;
            tailf:cli-compact-syntax;
            key "name";
            leaf name {
              type string {
                tailf:info
                  "WORD;;token name";
              }
            }
            uses crypto-pki-token-grouping;
          }
        }
        container default {
          tailf:info
            "set default values for tokens";
          uses crypto-pki-token-grouping;
        }
      }
      container isakmp {
        tailf:info
          "Configure ISAKMP policy";
        container default {
          tailf:info
            "ISAKMP default policy";
          leaf policy {
            tailf:info
              "Enable default policies for ISAKMP protection suite";
            tailf:cli-boolean-no;
            tailf:cli-full-command;
            type boolean;
            default "true";
          }
        }
        leaf enable {
          tailf:info
            "Enable ISAKMP";
          tailf:cli-boolean-no;
          tailf:cli-full-command;
          type boolean;
          default "true";
        }
        leaf identity {
          tailf:info
            "Set the identity which ISAKMP will use";
          type enumeration {
            enum "address" {
              tailf:info
                "Use the IP address of the interface for the identity";
            }
            enum "dn" {
              tailf:info
                "Use the distinguished name of the router cert for the identity";
            }
            enum "hostname" {
              tailf:info
                "Use the hostname of the router for the identity";
            }
          }
          default "address";
        }
        leaf fragmentation {
          tailf:info
            "IKE Fragmentation enabled if required";
          type empty;
        }
        leaf invalid-spi-recovery {
          tailf:info
            "Initiate IKE and send Invalid SPI Notify";
          type empty;
        }
        container client {
          tailf:info
            "Set client configuration policy";
          container configuration {
            tailf:info
              "Set client configuration policy";
            list group {
              tailf:info
                "Set group profile attributes for client";
              tailf:cli-mode-name "config-isakmp-group";
              key "name";
              leaf name {
                type string {
                  tailf:info
                    "WORD;;group name";
                }
              }
              container key {
                tailf:info
                  "pre-shared key/IKE password";
                tailf:cli-flatten-container;
                tailf:cli-compact-syntax;
                tailf:cli-sequence-commands;
                uses crypto-key-grouping {
                  refine "secret" {
                    tailf:cli-remove-before-change;
                  }
                }
              }
              leaf pool {
                tailf:info
                  "Set name of address pool";
                type string {
                  tailf:info
                    "WORD;;address pool name";
                }
              }
              leaf netmask {
                tailf:info
                  "netmask used by the client for local connectivity";
                type inet:ipv4-address {
                  tailf:info
                    "A.B.C.D;;Subnet Mask to be issued for client use";
                }
              }
            }
          }
        }
        list profile {
          tailf:info
            "Define ISAKMP Profiles";
          tailf:cli-mode-name "conf-isa-prof";
          key "name";
          leaf name {
            type string {
              tailf:info
                "WORD;;Name of ISAKMP Profile";
            }
          }
          leaf description {
            tailf:info
              "Specify a description of this profile";
            tailf:cli-multi-value;
            tailf:cli-preformatted;
            tailf:cli-full-command;
            type string {
              tailf:info
                "LINE;;a 1 line description of the profile";
            }
          }
          leaf vrf {
            tailf:info
              "Specify the VRF it is related to";
            tailf:cli-diff-dependency "../../../../ip/vrf" {
              tailf:xpath-root 3;
            }
            tailf:cli-diff-dependency "../../../../vrf/definition" {
              tailf:xpath-root 3;
            }
            type string {
              tailf:info
                "WORD;;VRF Name";
            }
          }
          list keyring {
            tailf:info
              "Specify keyring to use";
            tailf:cli-suppress-mode;
            tailf:cli-delete-when-empty;
            key "name";
            leaf name {
              tailf:cli-diff-dependency "../../../../keyring" {
                tailf:xpath-root 3;
              }
              type union {
                type enumeration {
                  enum "default" {
                    tailf:info
                      "Use global keyring";
                  }
                }
                type string {
                  tailf:info
                    "WORD;;Name of the keyring to use";
                }
              }
            }
          }
          container self-identity {
            tailf:info
              "Specify Identity to use";
            choice self-identity-choice {
              container address {
                tailf:info
                  "Use IPv4 address";
                presence "true";
              }
              container fqdn {
                tailf:info
                  "Use FQDN";
                presence "true";
              }
              leaf user-fqdn {
                tailf:info
                  "Use user FQDN";
                type string {
                  tailf:info
                    "WORD;;User FQDN <user@full.domain.name>";
                }
              }
            }
          }
          container match {
            tailf:info
              "Match values of peer";
            leaf fvrf {
              tailf:info
                "fvrf of the profile";
              tailf:cli-diff-dependency "../../../../../vrf/definition" {
                tailf:xpath-root 3;
              }
              type union {
                type string {
                  tailf:info
                    "WORD;;fvrf name (default: global)";
                }
                type enumeration {
                  enum "any" {
                    tailf:info
                      "any fvrf";
                  }
                }
              }
            }
            container identity {
              tailf:info
                "Peer identity";
              list group {
                tailf:info
                  "Group name";
                tailf:cli-suppress-mode;
                tailf:cli-delete-when-empty;
                key "name";
                leaf name {
                  type string {
                    tailf:info
                      "WORD;;Specify the group name";
                  }
                }
              }
              container address {
                tailf:info
                  "IP Address(es)";
                list ipv4 {
                  tailf:cli-drop-node-name;
                  tailf:cli-suppress-mode;
                  tailf:cli-delete-when-empty;
                  key "address mask";
                  leaf address {
                    type inet:ipv4-address {
                      tailf:info
                        "A.B.C.D;;IP address prefix";
                    }
                  }
                  leaf mask {
                    type inet:ipv4-address {
                      tailf:info
                        "A.B.C.D;;specify mask";
                    }
                  }
                  leaf vrf {
                    tailf:cli-drop-node-name;
                    tailf:cli-diff-dependency "../../../../../../../../ip/vrf" {
                      tailf:xpath-root 3;
                    }
                    tailf:cli-diff-dependency "../../../../../../../../vrf/definition" {
                      tailf:xpath-root 3;
                    }
                    type string {
                      tailf:info
                        "WORD;;Specify the F VRF (default global)";
                    }
                  }
                }
                container ipv4-host {
                  tailf:cli-drop-node-name;
                  list ipv4 {
                    tailf:cli-drop-node-name;
                    tailf:cli-suppress-mode;
                    tailf:cli-delete-when-empty;
                    key "address";
                    leaf address {
                      type inet:ipv4-address {
                        tailf:info
                          "A.B.C.D;;IP address prefix";
                      }
                    }
                    leaf vrf {
                      tailf:cli-drop-node-name;
                      tailf:cli-diff-dependency "../../../../../../../../../ip/vrf" {
                        tailf:xpath-root 3;
                      }
                      tailf:cli-diff-dependency "../../../../../../../../../vrf/definition" {
                        tailf:xpath-root 3;
                      }
                      type string {
                        tailf:info
                          "WORD;;Specify the F VRF (default global)";
                      }
                    }
                  }
                }
                list ipv6 {
                  tailf:info
                    "IPv6 Address(es)";
                  tailf:cli-suppress-mode;
                  tailf:cli-delete-when-empty;
                  key "address";
                  leaf address {
                    type ipv6-prefix {
                      tailf:info
                        "X:X:X:X::X/<0-128>;;IPv6 address prefix";
                    }
                  }
                  leaf vrf {
                    tailf:cli-drop-node-name;
                    tailf:cli-diff-dependency "../../../../../../../../ip/vrf" {
                      tailf:xpath-root 3;
                    }
                    tailf:cli-diff-dependency "../../../../../../../../vrf/definition" {
                      tailf:xpath-root 3;
                    }
                    type string {
                      tailf:info
                        "WORD;;Specify the F VRF (default global)";
                    }
                  }
                }
              }
              container host {
                tailf:info
                  "match a hostname/domain";
                leaf domain-name {
                  tailf:cli-drop-node-name;
                  tailf:cli-full-command;
                  type string {
                    tailf:info
                      "WORD;Specify the domain name";
                  }
                }
                list domain-name-vrf {
                  tailf:cli-drop-node-name;
                  tailf:cli-suppress-mode;
                  tailf:cli-delete-when-empty;
                  tailf:cli-incomplete-command;
                  tailf:cli-incomplete-no;
                  key "domain";
                  leaf domain {
                    type string {
                      tailf:info
                        "WORD;;Specify the domain name";
                    }
                  }
                  leaf vrf {
                    tailf:cli-drop-node-name;
                    tailf:cli-diff-dependency "../../../../../../../../ip/vrf" {
                      tailf:xpath-root 3;
                    }
                    tailf:cli-diff-dependency "../../../../../../../../vrf/definition" {
                      tailf:xpath-root 3;
                    }
                    type string {
                      tailf:info
                        "WORD;;Specify the F VRF (default global)";
                    }
                  }
                }
                container domain {
                  tailf:info
                    "match domain instead of exact";
                  list domain-name-vrf {
                    tailf:cli-drop-node-name;
                    tailf:cli-suppress-mode;
                    tailf:cli-delete-when-empty;
                    tailf:cli-incomplete-command;
                    tailf:cli-incomplete-no;
                    key "domain";
                    leaf domain {
                      type string {
                        tailf:info
                          "WORD;;Specify the domain name";
                      }
                    }
                    leaf vrf {
                      tailf:cli-drop-node-name;
                      tailf:cli-diff-dependency "../../../../../../../../../ip/vrf" {
                        tailf:xpath-root 3;
                      }
                      tailf:cli-diff-dependency "../../../../../../../../../vrf/definition" {
                        tailf:xpath-root 3;
                      }
                      type string {
                        tailf:info
                          "WORD;;Specify the VRF (default global)";
                      }
                    }
                  }
                  leaf domain-name {
                    tailf:cli-drop-node-name;
                    tailf:cli-full-command;
                    type string {
                      tailf:info
                        "WORD;;Specify the domain name";
                    }
                  }
                }
              }
            }
          }
          container client {
            tailf:info
              "Specify client configuration settings";
            container authentication {
              tailf:info
                "Use Extended Authentication";
              leaf list {
                tailf:info
                  "AAA authentication list to use";
                type string {
                  tailf:info
                    "WORD;;Named authentication list.";
                }
              }
            }
            container configuration {
              tailf:info
                "Specify client configuration settings";
              container address {
                tailf:info
                  "Specify client network address configuration";
                leaf initiate {
                  tailf:info
                    "Push the network address to the client";
                  type empty;
                }
                leaf respond {
                  tailf:info
                    "Respond to network address requests from the client";
                  type empty;
                }
              }
            }
          }
          container isakmp {
            tailf:info
              "ISAKMP Authorization command";
            container authorization {
              tailf:info
                "Authorization parameters.";
              leaf list {
                tailf:info
                  "AAA authorization list to use";
                type string {
                  tailf:info
                    "WORD;;Named authorization list.";
                }
              }
            }
          }
          container keepalive {
            tailf:info
              "Set a keepalive interval for use with IOS peers";
            tailf:cli-compact-syntax;
            tailf:cli-sequence-commands {
              tailf:cli-reset-siblings;
            }
            leaf seconds {
              tailf:cli-drop-node-name;
              tailf:cli-incomplete-command;
              type uint16 {
                tailf:info
                  "<10-3600>;;Number of seconds between keep alives";
                range "10..3600";
              }
            }
            leaf retry {
              tailf:info
                "Retry interval if keepalive fails";
              type uint8 {
                tailf:info
                  "<2-60>;;Number of seconds between retries if keepalive fails";
                range "2..60";
              }
            }
          }
          container local-address {
            tailf:info
              "Interface to use for local address for this isakmp profile";
            choice local-address-choice {
              leaf ipv4-address {
                tailf:cli-drop-node-name;
                type inet:ipv4-address {
                  tailf:info
                    "A.B.C.D;;Specify an IPv4 address to bind to";
                }
              }
              leaf ipv6-address {
                tailf:cli-drop-node-name;
                type inet:ipv6-address {
                  tailf:info
                    "X:X:X:X::X;;Specify an IPv6 address to bind to";
                }
              }
              container interface {
                tailf:cli-drop-node-name;
                uses interface-name-grouping;
              }
            }
          }
          leaf virtual-template {
            tailf:info
              "Specify the virtual-template for dynamic interface creation.";
            tailf:cli-full-command;
            type uint8 {
              tailf:info
                "<1-200>;;Virtual-template Number to clone";
              range "1..200";
            }
          }
          leaf qos-group {
            tailf:info
              "Apply a Qos policy class map for this profile";
            type uint16 {
              tailf:info
                "<1-1023>;;Qos Group value";
              range "1..1023";
            }
          }
        }
        list policy {
          tailf:info
            "Set policy for an ISAKMP protection suite";
          tailf:cli-mode-name "config-isakmp";
          key "priority";
          leaf priority {
            type uint16 {
              tailf:info
                "<1-10000>;;Priority of protection suite";
            }
          }
          container encr {
            tailf:info
              "Set encryption algorithm for protection suite";
            tailf:cli-compact-syntax;
            tailf:cli-sequence-commands {
              tailf:cli-reset-siblings;
            }
            leaf algorithm {
              tailf:cli-drop-node-name;
              type enumeration {
                enum "des" {
                  tailf:info
                    "DES - Data Encryption Standard (56 bit keys).";
                }
                enum "3des" {
                  tailf:info
                    "Three key triple DES";
                }
                enum "aes" {
                  tailf:info
                    "AES - Advanced Encryption Standard.";
                }
              }
              default "des";
            }
            leaf bits {
              when "../algorithm = 'aes'" {
                tailf:xpath-root 3;
                tailf:dependency "../algorithm";
              }
              tailf:cli-drop-node-name;
              type enumeration {
                enum "128" {
                  tailf:info
                    "128 bit keys.";
                }
                enum "192" {
                  tailf:info
                    "192 bit keys.";
                }
                enum "256" {
                  tailf:info
                    "256 bit keys.";
                }
              }
              default "128";
            }
          }
          leaf hash {
            tailf:info
              "Set hash algorithm for protection suite";
            type enumeration {
              enum "md5" {
                tailf:info
                  "Message Digest 5";
              }
              enum "sha" {
                tailf:info
                  "Secure Hash Standard";
              }
              enum "sha256" {
                tailf:info
                  "Secure Hash Standard";
              }
            }
            default "sha";
          }
          leaf authentication {
            tailf:info
              "Set authentication method for protection suite";
            type enumeration {
              enum "pre-share" {
                tailf:info
                  "Pre-Shared Key";
              }
              enum "rsa-encr" {
                tailf:info
                  "Rivest-Shamir-Adleman Encryption";
              }
              enum "rsa-sig" {
                tailf:info
                  "Rivest-Shamir-Adleman Signature";
              }
            }
          }
          leaf group {
            tailf:info
              "Set the Diffie-Hellman group";
            type enumeration {
              enum "1" {
                tailf:info
                  "Diffie-Hellman group 1 (768 bit)";
              }
              enum "2" {
                tailf:info
                  "Diffie-Hellman group 2 (1024 bit)";
              }
              enum "5" {
                tailf:info
                  "Diffie-Hellman group 5 (1536 bit)";
              }
              enum "14" {
                tailf:info
                  "Diffie-Hellman group 14 (2048 bit)";
              }
              enum "15" {
                tailf:info
                  "Diffie-Hellman group 15 (3072 bit)";
              }
              enum "16" {
                tailf:info
                  "Diffie-Hellman group 16 (4096 bit)";
              }
              enum "19" {
                tailf:info
                  "Diffie-Hellman group 19 (256 bit ecp)";
              }
              enum "20" {
                tailf:info
                  "Diffie-Hellman group 20 (384 bit ecp)";
              }
              enum "21" {
                tailf:info
                  "Diffie-Hellman group 21 (521 bit ecp)";
              }
              enum "24" {
                tailf:info
                  "Diffie-Hellman group 24 (2048 bit, 256 bit subgroup)";
              }
            }
          }
          leaf lifetime {
            tailf:info
              "Set lifetime for ISAKMP security association";
            type uint32 {
              tailf:info
                "<60-86400>;;lifetime in seconds";
              range "60..86400";
            }
            default "86400";
          }
        }
        container keepalive {
          tailf:info
            "Set a keepalive interval for use with IOS peers";
          tailf:cli-compact-syntax;
          tailf:cli-sequence-commands {
            tailf:cli-reset-siblings;
          }
          leaf seconds {
            tailf:cli-drop-node-name;
            type uint16 {
              tailf:info
                "<10-3600>;;Number of seconds between keep alives";
              range "10..3600";
            }
          }
          leaf retry-seconds {
            tailf:cli-drop-node-name;
            tailf:cli-optional-in-sequence;
            type uint8 {
              tailf:info
                "<2-60>;;Number of seconds between retries if keepalive fails";
              range "2..60";
            }
          }
          leaf option {
            tailf:cli-drop-node-name;
            type enumeration {
              enum "periodic" {
                tailf:info
                  "When using Dead Peer Detection (DPD), send periodic DPD messages";
              }
              enum "on-demand" {
                tailf:info
                  "When using Dead Peer Detection (DPD), send DPD messages only as needed";
              }
            }
            default "on-demand";
          }
        }
        container nat {
          tailf:info
            "Set a nat  keepalive interval for use with IOS peers";
          container keepalive {
            tailf:info
              "Set a keepalive interval for use with IOS peers";
            leaf seconds {
              tailf:cli-drop-node-name;
              type uint16 {
                tailf:info
                  "<5-3600>;;Number of seconds between keep alives";
                range "5..3600";
              }
            }
          }
        }
        list key {
          tailf:info
            "Set pre-shared key for remote peer";
          tailf:cli-suppress-mode;
          tailf:cli-delete-when-empty;
          tailf:cli-compact-syntax;
          tailf:cli-sequence-commands;
          key "address";
          leaf address {
            tailf:cli-expose-key-name;
            tailf:info
              "define shared key with IP address";
            type inet:ipv4-address {
              tailf:info
                "A.B.C.D;;Peer IP address";
            }
          }
          leaf encrypted {
            tailf:cli-drop-node-name;
            tailf:cli-prefix-key;
            tailf:cli-optional-in-sequence;
            type enumeration {
              enum "6" {
                tailf:info
                  "Specifies an ENCRYPTED password will follow";
              }
            }
          }
          leaf keystring {
            tailf:cli-drop-node-name;
            tailf:cli-prefix-key;
            tailf:cli-disallow-value "0|6";
            tailf:cli-reset-container;
            tailf:cli-remove-before-change;
            tailf:meta-data "secret-password" {
              tailf:meta-value "crypto isakmp key <PASSWORD> address <key>";
            }
            type string {
              tailf:info
                "WORD;;The UNENCRYPTED (cleartext) user password";
            }
          }
          leaf mask {
            tailf:cli-drop-node-name;
            tailf:cli-optional-in-sequence;
            type inet:ipv4-address {
              tailf:info
                "A.B.C.D;;Peer IP subnet mask";
            }
          }
          leaf no-xauth {
            tailf:info
              "Bypasses XAuth for this peer";
            type empty;
          }
        }
        container key-ipv6-list {
          tailf:cli-drop-node-name;
          list key {
            tailf:info
              "Set pre-shared key for remote peer";
            tailf:cli-suppress-mode;
            tailf:cli-delete-when-empty;
            tailf:cli-compact-syntax;
            tailf:cli-sequence-commands;
            key "ipv6";
            leaf ipv6 {
              tailf:info
                "define shared key with IPv6 address";
              tailf:cli-expose-key-name;
              type ipv6-prefix {
                tailf:info
                  "X:X:X:X::X/<0-128>;;Peer IPv6 prefix";
              }
            }
            leaf encrypted {
              tailf:cli-drop-node-name;
              tailf:cli-prefix-key;
              tailf:cli-optional-in-sequence;
              type enumeration {
                enum "6" {
                  tailf:info
                    "Specifies an ENCRYPTED password will follow";
                }
              }
            }
            leaf keystring {
              tailf:cli-drop-node-name;
              tailf:cli-prefix-key;
              tailf:cli-disallow-value "0|6";
              tailf:cli-reset-container;
              tailf:cli-remove-before-change;
              tailf:meta-data "secret-password" {
                tailf:meta-value "crypto isakmp key <PASSWORD> address ipv6 <key>";
              }
              type string {
                tailf:info
                  "WORD;;The UNENCRYPTED (cleartext) user password";
              }
            }
            leaf address {
              tailf:info
                "define shared key with IP address";
              tailf:cli-prefix-key;
              type empty;
            }
            leaf no-xauth {
              tailf:info
                "Bypasses XAuth for this peer";
              type empty;
            }
          }
        }
        container key-hostname-list {
          tailf:cli-drop-node-name;
          list key {
            tailf:info
              "Set pre-shared key for remote peer";
            tailf:cli-suppress-mode;
            tailf:cli-delete-when-empty;
            tailf:cli-compact-syntax;
            tailf:cli-sequence-commands;
            key "hostname";
            leaf hostname {
              tailf:cli-expose-key-name;
              tailf:info
                "define shared key with hostname";
              type string {
                tailf:info
                  "WORD;;hostname of peer with whom the key is shared";
              }
            }
            leaf encrypted {
              tailf:cli-drop-node-name;
              tailf:cli-prefix-key;
              tailf:cli-optional-in-sequence;
              type enumeration {
                enum "6" {
                  tailf:info
                    "Specifies an ENCRYPTED password will follow";
                }
              }
            }
            leaf keystring {
              tailf:cli-drop-node-name;
              tailf:cli-prefix-key;
              tailf:cli-disallow-value "0|6";
              tailf:cli-reset-container;
              tailf:cli-remove-before-change;
              tailf:meta-data "secret-password" {
                tailf:meta-value "crypto isakmp key <PASSWORD> hostname <key>";
              }
              type string {
                tailf:info
                  "WORD;;The UNENCRYPTED (cleartext) user password";
              }
            }
            leaf no-xauth {
              tailf:info
                "Bypasses XAuth for this peer";
              type empty;
            }
          }
        }
      }
      container ipsec {
        tailf:info
          "Configure IPSEC policy";
        container optional {
          tailf:info
            "Enable optional encryption for IPSec";
          tailf:cli-delete-when-empty;
          presence "true";
          leaf retry {
            tailf:info
              "Configure length of IPSec retry interval";
            type uint32 {
              tailf:info
                "<60-86400>;;Number of seconds between IPSec retries";
              range "60..86400";
            }
          }
        }
        container security-association {
          tailf:info
            "Security association parameters";
          leaf idle-time {
            tailf:info
              "Automatically delete IPSec SAs after a given idle period.";
            type uint32 {
              tailf:info
                "<60-86400>;;Idle time at which IPSec SAs are deleted";
              range "60..86400";
            }
          }
          container lifetime {
            tailf:info
              "security association lifetime";
            leaf kilobytes {
              tailf:info
                "Volume-based key duration";
              type union {
                type uint32 {
                  tailf:info
                    "<2560-4294967295>;;Security association duration in kilobytes encrypted";
                }
                type enumeration {
                  enum "disable" {
                    tailf:info
                      "Disable Volume-based Rekey";
                  }
                }
              }
            }
            leaf seconds {
              tailf:info
                "Time-based key duration";
              type uint32 {
                tailf:info
                  "<120-86400>;;Security association duration in seconds";
                range "120..86400";
              }
            }
          }
          container replay {
            tailf:info
              "Set replay checking.";
            leaf disable {
              tailf:info
                "Disable replay checking";
              type empty;
            }
            leaf window-size {
              tailf:info
                "Set replay window size.";
              type ipsec-window-size-type;
            }
          }
        }
        list transform-set {
          tailf:info
            "Define transform and settings";
          tailf:cli-mode-name "cfg-crypto-trans";
          tailf:cli-compact-syntax;
          tailf:cli-incomplete-command;
          key "name";
          leaf name {
            type string {
              tailf:info
                "WORD;;Transform set tag";
            }
          }
          leaf transform1 {
            tailf:cli-drop-node-name;
            tailf:cli-hide-in-submode;
            type enumeration {
              enum "ah-md5-hmac" {
                tailf:info
                  "AH-HMAC-MD5 transform";
              }
              enum "ah-sha-hmac" {
                tailf:info
                  "AH-HMAC-SHA transform";
              }
              enum "ah-sha256-hmac" {
                tailf:info
                  "AH-HMAC-SHA256 transform";
              }
              enum "ah-sha384-hmac" {
                tailf:info
                  "AH-HMAC-SHA384 transform";
              }
              enum "ah-sha512-hmac" {
                tailf:info
                  "AH-HMAC-SHA512 transform";
              }
            }
          }
          leaf transform2 {
            tailf:cli-drop-node-name;
            tailf:cli-hide-in-submode;
            type enumeration {
              enum "esp-3des" {
                tailf:info
                  "ESP transform using 3DES(EDE) cipher (168 bits)";
              }
              enum "esp-aes" {
                tailf:info
                  "ESP transform using AES cipher";
              }
              enum "esp-des" {
                tailf:info
                  "ESP transform using DES cipher (56 bits)";
              }
              enum "esp-gcm" {
                tailf:info
                  "ESP transform using GCM";
              }
              enum "esp-gmac" {
                tailf:info
                  "ESP transform using GMAC cipher";
              }
              enum "esp-null" {
                tailf:info
                  "ESP transform w/o cipher";
              }
              enum "esp-seal" {
                tailf:info
                  "ESP transform using SEAL cipher (160 bits)";
              }
            }
          }
          leaf transform2-bits {
            tailf:cli-drop-node-name;
            tailf:cli-hide-in-submode;
            type enumeration {
              enum "128" {
                tailf:info
                  "128 bit keys (with transform2)";
              }
              enum "192" {
                tailf:info
                  "192 bit keys (with transform2)";
              }
              enum "256" {
                tailf:info
                  "256 bit keys (with transform2)";
              }
            }
            default "128";
          }
          leaf transform3 {
            tailf:cli-drop-node-name;
            tailf:cli-hide-in-submode;
            type enumeration {
              enum "esp-md5-hmac" {
                tailf:info
                  "ESP transform using HMAC-MD5 auth";
              }
              enum "esp-sha-hmac" {
                tailf:info
                  "ESP transform using HMAC-SHA auth";
              }
              enum "esp-sha256-hmac" {
                tailf:info
                  "ESP transform using HMAC-SHA256 auth";
              }
              enum "esp-sha384-hmac" {
                tailf:info
                  "ESP transform using HMAC-SHA384 auth";
              }
              enum "esp-sha512-hmac" {
                tailf:info
                  "ESP transform using HMAC-SHA512 auth";
              }
            }
          }
          leaf transform4 {
            tailf:cli-drop-node-name;
            tailf:cli-hide-in-submode;
            type enumeration {
              enum "comp-lzs" {
                tailf:info
                  "IP Compression using the LZS compression algorithm";
              }
            }
          }
          container mode {
            tailf:info
              "encapsulation mode (transport/tunnel)";
            choice mode-choice {
              container transport {
                tailf:info
                  "transport (payload encapsulation) mode";
                presence "true";
                leaf require {
                  tailf:info
                    "Accept only the configured encapsulation mode.";
                  type empty;
                }
              }
              leaf tunnel {
                tailf:info
                  "tunnel (datagram encapsulation) mode";
                type empty;
              }
              default "tunnel";
            }
          }
        }
        container default {
          tailf:info
            "Default transform-set";
          leaf transform-set {
            tailf:cli-boolean-no;
            tailf:cli-full-command;
            type boolean;
            default "true";
          }
        }
        leaf fragmentation {
          tailf:info
            "Handling of fragmentation of near-MTU sized packets";
          type enumeration {
            enum "after-encryption" {
              tailf:info
                "Perform fragmentation of large packets after IPSec encapsulation.";
            }
            enum "before-encryption" {
              tailf:info
                "Perform fragmentation of large packets before IPSec encapsulation.";
            }
          }
        }
        leaf df-bit {
          tailf:info
            "Handling of encapsulated DF bit.";
          type enumeration {
            enum "clear" {
              tailf:info
                "Clear DF bit for encapsulated packets.";
            }
            enum "copy" {
              tailf:info
                "Copy DF bit from inner for encapsulated packets.";
            }
            enum "set" {
              tailf:info
                "Set DF bit for encapsulated packets.";
            }
          }
        }
        leaf nat-transparency {
          tailf:info
            "IPsec NAT transparency model";
          type enumeration {
            enum "spi-matching" {
              tailf:info
                "Match inbound SPI to outbound SPI for IPsec aware NAT";
            }
            enum "udp-encapsulation" {
              tailf:info
                "UDP encapsulation of IPsec protocols";
            }
          }
        }
        list profile {
          tailf:info
            "Configure an ipsec policy profile";
          tailf:cli-mode-name "ipsec-profile";
          key "name";
          leaf name {
            type string {
              tailf:info
                "WORD;;Profile name";
            }
          }
          container set {
            tailf:info
              "Set values for encryption/decryption";
            container security-association {
              tailf:info
                "Security association parameters";
              leaf dfbit {
                tailf:info
                  "Handling of encapsulated DF bit.";
                tailf:cli-full-command;
                type enumeration {
                  enum "clear" {
                    tailf:info
                      "Clear DF bit for encapsulated packets.";
                  }
                  enum "copy" {
                    tailf:info
                      "Copy DF bit from inner for encapsulated packets.";
                  }
                  enum "set" {
                    tailf:info
                      "Set DF bit for encapsulated packets.";
                  }
                }
              }
              container lifetime {
                tailf:info
                  "security association lifetime";
                leaf kilobytes {
                  tailf:info
                    "Volume-based key duration";
                  type union {
                    type uint32 {
                      tailf:info
                        "<2560-4294967295>;;Security association duration in kilobytes encrypted";
                    }
                    type enumeration {
                      enum "disable" {
                        tailf:info
                          "Disable Volume-based Rekey";
                      }
                    }
                  }
                }
                choice time-based-choice {
                  default "seconds";
                  leaf seconds {
                    tailf:info
                      "Time-based key duration";
                    type uint32 {
                      tailf:info
                        "<120-86400>;;Security association duration in seconds";
                      range "120..86400";
                    }
                    default "3600";
                  }
                  leaf days {
                    tailf:info
                      "Time-based key duration in days";
                    type uint8 {
                      tailf:info
                        "<1-30>;;Security association duration in days";
                      range "1..30";
                    }
                  }
                }
              }
              container idle-time {
                tailf:info
                  "Automatically delete IPSec SAs after a given idle period.";
                tailf:cli-compact-syntax;
                tailf:cli-sequence-commands {
                  tailf:cli-reset-siblings;
                }
                leaf seconds {
                  tailf:cli-drop-node-name;
                  type uint32 {
                    tailf:info
                      "<60-86400>;;Idle time at which IPSec SAs are deleted";
                    range "60..86400";
                  }
                }
                leaf default {
                  tailf:info
                    "All SAs idle-out reset to default peer";
                  type empty;
                }
              }
              container replay {
                tailf:info
                  "Set replay checking.";
                leaf disable {
                  tailf:info
                    "Disable replay checking";
                  type empty;
                }
                leaf window-size {
                  tailf:info
                    "Set replay window size.";
                  type ipsec-window-size-type;
                }
              }
              container dummy {
                tailf:info
                  "Enable transmitting dummy packets";
                choice dummy-choice {
                  leaf pps {
                    tailf:info
                      "Simulated traffic rate (in pps)";
                    type uint8 {
                      tailf:info
                        "<0-25>;;Rate of simulated traffic (in PPS)";
                      range "0..25";
                    }
                  }
                  leaf seconds {
                    tailf:info
                      "Simulated traffic rate (in seconds)";
                    type uint16 {
                      tailf:info
                        "<1-3600>;;Rate of simulated traffic (seconds between packets)";
                      range "1..3600";
                    }
                  }
                }
              }
              leaf ecn {
                tailf:info
                  "Handling of ECN bit";
                tailf:cli-full-command;
                type enumeration {
                  enum "discard" {
                    tailf:info
                      "Discard the Explicit Congestion Notification bits on decryption";
                  }
                  enum "propagate" {
                    tailf:info
                      "Propagate the Explicit Congestion Notification bits on decryption (RFC4301)";
                  }
                }
              }
            }
            leaf transform-set {
              tailf:info
                "Specify list of transform sets in priority order";
              tailf:non-strict-leafref {
                path "../../../../../crypto/ipsec/transform-set/name";
              }
              type string {
                tailf:info
                  "WORD;;Proposal tag";
              }
            }
            leaf pfs {
              tailf:info
                "Specify pfs settings";
              tailf:cli-full-command;
              type isakmp-pfs-type;
            }
            leaf identity {
              tailf:info
                "Identity restriction.";
              type string {
                tailf:info
                  "WORD;;Identity name";
              }
            }
            leaf mixed-mode {
              tailf:info
                "Turn on IPSec mixed-mode";
              tailf:cli-full-command;
              type empty;
            }
            choice ike-profile {
              leaf isakmp-profile {
                tailf:info
                  "Specify isakmp Profile";
                tailf:non-strict-leafref {
                  path "../../../../../crypto/isakmp/profile/name";
                }
                type string {
                  tailf:info
                    "WORD;;Name the isakmp profile";
                }
              }
              leaf ikev2-profile {
                tailf:info
                  "Specify ikev2 Profile";
                tailf:non-strict-leafref {
                  path "../../../../../crypto/ikev2/profile/name";
                }
                type string {
                  tailf:info
                    "WORD;;Profile name";
                }
              }
            }
          }
          leaf responder-only {
            tailf:info
              "Do not initiate SAs from this device";
            tailf:cli-full-command;
            type empty;
          }
        }
      }
      container call {
        tailf:info
          "Configure Crypto Call Admission Control";
        container admission {
          tailf:info
            "Configure Crypto Call Admission Control";
          container limit {
            tailf:info
              "Configure Crypto Call Admission Control limits";
            container ike {
              tailf:info
                "Configure Crypto Call Admission Control active IKE SA limit";
              leaf in-negotiation-sa {
                tailf:info
                  "Maximum number of in-negotiation IKE SAs allowed";
                type uint32 {
                  tailf:info
                    "<10-99999>;;maximum in-negotiation IKE SA limit";
                  range "10..99999";
                }
              }
            }
          }
        }
      }
      container gdoi {
        tailf:info
          "Configure GDOI policy";
        list group {
          tailf:info
            "Define a GDOI group";
          tailf:cli-mode-name "config-gdoi-group";
          key "name";
          leaf name {
            tailf:cli-disallow-value "ipv6";
            type string {
              tailf:info
                "WORD;;Group Name";
            }
          }
          leaf ipv6 {
            tailf:cli-prefix-key;
            type empty;
          }
          container identity {
            tailf:info
              "Set the identity of the group";
            choice identify-choice {
              leaf number {
                tailf:info
                  "Set the identity of the group as a number";
                type uint32 {
                  tailf:info
                    "<0-2147483647>;;Set the group number";
                }
              }
              container address {
                tailf:info
                  "Set the identity of the group as an address";
                leaf ipv4 {
                  tailf:info
                    "Set the identity of the group as an IPv4 address";
                  type inet:ipv4-address {
                    tailf:info
                      "A.B.C.D;;Group IPv4 address";
                  }
                }
              }
            }
          }
          container server {
            tailf:info
              "Set the group server for of the group";
            container local {
              tailf:info
                "Identify a group server defined locally";
              tailf:cli-add-mode;
              tailf:cli-mode-name "gdoi-local-server";
              tailf:cli-delete-when-empty;
              presence "true";
              must "not(../address/ipv4/name)" {
                tailf:xpath-root 3;
                error-message "Cannot Configure the key server as local.";
                tailf:dependency "../address/ipv4/name";
              }
              tailf:cli-diff-dependency "../address/ipv4/name" {
                tailf:xpath-root 3;
                tailf:cli-trigger-on-set;
              }
              container rekey {
                tailf:info
                  "Configure rekey policy for the group";
                container lifetime {
                  tailf:info
                    "Define the rekey lifetime";
                  choice lifetime-choice {
                    leaf seconds {
                      tailf:info
                        "Time-based key duration";
                      type uint32 {
                        tailf:info
                          "<300-86400>;;Lifetime in seconds";
                      }
                      default "86400";
                    }
                    leaf days {
                      type uint32 {
                        tailf:info
                          "Lifetime in days";
                      }
                    }
                    default "seconds";
                  }
                }
                container retransmit {
                  tailf:info
                    "Define the rekey retransmission parameters";
                  tailf:cli-compact-syntax;
                  tailf:cli-sequence-commands {
                    tailf:cli-reset-siblings;
                  }
                  leaf number-of-seconds {
                    tailf:cli-drop-node-name;
                    type uint8 {
                      tailf:info
                        "<10-60>;;Retransmit after this many seconds";
                      range "10..60";
                    }
                  }
                  choice retransmit-choice {
                    leaf number {
                      tailf:info
                        "Retransmit this many times";
                      type uint8 {
                        tailf:info
                          "<1-10>;;Number of retransmissions";
                        range "1..10";
                      }
                    }
                    leaf periodic {
                      type empty;
                    }
                  }
                }
                container authentication {
                  tailf:info
                    "Identify the rekey authentication keypair";
                  tailf:cli-compact-syntax;
                  tailf:cli-sequence-commands {
                    tailf:cli-reset-siblings;
                  }
                  choice authentication-choice {
                    leaf mypubkey {
                      tailf:info
                        "Identify a keypair associated with this device";
                      type empty;
                    }
                    leaf pubkey {
                      type empty;
                    }
                  }
                  leaf rsa {
                    tailf:info
                      "Identify an RSA keypair";
                    type string {
                      tailf:info
                        "WORD;;Key name";
                    }
                  }
                }
                container transport {
                  tailf:info
                    "Specify the rekey distribution method";
                  leaf unicast {
                    tailf:info
                      "specify unicast rekey distribution";
                    type empty;
                  }
                }
              }
              container replay {
                container time {
                  leaf window-size {
                    type uint32;
                  }
                }
              }
              container sa {
                tailf:info
                  "Configure a security association";
                list ipsec {
                  tailf:info
                    "Configure an IPsec SA";
                  tailf:cli-mode-name "gdoi-sa-ipsec";
                  key "id";
                  leaf id {
                    type uint32 {
                      tailf:info
                        "<1-65535>;;Sequence to insert into SA list";
                      range "1..65535";
                    }
                  }
                  leaf profile {
                    tailf:info
                      "Configure an ipsec profile for the SA";
                    tailf:non-strict-leafref {
                      path "../../../../../../../../crypto/ipsec/profile/name";
                    }
                    type string {
                      tailf:info
                        "WORD;;Profile name";
                    }
                  }
                  container match {
                    tailf:info
                      "Match characteristics of packets to encrypt";
                    container address {
                      tailf:info
                        "Match addresses of packets to encrypt";
                      choice address-choice {
                        leaf ipv4 {
                          tailf:info
                            "Match ipv4 packets";
                          type ext-ip-acl-type;
                        }
                        leaf ipv6 {
                          tailf:info
                            "Match ipv6 packets";
                          tailf:non-strict-leafref {
                            path "../../../../../../../../../../ipv6/access-list/named-acl/name";
                          }
                          type string {
                            tailf:info
                              "WORD;;IPv6 access list";
                          }
                        }
                      }
                    }
                  }
                  container replay {
                    tailf:info
                      "Set replay method";
                    container counter {
                      tailf:info
                        "Enable anti-replay check for single source traffic by using sequence number";
                      leaf window-size {
                        tailf:info
                          "Set replay window size.";
                        type ipsec-window-size-type;
                      }
                    }
                  }
                  container tag {
                    tailf:info
                      "Set inline tagging method";
                    container cts {
                      tailf:info
                        "Cisco Trust Security";
                      leaf sgt {
                        tailf:info
                          "Security Group Tag";
                        type empty;
                      }
                    }
                  }
                }
              }
              container address {
                tailf:info
                  "Configure server source address";
                leaf ipv4 {
                  tailf:info
                    "Set ipv4 address of local server";
                  type union {
                    type inet:ipv4-address {
                      tailf:info
                        "A.B.C.D;;IPv4 local address";
                    }
                    type string {
                      tailf:info
                        "WORD;;Interface name";
                    }
                  }
                }
              }
              container redundancy {
                tailf:info
                  "Enter cooperative key server configuration mode";
                tailf:cli-add-mode;
                tailf:cli-mode-name "gdoi-coop-ks-config";
                tailf:cli-full-command;
                container local {
                  tailf:info
                    "Local key server configurations";
                  tailf:cli-delete-when-empty;
                  presence "true";
                  leaf priority {
                    tailf:info
                      "Set local server priority";
                    type uint8 {
                      tailf:info
                        "<1-255>;;Local server priority";
                    }
                  }
                }
                container peer {
                  tailf:info
                    "Peer server configurations";
                  container address {
                    tailf:info
                      "Peer server address";
                    leaf ipv4 {
                      tailf:info
                        "Set peer server ipv4 address";
                      type inet:ipv4-address {
                        tailf:info
                          "A.B.C.D;;Peer server ipv4 address";
                      }
                    }
                  }
                }
              }
            }
            container address {
              tailf:info
                "Identify the group server by address";
              list ipv4 {
                tailf:info
                  "Set the IPv4 address of the group server";
                tailf:cli-suppress-mode;
                tailf:cli-delete-when-empty;
                must "not(../../local)" {
                  tailf:xpath-root 3;
                  error-message "Key server is already configured as local";
                  tailf:dependency "../../local";
                }
                tailf:cli-diff-dependency "../../local" {
                  tailf:xpath-root 3;
                  tailf:cli-trigger-on-set;
                }
                key "name";
                leaf name {
                  type inet:ipv4-address {
                    tailf:info
                      "A.B.C.D;;Group server IPv4 address";
                  }
                }
              }
            }
          }
          container client {
            tailf:info
              "Set the group client management/register interface";
            container registration {
              tailf:info
                "Set the group client management/register interface";
              container interface {
                tailf:info
                  "Set the group client management/register interface";
                uses interface-name-grouping;
              }
            }
          }
        }
      }
      list dynamic-map {
        tailf:info
          "Specify a dynamic crypto map template";
        tailf:cli-mode-name "config-crypto-map";
        key "name map-entry";
        leaf name {
          type string {
            tailf:info
              "WORD;;Dynamic crypto map template tag";
          }
        }
        leaf map-entry {
          type uint32 {
            tailf:info
              "<1-65535>;;Sequence to insert into dynamic-map entry";
          }
        }
        container set {
          tailf:info
            "Set values for encryption/decryption";
          leaf isakmp-profile {
            tailf:info
              "Specify isakmp Profile";
            tailf:non-strict-leafref {
              path "../../../../crypto/isakmp/profile/name";
            }
            type string {
              tailf:info
                "WORD;;Name the isakmp profile";
            }
          }
          leaf-list transform-set {
            tailf:info
              "Specify list of transform sets in priority order";
            tailf:cli-replace-all;
            tailf:cli-flat-list-syntax;
            tailf:non-strict-leafref {
              path "../../../../crypto/ipsec/transform-set/name";
            }
            type string {
              tailf:info
                "WORD;;Proposal tag";
            }
          }
        }
        container match {
          tailf:info
            "Match values.";
          leaf address {
            tailf:info
              "Match address of packets to encrypt";
            type ext-acl-type;
          }
        }
      }
      list map {
        tailf:info
          "Enter a crypto map";
        tailf:cli-suppress-mode;
        tailf:cli-delete-when-empty;
        tailf:cli-compact-syntax;
        tailf:cli-sequence-commands;
        tailf:cli-incomplete-command;
        key "name";
        leaf name {
          tailf:cli-disallow-value "ipv6";
          type string {
            tailf:info
              "WORD;;Crypto map tag";
          }
        }
        leaf ipv6 {
          tailf:cli-prefix-key;
          tailf:cli-optional-in-sequence;
          type empty;
        }
        container local-address {
          tailf:info
            "Interface to use for local address for this crypto map";
          tailf:cli-optional-in-sequence;
          uses interface-name-grouping;
        }
        container gdoi {
          tailf:info
            "Configure crypto map gdoi features";
          tailf:cli-optional-in-sequence;
          container fail-close {
            tailf:info
              "Configure crypto map on Fail Close mode";
            tailf:cli-add-mode;
            tailf:cli-mode-name "config-crypto-map-fail-close";
            presence "true";
            container match {
              tailf:info
                "Match address of packets for fail-close";
              leaf address {
                tailf:info
                  "Match address of packets for fail-close.";
                type ext-acl-type;
              }
            }
            leaf activate {
              tailf:info
                "Activate the crypto map to work in fail-close mode";
              type empty;
            }
          }
        }
        list seq-list {
          tailf:cli-drop-node-name;
          tailf:cli-mode-name "config-crypto-map";
          tailf:cli-compact-syntax;
          tailf:cli-sequence-commands;
          tailf:cli-incomplete-command;
          key "id";
          leaf id {
            tailf:cli-suppress-range;
            type uint16 {
              tailf:info
                "<1-65535>;;Sequence to insert into crypto map entry";
            }
          }
          leaf policy {
            tailf:cli-drop-node-name;
            tailf:cli-hide-in-submode;
            tailf:cli-no-value-on-delete;
            type enumeration {
              enum "ipsec-isakmp" {
                tailf:info
                  "IPSEC w/ISAKMP";
              }
              enum "ipsec-manual" {
                tailf:info
                  "IPSEC w/manual keying";
              }
              enum "gdoi" {
                tailf:info
                  "GDOI";
              }
              enum "ckm" {
                tailf:info
                  "configure kgs map";
              }
            }
          }
          leaf dynamic {
            tailf:info
              "Enable dynamic crypto map support";
            tailf:cli-hide-in-submode;
            tailf:cli-optional-in-sequence;
            tailf:cli-no-name-on-delete;
            tailf:cli-no-value-on-delete;
            tailf:cli-full-command;
            when "../policy = 'ipsec-isakmp'" {
              tailf:xpath-root 3;
              tailf:dependency "../policy";
            }
            tailf:non-strict-leafref {
              path "../../../../crypto/dynamic-map/name";
            }
            type string {
              tailf:info
                "WORD;;Name of dynamic-map template";
            }
          }
          leaf profile {
            tailf:info
              "Enable crypto map as a crypto-profile";
            tailf:cli-hide-in-submode;
            tailf:cli-optional-in-sequence;
            tailf:cli-no-name-on-delete;
            tailf:cli-no-value-on-delete;
            tailf:cli-full-command;
            when "../policy = 'ipsec-isakmp'" {
              tailf:xpath-root 3;
              tailf:dependency "../policy";
            }
            tailf:non-strict-leafref {
              path "../../../../crypto/isakmp/profile/name";
            }
            type string {
              tailf:info
                "WORD;;Name for this crypto profile";
            }
          }
          leaf description {
            tailf:cli-break-sequence-commands;
            tailf:info
              "Description of the crypto map statement policy";
            tailf:cli-full-command;
            tailf:cli-preformatted;
            tailf:cli-multi-value;
            type string {
              tailf:info
                "LINE;;A Short description";
            }
          }
          container set {
            tailf:info
              "Set values for encryption/decryption";
            when "../policy != 'gdoi'" {
              tailf:xpath-root 3;
              tailf:dependency "../policy";
            }
            leaf-list transform-set {
              tailf:info
                "Specify list of transform sets in priority order";
              tailf:cli-flat-list-syntax;
              tailf:cli-replace-all;
              tailf:cli-full-command;
              tailf:non-strict-leafref {
                path "../../../../../crypto/ipsec/transform-set/name";
              }
              max-elements 6;
              type string {
                tailf:info
                  "WORD;; Proposal tag";
              }
            }
            leaf isakmp-profile {
              tailf:info
                "Specify isakmp Profile";
              tailf:non-strict-leafref {
                path "../../../../../crypto/isakmp/profile/name";
              }
              type string {
                tailf:info
                  "WORD;;Name the isakmp profile";
              }
            }
            leaf-list peer {
              tailf:info
                "Allowed Encryption/Decryption peer";
              tailf:cli-list-syntax;
              type inet:host {
                tailf:info
                  "Hostname, A.B.C.D or X:X:X:X::X;;Address of peer";
              }
            }
            container security-association {
              tailf:info
                "Security association parameters";
              container level {
                tailf:info
                  "specify a security association granularity level for identities";
                leaf per-host {
                  tailf:info
                    "granularity to host level";
                  type empty;
                }
              }
              leaf dfbit {
                tailf:info
                  "Handling of encapsulated DF bit.";
                tailf:cli-full-command;
                type enumeration {
                  enum "clear" {
                    tailf:info
                      "Clear DF bit for encapsulated packets.";
                  }
                  enum "copy" {
                    tailf:info
                      "Copy DF bit from inner for encapsulated packets.";
                  }
                  enum "set" {
                    tailf:info
                      "Set DF bit for encapsulated packets.";
                  }
                }
              }
              container lifetime {
                tailf:info
                  "security association lifetime";
                leaf kilobytes {
                  tailf:info
                    "Volume-based key duration";
                  type union {
                    type uint32 {
                      tailf:info
                        "<2560-4294967295>;;Security association duration in kilobytes encrypted";
                      range "2560..4294967295";
                    }
                    type enumeration {
                      enum "disable" {
                        tailf:info
                          "Disable Volume-based Rekey";
                      }
                    }
                  }
                }
                choice days-seconds-choice {
                  leaf days {
                    tailf:info
                      "Time-based key duration in days";
                    type uint8 {
                      tailf:info
                        "<1-30>;;Security association duration in days";
                      range "1..30";
                    }
                  }
                  leaf seconds {
                    tailf:info
                      "Time-based key duration in seconds";
                    type uint32 {
                      tailf:info
                        "<120-2592000>;;Security association duration in seconds";
                      range "120..2592000";
                    }
                    default "3600";
                  }
                }
              }
              container idle-time {
                tailf:info
                  "Automatically delete IPSec SAs after a given idle period.";
                tailf:cli-compact-syntax;
                tailf:cli-sequence-commands {
                  tailf:cli-reset-siblings;
                }
                leaf seconds {
                  tailf:cli-drop-node-name;
                  type uint32 {
                    tailf:info
                      "<60-86400>;;Idle time at which IPSec SAs are deleted";
                    range "60..86400";
                  }
                }
                leaf default {
                  tailf:info
                    "All SAs idle-out reset to default peer";
                  type empty;
                }
              }
              container replay {
                tailf:info
                  "Set replay checking.";
                leaf disable {
                  tailf:info
                    "Disable replay checking";
                  type empty;
                }
                leaf window-size {
                  tailf:info
                    "Set replay window size.";
                  type enumeration {
                    enum "1024";
                    enum "512";
                    enum "256";
                    enum "128";
                    enum "64";
                  }
                  default "64";
                }
              }
              container dummy {
                tailf:info
                  "Enable transmitting dummy packets";
                choice dummy-choice {
                  leaf pps {
                    tailf:info
                      "Simulated traffic rate (in pps)";
                    type uint8 {
                      tailf:info
                        "<0-25>;;Rate of simulated traffic (in PPS)";
                      range "0..25";
                    }
                  }
                  leaf seconds {
                    tailf:info
                      "Simulated traffic rate (in seconds)";
                    type uint16 {
                      tailf:info
                        "<1-3600>;;Rate of simulated traffic (seconds between packets)";
                      range "1..3600";
                    }
                  }
                }
              }
              leaf ecn {
                tailf:info
                  "Handling of ECN bit";
                tailf:cli-full-command;
                type enumeration {
                  enum "discard" {
                    tailf:info
                      "Discard the Explicit Congestion Notification bits on decryption";
                  }
                  enum "propagate" {
                    tailf:info
                      "Propagate the Explicit Congestion Notification bits on decryption (RFC4301)";
                  }
                }
              }
            }
            leaf pfs {
              tailf:info
                "Specify pfs settings";
              tailf:cli-full-command;
              type isakmp-pfs-type;
            }
            container reverse-route {
              tailf:info
                "Reverse Route Injection.";
              leaf distance {
                tailf:info
                  "Distance metric for this static route";
                type uint8 {
                  tailf:info
                    "<1-255>;;Routing distance";
                  range "1..255";
                }
                default "1";
              }
              leaf tag {
                tailf:info
                  "Create route and tag it";
                type uint32 {
                  tailf:info
                    "<1-4294967295>;;Routing Tag ID";
                  range "1..4294967295";
                }
              }
            }
            leaf group {
              tailf:info
                "Set the san group parameters";
              tailf:non-strict-leafref {
                path "../../../../gkm/group/name";
              }
              type string {
                tailf:info
                  "WORD;;Set GDOI san group name";
              }
            }
          }
          container gdoi-set {
            tailf:cli-break-sequence-commands;
            tailf:cli-drop-node-name;
            when "../policy = 'gdoi'" {
              tailf:xpath-root 3;
              tailf:dependency "../policy";
            }
            container set {
              tailf:info
                "Set values for encryption/decryption";
              leaf group {
                tailf:info
                  "Set the secure group parameters";
                tailf:non-strict-leafref {
                  path "../../../../../../crypto/gdoi/group/name";
                }
                type string {
                  tailf:info
                    "WORD;;Set the group name";
                }
              }
            }
          }
          container match {
            tailf:info
              "Match values.";
            leaf address {
              tailf:info
                "Match address of packets to encrypt";
              type ext-ip-acl-type;
            }
          }
          container reverse-route {
            tailf:info
              "Reverse Route Injection";
            tailf:cli-compact-syntax;
            tailf:cli-sequence-commands;
            tailf:cli-reset-container;
            tailf:cli-delete-when-empty;
            presence "true";
            leaf remote-peer {
              tailf:info
                "Create route in route table for remote tunnel endpoint";
              tailf:cli-optional-in-sequence;
              type inet:ipv4-address {
                tailf:info
                  "A.B.C.D;;IPv4 address overrides remote tunnel endpoint";
              }
            }
            leaf gateway {
              tailf:info
                "Force encrypted traffic via this preferred gateway";
              tailf:cli-optional-in-sequence;
              when "../remote-peer" {
                tailf:xpath-root 3;
                tailf:dependency "../remote-peer";
              }
              type empty;
            }
            leaf static {
              tailf:info
                "Create routes based on static ACLs permanently";
              type empty;
            }
          }
          container qos {
            tailf:info
              "Quality of Service related commands";
            leaf pre-classify {
              tailf:info
                "Enable QOS classification before packets are tunnel encapsulated";
              type empty;
            }
          }
        }
      }
      container gkm {
        tailf:info
          "Configure GKM (Group Key Management, GDOI or G-IKEv2) Policy";
        list group {
          tailf:info
            "Configure a GKM (Group Key Management, GDOI or G-IKEv2) Group";
          tailf:cli-mode-name "config-gkm-group";
          key "name";
          leaf name {
            type string {
              tailf:info
                "WORD;;Group Name";
            }
          }
          container identity {
            tailf:info
              "Set the identity of the group";
            choice identity-choice {
              leaf number {
                tailf:info
                  "Set the identity of the group as a number";
                type uint32 {
                  tailf:info
                    "<0-4294967295>;;Set the group number";
                }
              }
              container address {
                tailf:info
                  "Set the identity of the group as an address";
                leaf ipv4 {
                  tailf:info
                    "Set the identity of the group as an IPv4 address";
                  type inet:ipv4-address {
                    tailf:info
                      "A.B.C.D;;Group IPv4 address";
                  }
                }
              }
            }
          }
          container server {
            tailf:info
              "Set the group server for of the group";
            list address {
              tailf:info
                "Identify the group server by address";
              tailf:cli-suppress-mode;
              tailf:cli-delete-when-empty;
              tailf:cli-show-long-obu-diffs;
              ordered-by user;
              key "protocol address";
              leaf protocol {
                type enumeration {
                  enum "ipv4" {
                    tailf:info
                      "Set the IPv4 address of the group server";
                  }
                  enum "ipv6" {
                    tailf:info
                      "Set the IPv6 address of the group server";
                  }
                }
              }
              leaf address {
                type union {
                  type inet:ipv4-address {
                    tailf:info
                      "A.B.C.D;;Group server IPv4 address";
                  }
                  type inet:ipv6-address {
                    tailf:info
                      "X:X:X:X::X;;Group server IPv6 address";
                  }
                }
              }
            }
          }
          container client {
            tailf:info
              "Set the group client parameters";
            container protocol {
              tailf:info
                "Group Member Registration & Rekey Protocol";
              leaf gikev2 {
                tailf:info
                  "Use G-IKEv2 Protocol for Registration & Rekey";
                tailf:non-strict-leafref {
                  path "../../../../../ikev2/profile/name";
                }
                type string {
                  tailf:info
                    "WORD;;IKEv2 Profile Name for G-IKEv2 Registration";
                }
              }
            }
            container registration {
              tailf:info
                "Set the group client management/register interface";
              container interface {
                tailf:info
                  "Set the group client management/register interface";
                uses interface-name-grouping;
              }
            }
          }
        }
      }
      container ssl {
        tailf:info
          "Configure Crypto SSL Options";
        list proposal {
          tailf:info
            "Define ssl Proposal";
          tailf:cli-mode-name "config-crypto-ssl-proposal";
          key "name";
          leaf name {
            type string {
              tailf:info
                "WORD;;Name of ssl Proposal";
            }
          }
          leaf-list protection {
            tailf:info
              "Specify the protection algorithms";
            tailf:cli-flat-list-syntax;
            type enumeration {
              enum "rsa-3des-ede-sha1" {
                tailf:info
                  "RSA, 3DES and SHA1";
              }
              enum "rsa-rc4128-md5" {
                tailf:info
                  "RSA, RC4 and MD5";
              }
              enum "rsa-aes128-sha1" {
                tailf:info
                  "RSA, AES128 and SHA1";
              }
              enum "rsa-aes256-sha1" {
                tailf:info
                  "RSA, AES256 and SHA1";
              }
            }
          }
        }
        container authorization {
          tailf:info
            "ssl authorization";
          list policy {
            tailf:info
              "Crypto SSL authorization policy";
            tailf:cli-mode-name "config-crypto-ssl-auth-policy";
            key "name";
            leaf name {
              type string {
                tailf:info
                  "WORD;;Name of the policy";
              }
            }
            leaf pool {
              tailf:info
                "Specify pool";
              type string {
                tailf:info
                  "WORD;;pool";
              }
            }
            container dns {
              tailf:info
                "Specify DNS Addresses";
              tailf:cli-compact-syntax;
              tailf:cli-sequence-commands {
                tailf:cli-reset-siblings;
              }
              leaf primary-server {
                tailf:cli-drop-node-name;
                type inet:ipv4-address {
                  tailf:info
                    "A.B.C.D;;Primary DNS IP address";
                }
              }
              leaf secondary-server {
                tailf:cli-drop-node-name;
                type inet:ipv4-address {
                  tailf:info
                    "A.B.C.D;;Secondary DNS IP address";
                }
              }
            }
            leaf banner {
              tailf:info
                "Specify banner";
              tailf:cli-multi-value;
              type string {
                tailf:info
                  "LINE;;banner string";
              }
            }
            leaf def-domain {
              tailf:info
                "Specify def_domain";
              type string {
                tailf:info
                  "WORD;;def_domain string";
              }
            }
          }
        }
        list policy {
          tailf:info
            "Define SSL policies";
          tailf:cli-mode-name "config-crypto-ssl-policy";
          key "name";
          leaf name {
            type string {
              tailf:info
                "WORD;;Name of ssl policy";
            }
          }
          container ssl {
            tailf:info
              "Specify ssl proposal";
            leaf proposal {
              tailf:info
                "Specify Proposal";
              type string {
                tailf:info
                  "WORD;;Specify the name of proposal to be attached";
              }
            }
          }
          container pki {
            tailf:info
              "Trustpoint options";
            tailf:cli-compact-syntax;
            tailf:cli-sequence-commands {
              tailf:cli-reset-all-siblings;
            }
            leaf trustpoint {
              tailf:info
                "Certificate Trustpoint to authenticate clients";
              tailf:cli-incomplete-command;
              type string {
                tailf:info
                  "WORD;;Trustpoint name";
              }
            }
            leaf sign {
              tailf:info
                "Sign";
              type empty;
            }
          }
          container ip {
            tailf:info
              "ip options";
            container address {
              tailf:info
                "ip address";
              tailf:cli-compact-syntax;
              tailf:cli-sequence-commands {
                tailf:cli-reset-all-siblings;
              }
              leaf local {
                tailf:info
                  "ip address local";
                type inet:ipv4-address {
                  tailf:info
                    "A.B.C.D;;IP address";
                }
              }
              leaf port {
                tailf:info
                  "port configuration";
                type union {
                  type uint16 {
                    tailf:info
                      "443;;Default secure port";
                    range "443";
                  }
                  type uint16 {
                    tailf:info
                      "<1025-65535>;;Port number";
                    range "1025..65535";
                  }
                }
              }
            }
          }
          leaf shutdown {
            tailf:info
              "shutdown";
            type empty;
          }
        }
        list profile {
          tailf:info
            "Define ssl Profiles";
          tailf:cli-mode-name "config-crypto-ssl-profile";
          key "name";
          leaf name {
            type string {
              tailf:info
                "WORD;;Name of ssl profile";
            }
          }
          container match {
            tailf:info
              "Specify the type to match";
            leaf policy {
              tailf:info
                "Specify Policy";
              tailf:cli-remove-before-change;
              tailf:non-strict-leafref {
                path "../../../../../crypto/ssl/policy/name";
              }
              type string {
                tailf:info
                  "WORD;;Specify the name of policy to be attached";
              }
            }
            leaf url {
              tailf:info
                "Specify url";
              type string {
                tailf:info
                  "WORD;;gateway[:port]/domain (specify port if not 443)";
              }
            }
          }
          container aaa {
            tailf:info
              "aaa";
            container authentication {
              tailf:info
                "aaa authentication";
              leaf list {
                tailf:info
                  "aaa authentication list";
                type string {
                  tailf:info
                    "WORD;;Specify the list name";
                }
              }
            }
            container authorization {
              tailf:info
                "aaa authorization";
              container user {
                tailf:info
                  "AAA user authorization";
                tailf:cli-compact-syntax;
                tailf:cli-sequence-commands {
                  tailf:cli-reset-siblings;
                }
                leaf list {
                  tailf:info
                    "AAA method list";
                  type string {
                    tailf:info
                      "WORD;;AAA list name";
                  }
                }
                leaf aaa-username {
                  tailf:cli-drop-node-name;
                  type string {
                    tailf:info
                      "WORD;;AAA username";
                  }
                }
              }
            }
          }
          container authentication {
            tailf:info
              "Specify authentication mode";
            container remote {
              tailf:info
                "remote server";
              leaf user-credentials {
                tailf:info
                  "User credential mode";
                type empty;
              }
            }
          }
          leaf shutdown {
            tailf:info
              "shutdown";
            type empty;
          }
        }
      }
      list tls-tunnel {
        tailf:info
          "Configure Crypto TLS-Tunnel Options";
        tailf:cli-mode-name "config-crypto-tls-tunnel";
        tailf:cli-run-template-enter "crypto tls-tunnel $(name)\\n ! meta-data :: $(.ipath) :: shutdown-container-before-change :: tls-tunnel\\n";
        tailf:cli-exit-command "! exit-meta-data-tls-tunnel";
        tailf:ned-data "." {
          tailf:xpath-root 3;
          tailf:transaction to;
        }
        key "name";
        leaf name {
          type string {
            tailf:info
              "WORD;;Name of TLS-Tunnel";
          }
        }
        list server {
          tailf:info
            "Specify the Server Address";
          tailf:cli-suppress-mode;
          tailf:cli-delete-when-empty;
          tailf:cli-compact-syntax;
          max-elements 2;
          key "protocol address";
          leaf protocol {
            type enumeration {
              enum "ipv4" {
                tailf:info
                  "IPv4 address";
              }
              enum "ipv6" {
                tailf:info
                  "IPv6 address";
              }
            }
          }
          leaf address {
            type union {
              type inet:ipv4-address {
                tailf:info
                  "A.B.C.D;;IPv4 Address";
              }
              type inet:ipv6-address {
                tailf:info
                  "X:X:X:X::X;;IPv6 Address";
              }
            }
          }
          leaf port {
            tailf:info
              "Port Configuration";
            type union {
              type uint16 {
                tailf:info
                  "Default Secure Port";
                range "443";
              }
              type uint16 {
                tailf:info
                  "<1025-65535>;;Port Number";
                range "1025..65535";
              }
            }
          }
        }
        leaf protection {
          tailf:info
            "Cipher-Suite";
          tailf:cli-full-command;
          type enumeration {
            enum "dhe-psk-aes128-cbc-sha1" {
              tailf:info
                "DHE, PSK, AES128-CBC and SHA1";
            }
            enum "dhe-psk-aes256-cbc-sha1" {
              tailf:info
                "DHE, PSK, AES256-CBC and SHA1";
            }
            enum "psk-aes128-cbc-sha1" {
              tailf:info
                "PSK, AES128-CBC and SHA1";
            }
            enum "psk-aes256-cbc-sha1" {
              tailf:info
                "PSK, AES256-CBC and SHA1";
            }
          }
          default "dhe-psk-aes256-cbc-sha1";
        }
        list local-interface {
          tailf:info
            "Specify the WAN interfaces";
          tailf:cli-suppress-mode;
          tailf:cli-delete-when-empty;
          key "name";
          leaf name {
            tailf:cli-diff-dependency "../../../../interface" {
              tailf:xpath-root 3;
            }
            type string {
              tailf:info
                "WORD;;Interface Name";
            }
          }
          leaf priority {
            tailf:info
              "Specify the Interface Priority (1 is highest)";
            type uint8 {
              tailf:info
                "<1-3>;;rank";
              range "1..3";
            }
          }
        }
        container psk {
          tailf:info
            "Specify the Pre-Shared Key";
          tailf:cli-compact-syntax;
          tailf:cli-sequence-commands;
          leaf id {
            tailf:info
              "Key Identity";
            tailf:cli-incomplete-command;
            type string {
              tailf:info
                "WORD;;identity";
            }
          }
          container key {
            tailf:info
              "Specify the Key";
            tailf:cli-flatten-container;
            tailf:cli-compact-syntax;
            tailf:cli-sequence-commands;
            uses crypto-key-grouping;
          }
        }
        container overlay-address {
          tailf:info
            "Specify the Overlay Address";
          tailf:cli-compact-syntax;
          tailf:cli-sequence-commands {
            tailf:cli-reset-siblings;
          }
          tailf:cli-diff-dependency "../../../ip/vrf" {
            tailf:xpath-root 3;
          }
          tailf:cli-diff-dependency "../../../vrf/definition" {
            tailf:xpath-root 3;
          }
          leaf address {
            tailf:cli-drop-node-name;
            tailf:cli-remove-before-change;
            type union {
              type inet:ipv4-address {
                tailf:info
                  "A.B.C.D;;IP Address";
              }
              type inet:ipv6-address {
                tailf:info
                  "X:X:X:X::X;;IPv6 Address";
              }
            }
          }
          leaf vrf {
            tailf:info
              "VRF name";
            type string {
              tailf:info
                "WORD;;VRF";
            }
          }
        }
        leaf shutdown {
          tailf:info
            "Shutdown the TLS-Tunnel";
          tailf:cli-full-command;
          type empty;
        }
      }
    }
    container transport-map {
      tailf:ncs-device-type "cli-ned";
      tailf:display-when "not(../../ncs:module) or ../../ncs:module[ncs:name='tailf-ned-cisco-ios']";
      tailf:info
        "Configure transport map";
      container type {
        tailf:info
          "Specify transport map type";
        tailf:cli-compact-syntax;
        tailf:cli-sequence-commands;
        list persistent {
          tailf:info
            "Persistent transport types";
          tailf:cli-mode-name "config-tmap";
          key "name";
          leaf name {
            type string {
              tailf:info
                "WORD;;Transport map name";
            }
          }
          leaf type {
            tailf:cli-drop-node-name;
            tailf:cli-prefix-key;
            type enumeration {
              enum "ssh" {
                tailf:info
                  "Persistent ssh transport type";
              }
              enum "telnet" {
                tailf:info
                  "Persistent telnet transport type";
              }
              enum "webui" {
                tailf:info
                  "Persistent webui transport type";
              }
            }
          }
          leaf authentication-retries {
            tailf:info
              "Specify number of authentication retries";
            type uint8 {
              tailf:info
                "<0-5>;;Number of authentication retries";
              range "0..5";
            }
          }
          container rsa {
            tailf:info
              "Configure RSA key-pair";
            leaf keypair-name {
              tailf:info
                "Configure RSA key-pair";
              type string {
                tailf:info
                  "WORD;;RSA key-pair name";
              }
            }
          }
          container transport {
            tailf:info
              "Configure interface(s) for the transport";
            container interface {
              tailf:info
                "Configure interface(s) for the transport";
              tailf:cli-compact-syntax;
              uses interface-name-grouping;
            }
          }
        }
      }
    }
    container macro {
      tailf:ncs-device-type "cli-ned";
      tailf:display-when "not(../../ncs:module) or ../../ncs:module[ncs:name='tailf-ned-cisco-ios']";
      tailf:info
        "Create a command macro";
      container auto {
        leaf monitor {
          tailf:cli-boolean-no;
          tailf:cli-full-command;
          type boolean;
          default "true";
        }
      }
      list name {
        tailf:info
          "Name of the macro";
        tailf:cli-suppress-mode;
        tailf:cli-delete-when-empty;
        tailf:cli-compact-syntax;
        tailf:cli-incomplete-command;
        key "name";
        leaf name {
          type string {
            tailf:info
              "WORD;;Name of the macro to apply";
          }
        }
        leaf commands {
          tailf:cli-drop-node-name;
          tailf:cli-no-value-on-delete;
          type string {
            tailf:info
              "LINE;;Quoted string. Use \\r\\n for newline. End delimeter @ is added automatically.";
          }
        }
      }
    }
    container buffers {
      tailf:ncs-device-type "cli-ned";
      tailf:display-when "not(../../ncs:module) or ../../ncs:module[ncs:name='tailf-ned-cisco-ios']";
      tailf:info
        "Adjust system buffer pool parameters";
      container huge {
        tailf:info
          "Huge buffers";
        leaf size {
          tailf:info
            "Size of huge buffers";
          type uint32 {
            tailf:info
              "<18024-65535>;;Size of huge buffers";
            range "18024..65535";
          }
        }
      }
    }
    container track {
      tailf:ncs-device-type "cli-ned";
      tailf:display-when "not(../../ncs:module) or ../../ncs:module[ncs:name='tailf-ned-cisco-ios']";
      tailf:info
        "Object tracking configuration commands";
      list track-object {
        tailf:cli-drop-node-name;
        tailf:cli-mode-name "config-track";
        tailf:cli-compact-syntax;
        tailf:cli-diff-dependency "../../ip/vrf" {
          tailf:xpath-root 3;
        }
        tailf:cli-diff-dependency "../../vrf/definition" {
          tailf:xpath-root 3;
        }
        key "object-number";
        leaf object-number {
          type uint16 {
            tailf:info
              "<1-1000>;;Tracked object";
            range "1..1000";
          }
        }
        choice track-type {
          container rtr {
            tailf:info
              "Response Time Reporter (RTR) entr";
            tailf:cli-hide-in-submode;
            tailf:cli-flatten-container;
            tailf:cli-compact-syntax;
            tailf:cli-sequence-commands;
            leaf operation-number {
              tailf:cli-drop-node-name;
              type uint32 {
                tailf:info
                  "<1-2147483647>;;Entry number";
                range "1..2147483647";
              }
            }
            leaf option {
              tailf:cli-drop-node-name;
              type enumeration {
                enum "reachability" {
                  tailf:info
                    "Reachability";
                }
                enum "state" {
                  tailf:info
                    "Return code state";
                }
              }
            }
          }
          container list {
            tailf:info
              "Group objects in a list";
            tailf:cli-hide-in-submode;
            tailf:cli-flatten-container;
            tailf:cli-compact-syntax;
            leaf boolean {
              tailf:info
                "List state based on a boolean calculation on objects";
              type enumeration {
                enum "and" {
                  tailf:info
                    "Boolean AND operation on list";
                }
                enum "or" {
                  tailf:info
                    "Boolean OR operation on list";
                }
              }
            }
          }
          container interface {
            tailf:info
              "Select an interface to track";
            tailf:cli-hide-in-submode;
            tailf:cli-flatten-container;
            tailf:cli-compact-syntax;
            tailf:cli-sequence-commands;
            uses interface-name-grouping;
            container ip {
              tailf:info
                "IP parameters";
              tailf:cli-flatten-container;
              tailf:cli-optional-in-sequence;
              leaf routing {
                tailf:info
                  "Track interface IP routing capability";
                type empty;
              }
            }
            leaf line-protocol {
              tailf:info
                "Track interface line-protocol";
              tailf:cli-full-command;
              type empty;
            }
          }
          container ip {
            tailf:info
              "IP protocol";
            tailf:cli-hide-in-submode;
            tailf:cli-flatten-container;
            tailf:cli-compact-syntax;
            container route {
              tailf:info
                "IP route";
              tailf:cli-flatten-container;
              tailf:cli-compact-syntax;
              tailf:cli-sequence-commands;
              leaf prefix {
                tailf:cli-drop-node-name;
                type inet:ipv4-address {
                  tailf:info
                    "A.B.C.D;;Prefix";
                }
              }
              leaf mask {
                tailf:cli-drop-node-name;
                type inet:ipv4-address {
                  tailf:info
                    "A.B.C.D;;mask";
                }
              }
              choice option-choice {
                leaf reachability {
                  tailf:info
                    "Route reachability state";
                  type empty;
                }
                container metric {
                  tailf:info
                    "Route metric";
                  tailf:cli-flatten-container;
                  leaf threshold {
                    tailf:info
                      "Route metric threshold";
                    type empty;
                  }
                }
              }
            }
            container sla {
              tailf:info
                "IP Service Level Agreement";
              tailf:cli-flatten-container;
              tailf:cli-compact-syntax;
              tailf:cli-sequence-commands;
              leaf operation-number {
                tailf:cli-drop-node-name;
                type uint32 {
                  tailf:info
                    "<1-2147483647>;;Entry number";
                }
              }
              choice option-choice {
                leaf reachability {
                  tailf:info
                    "Reachability";
                  type empty;
                }
                leaf state {
                  tailf:info
                    "Return code state";
                  type empty;
                }
                default "state";
              }
            }
          }
          container ipv6 {
            tailf:info
              "IPv6 protocol";
            tailf:cli-hide-in-submode;
            tailf:cli-flatten-container;
            tailf:cli-compact-syntax;
            container route {
              tailf:info
                "IPv6 route";
              tailf:cli-flatten-container;
              tailf:cli-compact-syntax;
              tailf:cli-sequence-commands;
              leaf prefix {
                tailf:cli-drop-node-name;
                type ipv6-prefix {
                  tailf:info
                    "X:X:X:X::X/<0-128>;;IPv6 prefix";
                }
              }
              choice option-choice {
                leaf reachability {
                  tailf:info
                    "Route reachability state";
                  type empty;
                }
                container metric {
                  tailf:info
                    "Route metric";
                  tailf:cli-flatten-container;
                  leaf threshold {
                    tailf:info
                      "Route metric threshold";
                    type empty;
                  }
                }
              }
            }
          }
        }
        list object {
          tailf:info
            "Add a tracked object to list";
          tailf:cli-suppress-mode;
          tailf:cli-delete-when-empty;
          tailf:cli-compact-syntax;
          when "../list/boolean" {
            tailf:xpath-root 3;
            tailf:dependency "../list/boolean";
          }
          key "id";
          leaf id {
            type uint16 {
              tailf:info
                "<1-1000>;;Tracked object number";
              range "1..1000";
            }
          }
          leaf not {
            tailf:info
              "Negate the state of object";
            type empty;
          }
        }
        container ip-vrf {
          tailf:cli-drop-node-name;
          when "../ip" {
            tailf:xpath-root 3;
            tailf:dependency "../ip";
          }
          container ip {
            tailf:info
              "Tracking IP configuration subcommands";
            leaf vrf {
              tailf:info
                "Configure VPN Routing/Forwarding table";
              type string {
                tailf:info
                  "WORD;;VPN Routing/Forwarding instance name";
              }
            }
          }
        }
        container ipv6-vrf {
          tailf:cli-drop-node-name;
          when "../ipv6" {
            tailf:xpath-root 3;
            tailf:dependency "../ipv6";
          }
          container ipv6 {
            tailf:info
              "Tracking IP configuration subcommands";
            leaf vrf {
              tailf:info
                "Configure VPN Routing/Forwarding table";
              type string {
                tailf:info
                  "WORD;;VPN Routing/Forwarding instance name";
              }
            }
          }
        }
        container delay {
          tailf:info
            "Tracking delay";
          tailf:cli-compact-syntax;
          leaf down {
            tailf:info
              "Delay down change notification";
            type uint8 {
              tailf:info
                "<0-180>;;Seconds to delay";
              range "0..180";
            }
          }
          leaf up {
            tailf:info
              "Delay up change notification";
            type uint8 {
              tailf:info
                "<0-180>;;Seconds to delay";
              range "0..180";
            }
          }
        }
      }
    }
    container csdb {
      tailf:ncs-device-type "cli-ned";
      tailf:display-when "not(../../ncs:module) or ../../ncs:module[ncs:name='tailf-ned-cisco-ios']";
      tailf:info
        "Common Session Database";
      container tcp {
        tailf:info
          "CSDB TCP protocol";
        leaf finwait-time {
          tailf:info
            "CSDB TCP protocol: FIN/RST timeout";
          type uint8 {
            tailf:info
              "<1-50>;;fin/rst timeout value (sec), default 5 sec";
            range "1..50";
          }
          default "5";
        }
        leaf idle-time {
          tailf:info
            "CSDB TCP protocol: idle timeout";
          type uint16 {
            tailf:info
              "<1-36000>;;idle timeout value (sec), default 3600 sec";
            range "1..36000";
          }
          default "3600";
        }
        container reassembly {
          tailf:info
            "CSDB Out-of-Order Module";
          leaf max-memory {
            tailf:info
              "CSDB Out-of-Order: Queue Memory";
            type uint32 {
              tailf:info
                "<1-102400>;;OoO memory (KB), default 1024 KB";
              range "1..102400";
            }
            default "1024";
          }
          leaf max-queue-length {
            tailf:info
              "CSDB Out-of-Order: Queue Length";
            type uint8 {
              tailf:info
                "<0-128>;;OoO queue length, default 16 packets, O means disable OoO";
              range "0..128";
            }
            default "16";
          }
        }
        leaf synwait-time {
          tailf:info
            "CSDB TCP protocol: 3-way handshake timeout";
          type uint16 {
            tailf:info
              "<0-300>;;syn timeout value (sec), default 30 sec";
            range "0..300";
          }
          default "30";
        }
      }
      container udp {
        tailf:info
          "CSDB UDP protocol";
        leaf idle-time {
          tailf:info
            "CSDB UDP Protocol: idle time";
          type uint16 {
            tailf:info
              "<1-1200>;;idle timeout value (sec), default 30 sec";
            range "1..1200";
          }
          default "30";
        }
      }
      container icmp {
        tailf:info
          "CSDB ICMP protocol";
        leaf idle-time {
          tailf:info
            "CSDB ICMP Protocol: idle time";
          type uint16 {
            tailf:info
              "<1-1200>;;idle timeout value (sec), default 10 sec";
            range "1..1200";
          }
          default "10";
        }
      }
      container session {
        tailf:info
          "CSDB Session Management";
        leaf max-session {
          tailf:info
            "CSDB Session: maximum session";
          type uint32 {
            tailf:info
              "<1-655350>;;session, default 65535";
            range "1..655350";
          }
          default "65535";
        }
      }
    }
    container ethernet {
      tailf:ncs-device-type "cli-ned";
      tailf:display-when "not(../../ncs:module) or ../../ncs:module[ncs:name='tailf-ned-cisco-ios']";
      tailf:info
        "Ethernet configuration";
      container lmi {
        tailf:info
          "Local Management Interface";
        leaf global {
          tailf:info
            "Ethernet LMI is enabled on all supported Interfaces";
          type empty;
        }
        leaf ce {
          tailf:info
            "Ethernet LMI Customer Edge";
          type empty;
        }
      }
      list evc {
        tailf:info
          "define an Ethernet virtual connection (EVC)";
        tailf:cli-mode-name "config-evc";
        tailf:cli-compact-syntax;
        tailf:cli-full-command;
        key "name";
        leaf name {
          type string {
            tailf:info
              "WORD;;EVC identifier of length <1-100>";
            length "1..100";
          }
        }
        container oam {
          tailf:info
            "OAM Protocol";
          container protocol {
            tailf:info
              "Protocol for EVC status reporting";
            choice protocol-choice {
              leaf ldp {
                tailf:info
                  "Protocol LDP";
                type empty;
              }
              container cfm {
                tailf:info
                  "Protocol CFM";
                leaf domain {
                  tailf:info
                    "Protocol CFM Domain";
                  type string {
                    tailf:info
                      "WORD;;domain name";
                  }
                }
              }
            }
          }
        }
      }
      container cfm {
        tailf:info
          "Connectivity Fault Management";
        tailf:cli-diff-dependency "../evc" {
          tailf:xpath-root 3;
        }
        leaf enable {
          tailf:info
            "CFM global enable";
          tailf:cli-full-command;
          type empty;
        }
        leaf ieee {
          tailf:info
            "CFM IEEE enable";
          tailf:cli-full-command;
          type empty;
        }
        leaf global {
          tailf:info
            "CFM global enable";
          tailf:cli-full-command;
          type empty;
        }
        container logging {
          tailf:info
            "Enable CFM syslog messages";
          presence "true";
        }
        container traceroute {
          tailf:info
            "CFM Traceroute";
          container cache {
            tailf:info
              "CFM Traceroute Cache";
            tailf:cli-display-separated;
            presence "true";
            leaf size {
              tailf:info
                "Cache size";
              type uint16 {
                tailf:info
                  "<1-4095>;;Number of cached lines (default 100)";
                range "1..4095";
              }
              default "100";
            }
            leaf hold-time {
              tailf:info
                "Hold Time";
              type uint16 {
                tailf:info
                  "<1-65535>;;minutes (default 100)";
                range "1..65535";
              }
              default "100";
            }
          }
        }
        container mip {
          tailf:info
            "CFM MIP commands";
          list auto-create {
            tailf:info
              "CFM MIP auto creation";
            tailf:cli-suppress-mode;
            tailf:cli-delete-when-empty;
            tailf:cli-compact-syntax;
            tailf:cli-sequence-commands;
            key "evc";
            leaf evc {
              tailf:info
                "auto create for CFM over EVC";
              tailf:cli-expose-key-name;
              type string {
                tailf:info
                  "WORD;;EVC name";
              }
            }
            leaf level {
              tailf:info
                "Maintenance Level";
              tailf:cli-prefix-key;
              type uint8 {
                tailf:info
                  "<0-7>;;maintenance level number";
                range "0..7";
              }
            }
          }
        }
        list domain {
          tailf:info
            "Configure a domain";
          tailf:cli-mode-name "config-ecfm";
          tailf:cli-compact-syntax;
          tailf:cli-incomplete-command;
          tailf:cli-diff-dependency "../ieee" {
            tailf:xpath-root 3;
          }
          key "name";
          leaf name {
            type string {
              tailf:info
                "WORD;;maintenance domain name";
            }
          }
          leaf level {
            tailf:info
              "Maintenance Level";
            tailf:cli-hide-in-submode;
            type uint8 {
              tailf:info
                "<0-7>;;maintenance level number";
            }
          }
          container mip {
            tailf:info
              "MIP commands for Domain";
            container auto-create {
              tailf:info
                "Enable auto MIP creation at Domain Level";
              tailf:cli-delete-when-empty;
              presence "true";
              leaf lower-mep-only {
                tailf:info
                  "Only for lower MEPs";
                type empty;
              }
            }
          }
          container mep {
            tailf:info
              "Maintenance End Point commands";
            leaf archive-hold-time {
              tailf:info
                "Time in minutes for entry to be retained";
              type uint16 {
                tailf:info
                  "<1-65535>;;minutes (default 100)";
                range "1..65535";
              }
              default "100";
            }
          }
          leaf sender-id {
            tailf:info
              "Include Sender ID TLV";
            tailf:cli-full-command;
            type enumeration {
              enum "chassis" {
                tailf:info
                  "Send Chassis ID";
              }
              enum "none" {
                tailf:info
                  "Info not included in Sender Id";
              }
            }
          }
          list service {
            tailf:info
              "Maintenance Association within Domain";
            tailf:cli-mode-name "config-ecfm-srv";
            tailf:cli-compact-syntax;
            tailf:cli-sequence-commands;
            tailf:cli-incomplete-command;
            key "csi-id";
            leaf csi-id {
              type string {
                tailf:info
                  "WORD;;service instance id - short MA name";
              }
            }
            leaf port {
              tailf:info
                "DOWN service direction with no vlan association";
              tailf:cli-hide-in-submode;
              tailf:cli-optional-in-sequence;
              tailf:cli-full-command;
              type empty;
            }
            leaf evc {
              tailf:info
                "Specify EVC";
              tailf:cli-hide-in-submode;
              tailf:cli-optional-in-sequence;
              type string {
                tailf:info
                  "WORD;;EVC name";
              }
            }
            leaf vlan {
              tailf:info
                "Specify vlan (range 1-4094)";
              tailf:cli-hide-in-submode;
              type uint16 {
                tailf:info
                  "<1-4094>;;between 1 and 4094";
                range "1..4094";
              }
            }
            leaf direction {
              tailf:info
                "service direction";
              tailf:cli-hide-in-submode;
              tailf:cli-full-command;
              type enumeration {
                enum "down" {
                  tailf:info
                    "direction towards the LAN";
                }
              }
            }
            container continuity-check {
              tailf:cli-break-sequence-commands;
              tailf:info
                "Enable Continuity Check for Maintenance Association";
              tailf:cli-display-separated;
              presence "true";
              leaf interval {
                tailf:info
                  "Interval Continuity Check messages transmitted";
                tailf:cli-full-command;
                type string {
                  tailf:info
                    "WORD;;interval string";
                }
              }
            }
            leaf sender-id {
              tailf:info
                "Include Sender ID TLV";
              tailf:cli-full-command;
              type enumeration {
                enum "chassis" {
                  tailf:info
                    "Send Chassis ID";
                }
                enum "none" {
                  tailf:info
                    "Info not included in Sender Id";
                }
              }
            }
            container ais {
              tailf:info
                "AIS Maintenance Condition";
              leaf period {
                tailf:info
                  "AIS Transmission period";
                type enumeration {
                  enum "1" {
                    tailf:info
                      "Seconds";
                  }
                  enum "60" {
                    tailf:info
                      "Seconds";
                  }
                }
                default "60";
              }
              leaf level {
                tailf:info
                  "Maintenance Level to send AIS";
                type uint8 {
                  tailf:info
                    "<0-7>;;Maintenance Level";
                  range "0..7";
                }
              }
            }
            container efd {
              tailf:info
                "Ethernet Fault Detection";
              container notify {
                tailf:info
                  "EFD Notification Registration";
                leaf g8032 {
                  tailf:info
                    "Notify G.8032 Controller of EFD events";
                  type empty;
                }
              }
            }
          }
        }
        container mep {
          tailf:info
            "Maintenance End Point";
          container crosscheck {
            tailf:info
              "Cross Check remote MEPs";
            leaf start-delay {
              tailf:info
                "Wait time before cross check starts";
              type uint16 {
                tailf:info
                  "<1-65535>;;seconds (30 seconds default)";
              }
            }
          }
        }
      }
      container ring {
        tailf:info
          "Ring";
        container g8032 {
          tailf:info
            "Specify the g.8032 ethernet ring";
          list profile {
            tailf:info
              "g.8032 ring profile configuration";
            tailf:cli-mode-name "config-erp-profile";
            key "profile-name";
            leaf profile-name {
              type string {
                tailf:info
                  "WORD;;ERP profile name string";
              }
            }
            container timer {
              tailf:info
                "g.8032 timer";
              leaf wtr {
                tailf:info
                  "Wait-to-Restore time";
                type uint8 {
                  tailf:info
                    "<1-12>;;minutes";
                  range "1..12";
                }
              }
              leaf guard {
                tailf:info
                  "Guard timer";
                type uint16 {
                  tailf:info
                    "<10-2000>;;milliseconds";
                  range "10..2000";
                }
              }
            }
          }
          list g8032-list {
            tailf:cli-drop-node-name;
            tailf:cli-mode-name "config-erp-ring";
            key "ring-name";
            leaf ring-name {
              tailf:cli-disallow-value "profile";
              type string {
                tailf:info
                  "WORD;;Name of the ethernet ring";
              }
            }
            container exclusion-list {
              tailf:info
                "Specifiy exclusion list not protected by ERP";
              leaf-list vlan-ids {
                tailf:info
                  "Assign list of VLANs to the exclusion list";
                tailf:cli-replace-all;
                tailf:cli-range-list-syntax;
                type uint16 {
                  tailf:info
                    "<1-4094>;;VLAN id";
                  range "1..4094";
                }
              }
            }
            container port0 {
              tailf:info
                "Port0 of the local node connected to G.8032 ring";
              tailf:cli-compact-syntax;
              tailf:cli-sequence-commands;
              tailf:cli-add-mode;
              tailf:cli-mode-name "config-erp-ring-port";
              tailf:cli-incomplete-command;
              container interface {
                tailf:info
                  "Assign port interface";
                tailf:cli-flatten-container;
                tailf:cli-compact-syntax;
                tailf:cli-hide-in-submode;
                uses interface-name-grouping;
              }
              container monitor {
                tailf:info
                  "Assign the Ethernet Service Instance to monitor g.8032 ring port";
                container service {
                  tailf:info
                    "Specify an Ethernet Service Instance";
                  leaf instance {
                    tailf:info
                      "Specify an Ethernet Service Instance";
                    type uint16 {
                      tailf:info
                        "Ethernet Service Instance ID";
                      range "1..8000";
                    }
                  }
                }
              }
            }
            choice port1-choice {
              container port1 {
                tailf:info
                  "Port1 of the local node connected to G.8032 ring";
                tailf:cli-compact-syntax;
                tailf:cli-sequence-commands;
                tailf:cli-add-mode;
                tailf:cli-mode-name "config-erp-ring-port";
                tailf:cli-incomplete-command;
                container interface {
                  tailf:info
                    "Assign port interface";
                  tailf:cli-flatten-container;
                  tailf:cli-compact-syntax;
                  tailf:cli-hide-in-submode;
                  uses interface-name-grouping;
                }
                container monitor {
                  tailf:info
                    "Assign the Ethernet Service Instance to monitor g.8032 ring port";
                  container service {
                    tailf:info
                      "Specify an Ethernet Service Instance";
                    leaf instance {
                      tailf:info
                        "Specify an Ethernet Service Instance";
                      type uint16 {
                        tailf:info
                          "Ethernet Service Instance ID";
                        range "1..8000";
                      }
                    }
                  }
                }
              }
              container port1-none {
                tailf:cli-drop-node-name;
                tailf:cli-full-command;
                container port1 {
                  leaf none {
                    tailf:info
                      "Assign port1 as none to enable g.8032 open-ring";
                    type empty;
                  }
                }
              }
            }
            list instance {
              tailf:info
                "Configure the g.8032 ethernet ring instance";
              tailf:cli-mode-name "config-erp-inst";
              tailf:cli-full-command;
              key "instance-id";
              leaf instance-id {
                type uint8 {
                  tailf:info
                    "<1-2>;;Instance number";
                  range "1..2";
                }
              }
              leaf profile {
                tailf:info
                  "Specify associated g.8032 ethernet ring profile";
                type string {
                  tailf:info
                    "WORD;;Ethernet ring profile name";
                }
              }
              container rpl {
                tailf:info
                  "Specify RPL owner, neighbor or next-neighbor";
                tailf:cli-compact-syntax;
                tailf:cli-sequence-commands;
                leaf port {
                  tailf:cli-drop-node-name;
                  tailf:cli-incomplete-command;
                  type enumeration {
                    enum "port0" {
                      tailf:info
                        "Assign port0 as RPL owner, neighbor or next-neighbor";
                    }
                    enum "port1" {
                      tailf:info
                        "Assign port1 as RPL owner, neighbor or next-neighbor";
                    }
                  }
                }
                leaf type {
                  tailf:cli-drop-node-name;
                  type enumeration {
                    enum "neighbor" {
                      tailf:info
                        "RPL neighbor";
                    }
                    enum "next-neighbor" {
                      tailf:info
                        "RPL next neighbor";
                    }
                    enum "owner" {
                      tailf:info
                        "RPL owner";
                    }
                  }
                }
              }
              container inclusion-list {
                tailf:info
                  "Specify inclusion list protected by ERP";
                leaf-list vlan-ids {
                  tailf:info
                    "Associates a set of VLAN IDs with the current instance";
                  tailf:cli-range-list-syntax;
                  type uint16 {
                    tailf:info
                      "WORD;;List of VLAN IDs in the form a-b,c,d,e-f,g";
                    range "1..4094";
                  }
                }
              }
              container aps-channel {
                tailf:info
                  "Configure g.8032 instance aps-channel";
                tailf:cli-add-mode;
                tailf:cli-mode-name "config-erp-inst-aps";
                container port0 {
                  tailf:info
                    "Configure g.8032 aps-channel info associated to port0";
                  container service {
                    tailf:info
                      "Specify an Ethernet Service Instance";
                    leaf instance {
                      tailf:info
                        "Specify an Ethernet Service Instance";
                      type uint16 {
                        tailf:info
                          "<1-8000>;;Ethernet Service Instance ID";
                        range "1..8000";
                      }
                    }
                  }
                }
                container port1 {
                  tailf:info
                    "Configure g.8032 aps-channel info associated to port1";
                  choice port1-choice {
                    container service {
                      tailf:info
                        "Specify an Ethernet Service Instance";
                      leaf instance {
                        tailf:info
                          "Specify an Ethernet Service Instance";
                        type uint16 {
                          tailf:info
                            "<1-8000>;;Ethernet Service Instance ID";
                          range "1..8000";
                        }
                      }
                    }
                    leaf none {
                      tailf:info
                        "Specify port1 APS channel as none";
                      type empty;
                    }
                  }
                }
              }
            }
          }
        }
      }
      list tcn-propagation {
        tailf:info
          "Enable TCN propagation";
        tailf:cli-suppress-mode;
        tailf:cli-delete-when-empty;
        key "source to";
        leaf source {
          type enumeration {
            enum "g8032" {
              tailf:info
                "g.8032 ethernet ring";
            }
            enum "rep" {
              tailf:info
                "REP ethernet ring";
            }
          }
        }
        leaf to {
          tailf:info
            "propagate TCN to";
          tailf:cli-expose-key-name;
          type enumeration {
            enum "g8032" {
              tailf:info
                "g.8032 ethernet ring";
            }
            enum "rep" {
              tailf:info
                "REP ethernet ring";
            }
          }
        }
      }
    }
    container performance {
      tailf:ncs-device-type "cli-ned";
      tailf:display-when "not(../../ncs:module) or ../../ncs:module[ncs:name='tailf-ned-cisco-ios']";
      tailf:info
        "Global Performance monitor configuration";
      container monitor {
        tailf:info
          "monitor";
        list context {
          tailf:info
            "Define ezPM context";
          tailf:cli-mode-name "config-perf-mon";
          tailf:cli-incomplete-command;
          tailf:cli-sequence-commands;
          key "name";
          leaf name {
            type string {
              tailf:info
                "WORD;;ezPM context name";
            }
          }
          leaf profile {
            tailf:info
              "Select ezPM profile";
            tailf:cli-hide-in-submode;
            tailf:cli-full-command;
            type enumeration {
              enum "application-experience" {
                tailf:info
                  "Application eXperience performance monitor profile";
              }
              enum "application-performance" {
                tailf:info
                  "Application performance profile";
              }
              enum "application-statistics" {
                tailf:info
                  "Application statistics profile";
              }
            }
          }
          container exporter {
            tailf:cli-break-sequence-commands;
            tailf:info
              "Create exporter";
            list destination {
              tailf:info
                "Export destination configuration";
              tailf:cli-suppress-mode;
              tailf:cli-delete-when-empty;
              tailf:cli-compact-syntax;
              key "address source";
              leaf address {
                type inet:host {
                  tailf:info
                    "Hostname or A.B.C.D or X:X::X;;Destination address";
                }
              }
              leaf source {
                tailf:info
                  "Originating interface";
                tailf:cli-expose-key-name;
                tailf:cli-diff-dependency "../../../../../../interface" {
                  tailf:xpath-root 3;
                }
                type string {
                  tailf:info
                    "WORD;;Interface Name";
                }
              }
              leaf vrf {
                tailf:info
                  "vrf";
                type string {
                  tailf:info
                    "WORD;;VRF label";
                }
              }
              leaf transport {
                tailf:info
                  "transport";
                type enumeration {
                  enum "udp" {
                    tailf:info
                      "UDP transport protocol";
                  }
                }
              }
              leaf port {
                tailf:info
                  "port";
                type uint16 {
                  tailf:info
                    "<1-65535>;;Optional port value";
                  range "1..65535";
                }
              }
            }
          }
          container traffic-monitor {
            tailf:info
              "Select traffic monitor ";
            container all {
              tailf:info
                "All traffic monitors in this profile";
              presence "true";
              leaf ipv4 {
                tailf:info
                  "Activate monitor for ipv4 traffic";
                type empty;
              }
              leaf ipv6 {
                tailf:info
                  "Activate monitor for ipv6 traffic";
                type empty;
              }
            }
            container url {
              tailf:info
                "URL information, application response time (ART) metrics and counters";
              tailf:cli-compact-syntax;
              presence "true";
              leaf ipv4 {
                tailf:info
                  "Activate monitor for ipv4 traffic";
                type empty;
              }
              leaf class-replace {
                tailf:info
                  "Replace traffic classification";
                type string {
                  tailf:info
                    "WORD;;User defined class name";
                }
              }
              leaf cache-size {
                tailf:info
                  "Maximum flow entries in the Flow Cache";
                type uint32 {
                  tailf:info
                    "<64-1048576>;;Maximum number of entries";
                  range "64..1048576";
                }
              }
            }
            container application-client-server-stats {
              tailf:info
                "Per interface, client, server and application statistics";
              presence "true";
            }
            container application-stats {
              tailf:info
                "Per application and interface statistics";
              presence "true";
            }
            container application-response-time {
              tailf:info
                "Application response time (ART) metrics and statistics for TCP traffic";
              presence "true";
            }
            container media {
              tailf:info
                "Media metrics and statistics for RTP traffic";
              presence "true";
            }
          }
        }
      }
    }
    container l2 {
      tailf:ncs-device-type "cli-ned";
      tailf:display-when "not(../../ncs:module) or ../../ncs:module[ncs:name='tailf-ned-cisco-ios']";
      tailf:info
        "Layer 2 configuration";
      list vfi {
        tailf:info
          "Configure a virtual forwarding instance";
        tailf:cli-mode-name "config-vfi";
        tailf:cli-compact-syntax;
        key "name";
        leaf name {
          tailf:cli-diff-dependency "../../../bridge-domain" {
            tailf:xpath-root 3;
          }
          type string {
            tailf:info
              "WORD;;VFI name";
          }
        }
        leaf point-to-point {
          tailf:info
            "Point-to-point configuration mode";
          tailf:cli-hide-in-submode;
          tailf:cli-full-command;
          type empty;
        }
        leaf manual {
          tailf:info
            "Multipoint manual configuration mode";
          tailf:cli-hide-in-submode;
          tailf:cli-full-command;
          type empty;
        }
        leaf autodiscovery {
          tailf:info
            "Multipoint autodiscovery configuration mode";
          tailf:cli-hide-in-submode;
          type empty;
        }
        leaf evc {
          when "../autodiscovery" {
            tailf:xpath-root 3;
            tailf:dependency "../autodiscovery";
          }
          tailf:cli-drop-node-name;
          tailf:cli-hide-in-submode;
          tailf:cli-full-command;
          type string {
            tailf:info
              "WORD;;EVC name";
          }
        }
        container vpn {
          tailf:info
            "VPN configuration";
          leaf id {
            tailf:info
              "VPN id";
            type uint32 {
              tailf:info
                "<1-4294967295>;;VPN id value";
              range "1..4294967295";
            }
          }
        }
        leaf bridge-domain {
          tailf:info
            "Bridge Domain";
          type uint16 {
            tailf:info
              "<1-8000>;;Bridge Domain ID value";
            range "1..8000";
          }
        }
        leaf mtu {
          tailf:cli-full-command;
          type uint16;
        }
        leaf rd {
          tailf:info
            "Specify Route Distinguisher";
          tailf:cli-remove-before-change;
          tailf:cli-full-command;
          type rd-type;
        }
        container route-target {
          tailf:info
            "Specify Target VPN Extended Communities";
          tailf:cli-diff-dependency "../rd" {
            tailf:xpath-root 3;
          }
          uses route-target-grouping;
        }
        list neighbor {
          tailf:info
            "VFI neighbor configuration";
          tailf:cli-suppress-mode;
          tailf:cli-delete-when-empty;
          tailf:cli-compact-syntax;
          tailf:cli-sequence-commands {
            tailf:cli-reset-all-siblings;
          }
          tailf:cli-incomplete-command;
          key "id";
          leaf id {
            type inet:ipv4-address {
              tailf:info
                "A.B.C.D;;VFI neighbor's router id";
            }
          }
          leaf vcid {
            tailf:cli-drop-node-name;
            tailf:cli-optional-in-sequence;
            tailf:cli-incomplete-command;
            type uint32 {
              tailf:info
                "<1-4294967295>;;Enter VC ID value";
              range "1..4294967295";
            }
          }
          leaf encapsulation {
            tailf:info
              "Connection encapsulation type";
            tailf:cli-optional-in-sequence;
            type enumeration {
              enum "mpls" {
                tailf:info
                  "Use MPLS encapsulation";
              }
              enum "l2tpv3" {
                tailf:info
                  "Use L2TPv3 encapsulation";
              }
            }
          }
          leaf pw-class {
            tailf:info
              "Pseudowire-class configuration";
            tailf:cli-optional-in-sequence;
            tailf:non-strict-leafref {
              path "../../../../pseudowire-class/name";
            }
            type string {
              tailf:info
                "WORD;;Pseudowire-class name";
            }
          }
          leaf no-split-horizon {
            tailf:info
              "Disable split-horizon forwarding";
            type empty;
          }
        }
      }
    }
    container interface {
      tailf:ncs-device-type "cli-ned";
      tailf:display-when "not(../../ncs:module) or ../../ncs:module[ncs:name='tailf-ned-cisco-ios']";
      tailf:info
        "Configure interfaces";
      tailf:cli-explicit-exit;
      list Null {
        tailf:info
          "Null interface";
        tailf:cli-allow-join-with-key {
          tailf:cli-display-joined;
        }
        tailf:cli-mode-name "config-if";
        tailf:cli-suppress-key-abbreviation;
        tailf:cli-full-command;
        key "name";
        leaf name {
          type uint8 {
            tailf:info
              "<0-0>;;Null interface number";
            range "0";
          }
        }
        container ip {
          tailf:info
            "Interface Internet Protocol config commands";
          leaf unreachables {
            tailf:info
              "Enable sending ICMP Unreachable messages";
            tailf:cli-boolean-no;
            tailf:cli-full-command;
            type boolean;
            default "true";
          }
        }
        container ipv6 {
          tailf:info
            "IPv6 interface subcommands";
          leaf unreachables {
            tailf:info
              "Enable sending of ICMP Unreachable messages";
            tailf:cli-boolean-no;
            tailf:cli-full-command;
            type boolean;
            default "true";
          }
        }
      }
      list Loopback {
        tailf:info
          "Loopback interface";
        tailf:cli-allow-join-with-key {
          tailf:cli-display-joined;
        }
        tailf:cli-mode-name "config-if";
        tailf:cli-suppress-key-abbreviation;
        tailf:cli-full-command;
        key "name";
        leaf name {
          type string {
            tailf:info
              "<0-2147483647>;;Loopback interface number";
            pattern '([0-9\.])+';
          }
        }
        uses interface-common-pre-grouping;
        uses interface-common-grouping;
      }
      list VirtualPortGroup {
        tailf:info
          "Virtual Port Group";
        tailf:cli-allow-join-with-key {
          tailf:cli-display-joined;
        }
        tailf:cli-mode-name "config-if";
        tailf:cli-suppress-key-abbreviation;
        key "name";
        leaf name {
          type uint8 {
            tailf:info
              "<0-31>;;VirtualPortGroup interface number";
          }
        }
        uses interface-common-pre-grouping;
        uses interface-common-grouping;
        uses interface-pointtopoint-grouping;
      }
      list Dot11Radio {
        tailf:info
          "IEEE 802.11 WLAN";
        tailf:cli-allow-join-with-key {
          tailf:cli-display-joined;
        }
        tailf:cli-mode-name "config-if";
        tailf:cli-suppress-key-abbreviation;
        key "name";
        leaf name {
          type string {
            tailf:info
              "LINE;;Dot11Radio interface number";
            pattern '[0-9]+.*';
          }
        }
        uses interface-common-pre-grouping;
        uses interface-ethernet-pre-grouping;
        uses interface-common-grouping;
        uses interface-ethernet-post-grouping;
        container encryption {
          tailf:info
            "Configure dot11 encryption parameters";
          uses interface-encryption-mode-grouping;
          list vlan {
            tailf:info
              "vlan";
            tailf:cli-suppress-mode;
            tailf:cli-delete-when-empty;
            tailf:cli-compact-syntax;
            key "id";
            leaf id {
              type string {
                tailf:info
                  "WORD;;vlan ID number or vlan nam";
              }
            }
            uses interface-encryption-mode-grouping;
          }
        }
        container broadcast-key {
          tailf:info
            "Configure broadcast key rotation period";
          list vlan {
            tailf:info
              "vlan";
            tailf:cli-suppress-mode;
            tailf:cli-delete-when-empty;
            tailf:cli-compact-syntax;
            tailf:cli-reset-container;
            key "name";
            leaf name {
              type string {
                tailf:info
                  "WORD;;vlan ID number or vlan name";
              }
            }
            leaf change {
              tailf:info
                "key rotation";
              type uint32 {
                tailf:info
                  "<10-10000000>;;Key rotation period in seconds";
                range "10..10000000";
              }
            }
          }
        }
        list ssid {
          tailf:info
            "Configure radio service set parameters";
          tailf:cli-suppress-mode;
          tailf:cli-delete-when-empty;
          key "name";
          leaf name {
            type string {
              tailf:info
                "LINE;;radio Service Set ID (Up to 32 character";
              length "1..32";
            }
          }
        }
        container antenna {
          tailf:info
            "dot11 radio antenna setting";
          leaf gain {
            tailf:info
              "Configure Resultant Antenna Gain";
            type int16 {
              tailf:info
                "<-128 - 128>;;Resultant Antenna Gain in dB";
              range "-128..128";
            }
          }
        }
        leaf peakdetect {
          type empty;
        }
        leaf mbssid {
          tailf:info
            "enable mbssid";
          tailf:cli-full-command;
          type empty;
        }
        leaf speed {
          tailf:info
            "Set allowed radio bit rates";
          tailf:cli-multi-value;
          tailf:cli-full-command;
          type string {
            tailf:info
              "WORD;;allowed radio bit rates";
          }
        }
        container dfs {
          tailf:info
            "Dynamic Frequency Selection commands";
          container band {
            tailf:info
              "Specify frequency bands";
            tailf:cli-incomplete-no;
            choice band-choice {
              leaf block {
                tailf:info
                  "Block specified frequency bands from being selected by DFS";
                tailf:cli-boolean-no;
                tailf:cli-full-command;
                type boolean;
                default "true";
              }
              container block-conf {
                tailf:cli-drop-node-name;
                tailf:cli-compact-syntax;
                tailf:cli-sequence-commands {
                  tailf:cli-reset-siblings;
                }
                leaf one {
                  tailf:info
                    "5.150 to 5.250 GHz";
                  tailf:alt-name "1";
                  tailf:cli-optional-in-sequence;
                  tailf:cli-incomplete-command;
                  type empty;
                }
                leaf two {
                  tailf:info
                    "5.250 to 5.350 GHz";
                  tailf:alt-name "2";
                  tailf:cli-optional-in-sequence;
                  tailf:cli-incomplete-command;
                  type empty;
                }
                leaf three {
                  tailf:info
                    "5.470 to 5.725 GHz";
                  tailf:alt-name "3";
                  tailf:cli-optional-in-sequence;
                  tailf:cli-incomplete-command;
                  type empty;
                }
                leaf four {
                  tailf:info
                    "5.725 to 5.825 GHz";
                  tailf:alt-name "4";
                  tailf:cli-optional-in-sequence;
                  tailf:cli-incomplete-command;
                  type empty;
                }
                leaf block {
                  tailf:info
                    "Block specified frequency bands from being selected by DFS";
                  type empty;
                }
              }
            }
          }
        }
        container packet {
          tailf:info
            "IEEE 802.11 packet";
          leaf retries {
            tailf:info
              "maximum best-effort data packet retries";
            type uint8 {
              tailf:info
                "<1-128>;;number of packet retries before giving up";
              range "1..128";
            }
          }
        }
        container channel {
          tailf:info
            "Set the radio frequency";
          leaf dfs {
            tailf:info
              "Use Dynamic Frequency Selection";
            type empty;
          }
        }
        container channel-conf {
          tailf:cli-drop-node-name;
          container channel {
            tailf:info
              "Set the radio frequency";
            tailf:cli-compact-syntax;
            leaf least-congested {
              tailf:info
                "Scan for best frequency";
              type empty;
            }
            leaf-list frequency {
              tailf:cli-drop-node-name;
              tailf:cli-flat-list-syntax;
              tailf:cli-replace-all;
              ordered-by user;
              type uint16 {
                tailf:info
                  "NUM;;frequency";
              }
            }
          }
        }
        container station-role {
          tailf:info
            "role of the radio";
          container root {
            tailf:info
              "Root access point or bridge";
            presence "true";
          }
        }
        container rts {
          tailf:info
            "dot11 Request To Send";
          leaf threshold {
            tailf:info
              "RTS threshold";
            type uint16 {
              tailf:info
                "<0-2347>;;threshold in bytes";
              range "0..2347";
            }
          }
          leaf retries {
            tailf:info
              "RTS max retries";
            type uint8 {
              tailf:info
                "<1-128>;;max retries";
              range "1..128";
            }
          }
        }
        container world-mode {
          tailf:info
            "Dot11 radio world mode";
          container dot11d {
            tailf:info
              "802.11d World Mode advertise country";
            tailf:cli-compact-syntax;
            tailf:cli-sequence-commands {
              tailf:cli-reset-siblings;
            }
            leaf country-code {
              tailf:info
                "ISO /IEC 3166-1 country code";
              tailf:cli-incomplete-command;
              type string {
                tailf:info
                  "WORD;;two characters country code";
              }
            }
            leaf location {
              tailf:cli-drop-node-name;
              type enumeration {
                enum "both" {
                  tailf:info
                    "location indoor and outdoor";
                }
                enum "indoor" {
                  tailf:info
                    "location indoor";
                }
                enum "outdoor" {
                  tailf:info
                    "location outdoor";
                }
              }
            }
          }
        }
        leaf infrastructure-client {
          tailf:info
            "Reserve a dot11 virtual interface for a WGB client";
          type empty;
        }
      }
      list Embedded-Service-Engine {
        tailf:info
          "cisco embedded service engine module";
        tailf:cli-allow-join-with-key {
          tailf:cli-display-joined;
        }
        tailf:cli-mode-name "config-if";
        tailf:cli-suppress-key-abbreviation;
        key "name";
        leaf name {
          type string {
            tailf:info
              "<0-2>/<0-0>;;Embedded-Service-Engine interface number";
            pattern '[0-9]+.*';
          }
        }
        uses interface-common-pre-grouping;
        uses interface-common-grouping;
      }
      list Service-Engine {
        tailf:info
          "Cisco service engine module";
        tailf:cli-allow-join-with-key {
          tailf:cli-display-joined;
        }
        tailf:cli-mode-name "config-if";
        tailf:cli-suppress-key-abbreviation;
        key "name";
        leaf name {
          type string {
            pattern '[0-9]+.*';
          }
        }
        uses interface-common-pre-grouping;
        uses interface-common-grouping;
      }
      list Tunnel {
        tailf:info
          "Tunnel interface";
        tailf:cli-allow-join-with-key {
          tailf:cli-display-joined;
        }
        tailf:cli-mode-name "config-if";
        tailf:cli-suppress-key-abbreviation;
        tailf:cli-recursive-delete;
        key "name";
        leaf name {
          type uint32 {
            tailf:info
              "<0-2147483647>;;Tunnel interface number";
          }
        }
        uses interface-common-pre-grouping;
        uses interface-common-grouping;
        uses interface-tunnel-grouping;
      }
      list Port-channel {
        tailf:info
          "Ethernet Channel of interfaces";
        tailf:cli-allow-join-with-key {
          tailf:cli-display-joined;
        }
        tailf:cli-mode-name "config-if";
        tailf:cli-suppress-key-abbreviation;
        tailf:cli-recursive-delete;
        key "name";
        leaf name {
          type uint32 {
            tailf:info
              "<1-512>;;Port-channel interface number";
            range "1..512";
          }
        }
        uses interface-common-pre-grouping;
        uses interface-ethernet-pre-grouping;
        uses interface-switch-grouping;
        uses interface-ethernet-switch-grouping;
        uses interface-common-switch-grouping;
        uses interface-ethernet-post-grouping;
        container mlacp {
          tailf:info
            "mLACP Port Channel interface subcommands";
          container interchassis {
            tailf:info
              "mLACP Interchassis commands";
            leaf group {
              tailf:info
                "Interchassis Group";
              type uint32 {
                tailf:info
                  "<1-4294967295>;;Group ID";
              }
            }
          }
        }
        container port-channel {
          tailf:info
            "Port Channel interface subcommands";
          container load-balance {
            tailf:info
              "Configure load-balancing for egress traffic";
            leaf flow-based {
              tailf:info
                "Flow based load-balancing on the port-channel";
              tailf:cli-full-command;
              tailf:cli-diff-dependency "../link" {
                tailf:xpath-root 3;
                tailf:cli-trigger-on-set;
              }
              tailf:cli-diff-dependency "../weighted" {
                tailf:xpath-root 3;
                tailf:cli-trigger-on-set;
              }
              type empty;
            }
            leaf link {
              tailf:info
                "Manually configure a member link for load-balancing";
              tailf:cli-full-command;
              type uint8 {
                tailf:info
                  "<1-16>;;The link ID of the member link to use for egress load-balancing";
                range "1..16";
              }
            }
            container weighted {
              tailf:info
                "Configure weighted load-balancing on the port-channel";
              container default {
                tailf:info
                  "Configure default parameters";
                leaf weight {
                  tailf:info
                    "Modify the default weight";
                  type uint16 {
                    tailf:info
                      "<1-10000>;;weight value";
                    range "1..10000";
                  }
                }
              }
              leaf rebalance {
                tailf:info
                  "Configure or disable automatic rebalancing";
                type union {
                  type uint16 {
                    tailf:info
                      "<1-10000>;;The threshold weight used to trigger automatic rebalancing";
                    range "1..10000";
                  }
                  type enumeration {
                    enum "disable" {
                      tailf:info
                        "Disable automatic rebalancing";
                    }
                  }
                }
              }
            }
          }
          leaf min-links {
            tailf:info
              "Minimum number of bundled ports needed to bring up this port channel";
            type uint8 {
              tailf:info
                "<2-8>;;The minimum number of bundled ports needed before this port channel can come up.";
              range "2..8";
            }
          }
        }
      }
      container Port-channel-subinterface {
        tailf:cli-drop-node-name;
        list Port-channel {
          tailf:info
            "Ethernet Channel of interfaces";
          tailf:cli-allow-join-with-key {
            tailf:cli-display-joined;
          }
          tailf:cli-mode-name "config-subif";
          tailf:cli-suppress-key-abbreviation;
          tailf:cli-recursive-delete;
          key "name";
          leaf name {
            tailf:cli-diff-dependency "../../../Port-channel" {
              tailf:xpath-root 3;
            }
            type string {
              pattern '[0-9]+\.[0-9]+';
            }
          }
          uses interface-common-pre-grouping;
          uses interface-ethernet-pre-grouping;
          uses sub-interface-switch-grouping;
          uses sub-interface-ethernet-switch-grouping;
          uses sub-interface-common-switch-grouping;
          uses sub-interface-ethernet-post-grouping;
        }
      }
      list Multilink {
        tailf:info
          "Multilink-group interface";
        tailf:cli-allow-join-with-key {
          tailf:cli-display-joined;
        }
        tailf:cli-mode-name "config-if";
        tailf:cli-suppress-key-abbreviation;
        key "name";
        leaf name {
          type uint16 {
            tailf:info
              "<1-65535>;;Multilink interface number";
            range "1..65535";
          }
        }
        uses interface-common-pre-grouping;
        uses interface-common-grouping;
        uses interface-pointtopoint-grouping;
      }
      list MFR {
        tailf:info
          "Multilink Frame Relay bundle interface";
        tailf:cli-allow-join-with-key {
          tailf:cli-display-joined;
        }
        tailf:cli-mode-name "config-if";
        tailf:cli-suppress-key-abbreviation;
        key "name";
        leaf name {
          type uint32 {
            tailf:info
              "<0-2147483647>;;MFR interface number";
          }
        }
        uses interface-common-pre-grouping;
        uses interface-common-grouping;
        uses interface-pointtopoint-grouping;
      }
      container MFR-subinterface {
        tailf:cli-drop-node-name;
        list MFR {
          tailf:info
            "Multilink Frame Relay bundle interface";
          tailf:cli-allow-join-with-key {
            tailf:cli-display-joined;
          }
          tailf:cli-mode-name "config-subif";
          tailf:cli-suppress-key-abbreviation;
          tailf:cli-incomplete-command;
          key "name";
          leaf name {
            tailf:cli-diff-dependency "../../../MFR" {
              tailf:xpath-root 3;
            }
            type string {
              pattern '[0-9]+\.[0-9]+';
            }
          }
          leaf type {
            tailf:cli-drop-node-name;
            tailf:cli-hide-in-submode;
            type enumeration {
              enum "multipoint" {
                tailf:info
                  "Treat as a multipoint link";
              }
              enum "point-to-point" {
                tailf:info
                  "Treat as a point-to-point link";
              }
            }
          }
          uses interface-common-pre-grouping;
          uses sub-interface-common-grouping;
        }
      }
      list BRI {
        tailf:info
          "ISDN Basic Rate Interface";
        tailf:cli-allow-join-with-key {
          tailf:cli-display-joined;
        }
        tailf:cli-mode-name "config-if";
        tailf:cli-suppress-key-abbreviation;
        key "name";
        leaf name {
          type string {
            tailf:info
              "<slot>/<port>;;BRI interface number";
            pattern '[0-9]+.*';
          }
        }
        uses interface-common-pre-grouping;
        uses interface-common-grouping;
        uses interface-pointtopoint-grouping;
      }
      list Ethernet {
        tailf:info
          "Ethernet";
        tailf:cli-allow-join-with-key {
          tailf:cli-display-joined;
        }
        tailf:cli-mode-name "config-if";
        tailf:cli-suppress-key-abbreviation;
        key "name";
        leaf name {
          type string {
            tailf:info
              "<slot>/<port>;;Ethernet interface number";
            pattern '[0-9]+.*';
          }
        }
        uses interface-common-pre-grouping;
        uses interface-ethernet-pre-grouping;
        uses interface-switch-grouping;
        uses interface-ethernet-switch-grouping;
        uses interface-common-switch-grouping;
        uses interface-ethernet-post-grouping;
      }
      list FastEthernet {
        tailf:info
          "FastEthernet IEEE 802.3";
        tailf:cli-allow-join-with-key {
          tailf:cli-display-joined;
        }
        tailf:cli-mode-name "config-if";
        tailf:cli-suppress-key-abbreviation;
        key "name";
        leaf name {
          type string {
            tailf:info
              "<0-66>/<0-128>;;FastEthernet interface number";
            pattern '[0-9]+.*';
          }
        }
        uses interface-common-pre-grouping;
        uses interface-ethernet-pre-grouping;
        uses interface-switch-grouping;
        uses interface-ethernet-switch-grouping;
        uses interface-common-switch-grouping;
        uses interface-ethernet-post-grouping;
      }
      list GigabitEthernet {
        tailf:info
          "GigabitEthernet IEEE 802.3z";
        tailf:cli-allow-join-with-key {
          tailf:cli-display-joined;
        }
        tailf:cli-mode-name "config-if";
        tailf:cli-suppress-key-abbreviation;
        key "name";
        leaf name {
          type string {
            tailf:info
              "<0-66>/<0-128>;;GigabitEthernet interface number";
            pattern '[0-9]+.*';
          }
        }
        uses interface-common-pre-grouping;
        uses interface-ethernet-pre-grouping;
        uses interface-switch-grouping;
        uses interface-ethernet-switch-grouping;
        uses interface-common-switch-grouping;
        uses interface-ethernet-post-grouping;
      }
      list TenGigabitEthernet {
        tailf:info
          "Ten Gigabit Ethernet";
        tailf:cli-allow-join-with-key {
          tailf:cli-display-joined;
        }
        tailf:cli-mode-name "config-if";
        tailf:cli-suppress-key-abbreviation;
        key "name";
        leaf name {
          type string {
            tailf:info
              "<0-66>/<0-128>;;TenGigabitEthernet interface number";
            pattern '[0-9]+.*';
          }
        }
        uses interface-common-pre-grouping;
        uses interface-ethernet-pre-grouping;
        uses interface-switch-grouping;
        uses interface-ethernet-switch-grouping;
        uses interface-common-switch-grouping;
        uses interface-ethernet-post-grouping;
      }
      list FortyGigabitEthernet {
        tailf:info
          "Forty Gigabit Ethernet";
        tailf:cli-allow-join-with-key {
          tailf:cli-display-joined;
        }
        tailf:cli-mode-name "config-if";
        tailf:cli-suppress-key-abbreviation;
        key "name";
        leaf name {
          type string {
            tailf:info
              "X/Y/Z;;FortyGigabitEthernet interface id";
            pattern '[0-9]+.*';
          }
        }
        uses interface-common-pre-grouping;
        uses interface-ethernet-pre-grouping;
        uses interface-switch-grouping;
        uses interface-ethernet-switch-grouping;
        uses interface-common-switch-grouping;
        uses interface-ethernet-post-grouping;
      }
      list HundredGigE {
        tailf:info
          "Ten Gigabit Ethernet";
        tailf:cli-allow-join-with-key {
          tailf:cli-display-joined;
        }
        tailf:cli-mode-name "config-if";
        tailf:cli-suppress-key-abbreviation;
        key "name";
        leaf name {
          type string {
            tailf:info
              "<0-66>/<0-128>;;HundredGigE interface number";
            pattern '[0-9]+.*';
          }
        }
        uses interface-common-pre-grouping;
        uses interface-ethernet-pre-grouping;
        uses interface-switch-grouping;
        uses interface-ethernet-switch-grouping;
        uses interface-common-switch-grouping;
        uses interface-ethernet-post-grouping;
      }
      list Wlan-GigabitEthernet {
        tailf:info
          "Internal GigabitEthernet IEEE 802.3z connecting to embedded AP";
        tailf:cli-allow-join-with-key {
          tailf:cli-display-joined;
        }
        tailf:cli-mode-name "config-if";
        tailf:cli-suppress-key-abbreviation;
        key "name";
        leaf name {
          type string {
            tailf:info
              "<0-0>;;Wlan-GigabitEthernet interface number";
            pattern '[0-9]+.*';
          }
        }
        uses interface-common-pre-grouping;
        uses interface-ethernet-pre-grouping;
        uses interface-switch-grouping;
        uses interface-ethernet-switch-grouping;
        uses interface-common-switch-grouping;
        uses interface-ethernet-post-grouping;
      }
      list wlan-ap {
        tailf:info
          "Service module interface to embedded AP";
        tailf:cli-allow-join-with-key {
          tailf:cli-display-joined;
        }
        tailf:cli-mode-name "config-if";
        tailf:cli-suppress-key-abbreviation;
        key "name";
        leaf name {
          type string {
            tailf:info
              "<0-0>;;wlan-ap interface number";
            pattern '[0-9]+.*';
          }
        }
        uses interface-common-pre-grouping;
        uses interface-ethernet-pre-grouping;
        uses interface-ethernet-grouping;
        uses interface-common-grouping;
        uses interface-ethernet-post-grouping;
      }
      list Dialer {
        tailf:info
          "Dialer interface";
        tailf:cli-allow-join-with-key {
          tailf:cli-display-joined;
        }
        tailf:cli-mode-name "config-if";
        tailf:cli-suppress-key-abbreviation;
        key "name";
        leaf name {
          type string {
            tailf:info
              "<0-255>;;Dialer interface number";
            pattern '[0-9]+.*';
          }
        }
        uses interface-common-pre-grouping;
        uses interface-common-grouping;
        uses interface-pointtopoint-grouping;
      }
      list ATM {
        tailf:info
          "ATM interface";
        tailf:cli-allow-join-with-key {
          tailf:cli-display-joined;
        }
        tailf:cli-mode-name "config-if";
        tailf:cli-suppress-key-abbreviation;
        key "name";
        leaf name {
          type string {
            pattern '[0-9]+.*';
          }
        }
        leaf point-to-point {
          tailf:info
            "Point-to-point interface";
          tailf:cli-hide-in-submode;
          tailf:cli-full-command;
          type empty;
        }
        uses interface-common-pre-grouping;
        uses interface-common-grouping;
        container ima {
          tailf:info
            "IMA Interface commands";
          leaf version {
            tailf:info
              "IMA version";
            tailf:cli-full-command;
            type enumeration {
              enum "1.0" {
                tailf:info
                  "IMA version 1.0";
              }
              enum "1.1" {
                tailf:info
                  "IMA version 1.1";
              }
            }
          }
          leaf group-id {
            type uint8;
          }
        }
        container atm {
          tailf:info
            "Modify ATM parameters";
          container bandwidth {
            tailf:info
              "Allow bandwidth change on ATM PVCs";
            leaf dynamic {
              tailf:info
                "Allow dynamic bandwidth change on ATM PVCs";
              type empty;
            }
          }
          container mcpt-timers {
            tailf:info
              "Configure Maximum cell Packing Timeout Values";
            tailf:cli-compact-syntax;
            tailf:cli-sequence-commands {
              tailf:cli-reset-siblings;
            }
            leaf timer-1 {
              tailf:cli-drop-node-name;
              tailf:cli-incomplete-command;
              type uint16 {
                tailf:info
                  "<500-10000>;;MCPT timer1 value in microsecond";
                range "500..10000";
              }
            }
            leaf timer-2 {
              tailf:cli-drop-node-name;
              tailf:cli-incomplete-command;
              type uint16 {
                tailf:info
                  "<500-10000>;;MCPT timer2 value in microsecond";
                range "500..10000";
              }
            }
            leaf timer-3 {
              tailf:cli-drop-node-name;
              type uint16 {
                tailf:info
                  "<1000-10000>;;MCPT timer3 value in microsecond";
                range "1000..10000";
              }
            }
          }
          leaf enable-ilmi-trap {
            tailf:cli-boolean-no;
            tailf:cli-full-command;
            type boolean;
            default "true";
          }
          container ilmi-keepalive {
            tailf:info
              "Keepalive polling configuration";
            presence "true";
          }
          container route-bridged {
            tailf:info
              "Route 1483 Ethernet encapsulated packets";
            leaf ip {
              tailf:info
                "Route IP over RFC 1483 Ethernet";
              type empty;
            }
            leaf ipv6 {
              tailf:info
                "Route IPv6 over RFC 1483 Ethernet";
              type empty;
            }
          }
        }
        list pvc {
          tailf:info
            "Configure ATM PVC parameters";
          tailf:cli-mode-name "cfg-if-atm-pvc";
          key "name";
          leaf name {
            type string {
              tailf:info
                "WORD;;VPI/VCI or VCI or handle";
            }
          }
          leaf l2transport {
            tailf:info
              "Set PVC to L2 transport VC, No L3 function";
            tailf:cli-hide-in-submode;
            type empty;
          }
          leaf class-vc {
            tailf:info
              "Configure default vc-class name";
            tailf:non-strict-leafref {
              path "../../../../vc-class/atm/name";
            }
            type string {
              tailf:info
                "WORD;;ATM vc-class name to use on this VC";
            }
          }
          container cell-packing {
            tailf:info
              "ATM Cell packing";
            tailf:cli-compact-syntax;
            tailf:cli-sequence-commands {
              tailf:cli-reset-siblings;
            }
            leaf maxcells {
              tailf:cli-drop-node-name;
              tailf:cli-incomplete-command;
              type uint8 {
                tailf:info
                  "<2-28>;;Maximum number of Cells in a packet";
                range "2..28";
              }
            }
            leaf mcpt-timer {
              tailf:info
                "Which MCPT timer to use";
              type uint8 {
                tailf:info
                  "<1-3>;;Which MCPT timer to use";
                range "1..3";
              }
            }
          }
          leaf encapsulation {
            tailf:info
              "Select ATM Encapsulation for VC";
            tailf:cli-full-command;
            type enumeration {
              enum "aal0" {
                tailf:info
                  "Raw Cell, No SAR processing(Like-Like)";
              }
              enum "aal5" {
                tailf:info
                  "AAL5 Encapsulation(Like-Like)";
              }
              enum "aal5snap" {
                tailf:info
                  "AAL5+LLC/SNAP Encapsulation";
              }
            }
          }
          container service-policy {
            tailf:info
              "Attach a policy-map to a VC";
            uses service-policy-grouping;
          }
          container pppoe-client {
            tailf:info
              "pppoe-client";
            list dial-pool-number {
              tailf:info
                "dialer pool keyword";
              tailf:cli-suppress-mode;
              tailf:cli-delete-when-empty;
              tailf:cli-compact-syntax;
              tailf:cli-remove-before-change;
              key "id";
              leaf id {
                type uint8 {
                  tailf:info
                    "<1-255>;;Dialer pool number";
                }
              }
              leaf dial-on-demand {
                tailf:info
                  "dial on demand enabled";
                type empty;
              }
              leaf restart {
                tailf:info
                  "Set restart timeout value";
                type uint16 {
                  tailf:info
                    "<1-3600>;;Restart timeout, in seconds";
                  range "1..3600";
                }
              }
              leaf mac-override {
                tailf:info
                  "Use mac-address from dialer interface";
                tailf:cli-full-command;
                type empty;
              }
              leaf service-name {
                tailf:info
                  "Service name requested by the PPPoE client for this dial-pool-number";
                type string {
                  tailf:info
                    "LINE;;Service Name string";
                }
              }
            }
            leaf ppp-max-payload {
              tailf:info
                "Send PPP Max-Payload tag in PPPoE control packets";
              type uint16 {
                tailf:info
                  "<64-2030>;;Maximum MRU value to be negotiated during PPP LCP negotiation";
                range "64..2030";
              }
            }
          }
          uses xconnect-grouping;
        }
      }
      list CEM {
        tailf:info
          "Circuit Emulation interface";
        tailf:cli-allow-join-with-key {
          tailf:cli-display-joined;
        }
        tailf:cli-mode-name "config-if";
        tailf:cli-suppress-key-abbreviation;
        key "name";
        leaf name {
          type string {
            pattern '[0-9]+.*';
          }
        }
        uses interface-common-pre-grouping;
        uses interface-common-grouping;
        list cem {
          tailf:info
            "Configure a CEM channel";
          tailf:cli-mode-name "config-if-cem";
          key "id";
          leaf id {
            tailf:info
              "<0-64>;;Enter the group value";
            type uint8 {
              range "0..64";
            }
          }
          container cem {
            tailf:info
              "Apply CEM class";
            leaf class {
              tailf:info
                "Apply CEM class";
              tailf:non-strict-leafref {
                path "../../../../../class/cem/name";
              }
              type string {
                tailf:info
                  "WORD;;cem class name";
              }
            }
          }
          container service-policy {
            tailf:info
              "Attach a policy-map to CEM Circuit";
            leaf input {
              tailf:info
                "Attach a policy-map to ingress of CEM Circuit";
              tailf:non-strict-leafref {
                path "../../../../../policy-map/name";
              }
              type string {
                tailf:info
                  "WORD;;Policy-map name";
              }
            }
          }
          uses xconnect-grouping;
        }
      }
      list BDI {
        tailf:info
          "Bridge-Domain interface";
        tailf:cli-allow-join-with-key {
          tailf:cli-display-joined;
        }
        tailf:cli-mode-name "config-if";
        tailf:cli-suppress-key-abbreviation;
        key "name";
        leaf name {
          tailf:cli-diff-dependency "../../../bridge-domain/bridge-domain-list" {
            tailf:xpath-root 3;
          }
          type uint16 {
            tailf:info
              "<1-4095>;;BDI interface number";
            range "1..4095";
          }
        }
        uses interface-common-pre-grouping;
        uses interface-ethernet-pre-grouping;
        uses interface-ethernet-grouping;
        uses interface-common-grouping;
        uses interface-ethernet-post-grouping;
      }
      list BVI {
        tailf:info
          "Bridge-Group Virtual Interface";
        tailf:cli-allow-join-with-key {
          tailf:cli-display-joined;
        }
        tailf:cli-mode-name "config-if";
        tailf:cli-suppress-key-abbreviation;
        key "name";
        leaf name {
          type string {
            tailf:info
              "<1-255>;;BVI interface number";
            pattern '[0-9]+.*';
          }
        }
        uses interface-common-pre-grouping;
        uses interface-common-grouping;
      }
      list Cable {
        tailf:info
          "CMTS interface";
        tailf:cli-allow-join-with-key {
          tailf:cli-display-joined;
        }
        tailf:cli-mode-name "config-if";
        tailf:cli-suppress-key-abbreviation;
        key "name";
        leaf name {
          type string {
            pattern '[0-9]+.*';
          }
        }
        uses interface-common-pre-grouping;
        uses interface-common-grouping;
        container downstream {
          tailf:info
            "Associate a Cable/Modular-Cable/Integrated-Cable interface with this CGD host";
          list Cable {
            tailf:info
              "Cable";
            tailf:cli-allow-join-with-key;
            tailf:cli-suppress-mode;
            tailf:cli-delete-when-empty;
            key "name";
            leaf name {
              type string {
                tailf:info
                  "<slot>/<card>/<port>;;Enter slot/subslot/bay";
              }
            }
            leaf rf-channel {
              tailf:info
                "RF channel";
              type string {
                tailf:info
                  "<grouplist>;;List of port numbers and number ranges";
              }
            }
          }
          list Modular-Cable {
            tailf:info
              "Modular cable";
            tailf:cli-allow-join-with-key;
            tailf:cli-suppress-mode;
            tailf:cli-delete-when-empty;
            key "name";
            leaf name {
              type string {
                tailf:info
                  "<slot>/<card>/<port>;;Enter slot/subslot/bay";
              }
            }
            leaf rf-channel {
              tailf:info
                "RF channel";
              type string {
                tailf:info
                  "<grouplist>;;List of port numbers and number ranges";
              }
            }
            leaf upstream {
              tailf:info
                "Logical Identifier of upstreams serving these downstream rf-channels";
              type string {
                tailf:info
                  "<grouplist>;;List of Ranges for upstream channel <0-11>";
              }
            }
          }
          list Integrated-Cable {
            tailf:info
              "Integrated cable";
            tailf:cli-allow-join-with-key;
            tailf:cli-suppress-mode;
            tailf:cli-delete-when-empty;
            key "name";
            leaf name {
              type string {
                tailf:info
                  "<slot>/<card>/<port>;;Enter slot/subslot/bay";
              }
            }
            leaf rf-channel {
              tailf:info
                "RF channel";
              type string {
                tailf:info
                  "<grouplist>;;List of port numbers and number ranges";
              }
            }
          }
        }
        list upstream {
          tailf:info
            "Associate a Upstream channel with this CGD host";
          tailf:cli-suppress-mode;
          tailf:cli-delete-when-empty;
          tailf:cli-compact-syntax;
          tailf:cli-incomplete-command;
          key "id";
          leaf id {
            type uint8 {
              tailf:info
                "<0-7>;;US channel index in M";
              range "0..7";
            }
          }
          leaf Upstream-Cable {
            tailf:info
              "Upstream Cable Controller";
            tailf:cli-incomplete-command;
            type string {
              tailf:info
                "<slot>/<card>/<port>;;slot/subslot/controller of upstream us-channels";
            }
          }
          leaf us-channel {
            tailf:info
              "Associate Upstream channels into this MD";
            type uint8 {
              tailf:info
                "<0-7>;;US channel index in the controller";
              range "0..7";
            }
          }
        }
        container cable {
          tailf:info
            "Cable interface subcommands";
          container tftp-enforce {
            tailf:info
              "Only allow modems to register if they attempt tftp first";
            tailf:cli-delete-when-empty;
            presence "true";
            leaf mark-only {
              tailf:info
                "Allow registration but mark violating modems with # symbol";
              type empty;
            }
          }
          leaf ip-init {
            tailf:info
              "IP Initialization Parameters";
            type enumeration {
              enum "apm" {
                tailf:info
                  "Alternate Provisioning mode";
              }
              enum "dual-stack" {
                tailf:info
                  "Dual-stack Provisioning mode";
              }
              enum "ipv4" {
                tailf:info
                  "IPv4 Provisioning mode";
              }
              enum "ipv6" {
                tailf:info
                  "IPv6 Provisioning mode";
              }
            }
            default "ipv4";
          }
          container mtc-mode {
            tailf:info
              "Enable/Disable Multiple Transmit Channel Mode";
            presence "true";
          }
          list rcc-template {
            tailf:info
              "Bind RCC template to interface";
            tailf:cli-suppress-mode;
            tailf:cli-delete-when-empty;
            key "index";
            leaf index {
              type uint8 {
                tailf:info
                  "<1-255>;;cable rcc-template id";
                range "1..255";
              }
            }
          }
          container rcp-control {
            tailf:info
              "Receive Channel Profile control";
            leaf verbose {
              tailf:info
                "Enable verbose reporting";
              type empty;
            }
          }
          container shared-secret {
            tailf:info
              "Shared Secret String";
            tailf:cli-compact-syntax;
            tailf:cli-sequence-commands;
            uses password-grouping;
          }
          container dynamic-secret {
            tailf:info
              "Enable dynamic secret for CM config files";
            tailf:cli-compact-syntax;
            tailf:cli-sequence-commands {
              tailf:cli-reset-siblings;
            }
            choice dynamic-secret-choice {
              case reject {
                leaf reject {
                  tailf:info
                    "Reject registration request from modems violating dynamic secret";
                  type empty;
                }
              }
              case mark {
                leaf mark {
                  tailf:info
                    "Mark modems violating dynamic secret";
                  type empty;
                }
              }
              case lock {
                leaf lock {
                  tailf:info
                    "Lock modems violating dynamic secret";
                  type empty;
                }
                leaf lock-qos {
                  tailf:cli-drop-node-name;
                  tailf:cli-optional-in-sequence;
                  type uint16 {
                    tailf:info
                      "<1-1023>;;Profile used to lock";
                    range "1..1023";
                  }
                }
              }
            }
            leaf nocrypt {
              tailf:info
                "Do not encrypt modem config file name";
              type empty;
            }
          }
          container enable-trap {
            tailf:info
              "Enable an SNMP cable trap";
            leaf cmonoff-notification {
              tailf:info
                "Cable Modem Online/Offline notification";
              type empty;
            }
            leaf cmonoff-interval {
              tailf:info
                "Interval in Seconds";
              type uint32 {
                tailf:info
                  "<0-86400>;;Interval in secs";
                range "0..86400";
              }
            }
          }
          leaf packet-cache {
            tailf:cli-boolean-no;
            tailf:cli-full-command;
            type boolean;
            default "true";
          }
          leaf default-phy-burst {
            tailf:info
              "Max phy burst if max long data grant is 0";
            type uint16 {
              tailf:info
                "<0-4096>;;Maximal number of bytes allowed in a burst";
              range "0..4096";
            }
          }
          container insertion-interval {
            tailf:info
              "Period between initial ranging opportunities - msec";
            choice interval-choice {
              leaf fixed-intrvl {
                tailf:cli-drop-node-name;
                type uint16 {
                  tailf:info
                    "<100-2000>;;Fixed period between initial ranging slots - msec";
                }
              }
              container automatic {
                tailf:info
                  "Use automatic adjustment algorithm for initial ranging period";
                tailf:cli-compact-syntax;
                tailf:cli-sequence-commands {
                  tailf:cli-reset-siblings;
                }
                leaf min-intrvl {
                  tailf:cli-drop-node-name;
                  type uint8 {
                    tailf:info
                      "<20-120>;;Lower bound on period between initial ranging slots - msecs";
                    range "20..120";
                  }
                  default "60";
                }
                leaf max-intrvl {
                  tailf:cli-drop-node-name;
                  type uint16 {
                    tailf:info
                      "<240-1800>;;Upper bound on period between initial ranging slots - msecs";
                    range "240..1800";
                  }
                  default "480";
                }
              }
            }
          }
          container map-advance {
            tailf:info
              "Set algorithm for the look-ahead time in MAPs";
            choice map-advance-choice {
              leaf static {
                type uint16 {
                  tailf:info
                    "<100-20000>;;max map advance - usecs";
                  range "100..20000";
                }
              }
              container dynamic {
                tailf:info
                  "Automatically tune the value to the current propagation delay";
                tailf:cli-compact-syntax;
                tailf:cli-sequence-commands;
                leaf safety {
                  tailf:cli-drop-node-name;
                  tailf:cli-incomplete-command;
                  type uint16 {
                    tailf:info
                      "<300-1500>;;Safety factor - usecs";
                    range "300..1500";
                  }
                }
                leaf max-delay {
                  tailf:cli-drop-node-name;
                  type uint16 {
                    tailf:info
                      "<100-20000>;;max map advance - usecs";
                    range "100..20000";
                  }
                }
              }
            }
          }
          leaf sync-interval {
            tailf:info
              "Interval between CMTS transmission of successive SYNC";
            type uint16 {
              tailf:info
                "<1-200>;;sync interval - msec";
              range "1..200";
            }
          }
          leaf bundle {
            tailf:info
              "Bundle number for bundling of cable interfaces";
            type uint8 {
              tailf:info
                "<1-255>;;Bundle number";
              range "1..255";
            }
          }
          container downstream {
            tailf:info
              "Downstream parameter configuration";
            leaf description {
              tailf:info
                "Downstream name/description";
              tailf:cli-multi-value;
              tailf:cli-preformatted;
              tailf:cli-full-command;
              type string {
                tailf:info
                  "LINE;;Up to 80 characters describing this DS port";
                length "0..80";
              }
            }
            container dsg {
              tailf:info
                "Downstream DSG settings";
              leaf timer {
                tailf:info
                  "DSG Timer Setting";
                type uint16 {
                  tailf:info
                    "<1-65535>;;DSG timer index.";
                }
              }
              list tg {
                tailf:info
                  "DSG Tunnel group";
                tailf:cli-suppress-mode;
                tailf:cli-delete-when-empty;
                key "tgid";
                leaf tgid {
                  type uint16 {
                    tailf:info
                      "<1-65535>;;DSG Tunnel Group ID";
                    range "1..65535";
                  }
                }
                list channel {
                  tailf:info
                    "DSG Channel";
                  tailf:cli-suppress-mode;
                  tailf:cli-delete-when-empty;
                  key "channel-id";
                  leaf channel-id {
                    type uint16 {
                      tailf:info
                        "<1-65535>;;DSG Channel ID";
                      range "1..65535";
                    }
                  }
                }
              }
            }
          }
          container upstream {
            tailf:info
              "Upstream port configuration";
            leaf balance-scheduling {
              tailf:info
                "upstream channel balance scheduling on one mac-domain";
              type empty;
            }
            leaf max-ports {
              tailf:info
                "Maximum number of upstream ports for this interface";
              type uint8 {
                tailf:info
                  "<0-8>;;Number of upstreams";
                range "0..8";
              }
            }
            list bonding-group {
              tailf:info
                "Configure upstream bonding group";
              tailf:cli-mode-name "config-upstream-bonding";
              key "id";
              leaf id {
                type uint16 {
                  tailf:info
                    "<1-65535>;;bonding group id";
                  range "1..65535";
                }
              }
              uses description-grouping;
              list upstream {
                tailf:info
                  "Add an upstream to this bonding group.";
                tailf:cli-suppress-mode;
                tailf:cli-delete-when-empty;
                key "number";
                leaf number {
                  type uint8 {
                    tailf:info
                      "<0-4>;;upstream to add";
                  }
                }
              }
              leaf attributes {
                tailf:info
                  "Configure attributes for this bonding group.";
                type string {
                  tailf:info
                    "<0-FFFFFFFF>;;UBG Attribute Value in hex";
                }
              }
            }
            container resiliency {
              tailf:info
                "upstream resiliency configuration";
              leaf on-failure {
                tailf:info
                  "ranging retries exceeded error handling";
                type enumeration {
                  enum "disable-channel" {
                    tailf:info
                      "disable channel";
                  }
                  enum "extended-ranging" {
                    tailf:info
                      "continue to range";
                  }
                  enum "reset-modem" {
                    tailf:info
                      "take modem offline";
                  }
                }
                default "extended-ranging";
              }
            }
            list cable-upstream-list {
              tailf:cli-drop-node-name;
              tailf:cli-suppress-mode;
              tailf:cli-delete-when-empty;
              key "port";
              leaf port {
                type uint8 {
                  tailf:info
                    "<0-4>;;Port number";
                }
              }
              leaf connector {
                tailf:info
                  "Physical upstream connector";
                type uint8 {
                  tailf:info
                    "<0-19>;;Physical port number";
                  range "0..19";
                }
              }
              leaf frequency {
                tailf:info
                  "Frequency";
                type uint32 {
                  tailf:info
                    "<5000000-85000000>;;Upstream Frequency in Hz";
                  range "5000000..85000000";
                }
              }
              container channel-width {
                tailf:info
                  "Channel width in HZ";
                tailf:cli-compact-syntax;
                tailf:cli-sequence-commands {
                  tailf:cli-reset-siblings;
                }
                leaf first-choice-width {
                  tailf:cli-drop-node-name;
                  type uint32 {
                    tailf:info
                      "Channel width Hz";
                  }
                }
                leaf last-choice-width {
                  tailf:cli-drop-node-name;
                  type uint32 {
                    tailf:info
                      "Channel width Hz";
                  }
                }
              }
              leaf description {
                tailf:info
                  "Upstream name/description";
                tailf:cli-multi-value;
                tailf:cli-preformatted;
                tailf:cli-full-command;
                type string {
                  tailf:info
                    "LINE;;Up to 80 characters describing this US port";
                }
              }
              leaf docsis-mode {
                tailf:info
                  "Upstream channel DOCSIS mode";
                type enumeration {
                  enum "atdma" {
                    tailf:info
                      "DOCSIS 2.0 ATDMA-only channel";
                  }
                  enum "scdma" {
                    tailf:info
                      "DOCSIS 2.0 SCDMA-only channel";
                  }
                  enum "tdma" {
                    tailf:info
                      "DOCSIS 1.x-only channel";
                  }
                  enum "tdma-atdma" {
                    tailf:info
                      "DOCSIS 1.x and DOCSIS 2.0 mixed channel";
                  }
                }
              }
              leaf minislot-size {
                tailf:info
                  "Minislot size";
                type uint8 {
                  tailf:info
                    "Minislot size in time ticks";
                  range "1|2|4|8|16|32|64|128";
                }
              }
              container power-adjust {
                tailf:info
                  "Power adjustment";
                leaf continue {
                  tailf:info
                    "Minimum power adjustment which set CONTINUE ranging status";
                  type uint8 {
                    tailf:info
                      "<2-15>;;Power level in dB";
                    range "2..15";
                  }
                }
              }
              container range-backoff {
                tailf:info
                  "Change Range Backoff Value";
                tailf:cli-compact-syntax;
                tailf:cli-sequence-commands;
                choice range-backoff-choice {
                  case automatic {
                    leaf automatic {
                      tailf:info
                        "Automatic Change Range Backoff Value";
                      type empty;
                    }
                  }
                  case numeric {
                    leaf start {
                      tailf:cli-drop-node-name;
                      tailf:cli-incomplete-command;
                      type uint8 {
                        tailf:info
                          "<0-15>;;rangebackoff-start";
                      }
                    }
                    leaf end {
                      tailf:cli-drop-node-name;
                      type uint8 {
                        tailf:info
                          "<0-15>;;rangebackoff-end";
                      }
                    }
                  }
                }
              }
              container modulation-profile {
                tailf:info
                  "Modulation Profile Number";
                tailf:cli-compact-syntax;
                tailf:cli-sequence-commands {
                  tailf:cli-reset-siblings;
                }
                leaf primary-profile-number {
                  tailf:cli-drop-node-name;
                  type uint8 {
                    tailf:info
                      "VALUE;;modulation number";
                  }
                }
                leaf secondary-profile-number {
                  tailf:cli-drop-node-name;
                  type uint8 {
                    tailf:info
                      "VALUE;;secondary modulation number";
                  }
                }
                leaf tertiary-profile-number {
                  tailf:cli-drop-node-name;
                  type uint8 {
                    tailf:info
                      "VALUE;;tertiary modulation number";
                  }
                }
              }
              leaf rate-limit {
                tailf:info
                  "Enable DOCSIS rate limiting on current upstream";
                tailf:cli-boolean-no;
                tailf:cli-full-command;
                type boolean;
              }
              leaf equalization-coefficient {
                tailf:info
                  "Enable equalization coefficient";
                type empty;
              }
              leaf equalization-error-recovery {
                tailf:info
                  "Enable equ coeff error recovery";
                tailf:cli-boolean-no;
                tailf:cli-full-command;
                type boolean;
                default "true";
              }
              container rate-adapt {
                tailf:info
                  "Configure upstream rate-adapt";
                presence "true";
              }
              leaf attribute-mask {
                tailf:info
                  "Upstream Channel Provisioned Attribute Mask";
                type string {
                  tailf:info
                    "<0-FFFFFFFF>;;Attribute mask in hex";
                }
              }
              leaf chan-class-id {
                tailf:info
                  "Channel Class ID";
                type string {
                  tailf:info
                    "<0-FFFFFFFF>;;Class ID Extension";
                }
              }
              leaf shutdown {
                tailf:info
                  "Shutdown upstream port";
                tailf:cli-boolean-no;
                tailf:cli-full-command;
                type boolean;
              }
            }
          }
          container sid-cluster-group {
            tailf:info
              "SID Cluster Group parameters for Upstream Channel Bonding";
            leaf dynamic {
              tailf:info
                "Dynamic algorithm";
              type empty;
            }
            leaf num-of-cluster {
              tailf:info
                "Number of SID Cluster Group";
              type uint8 {
                tailf:info
                  "<1-8>;;1, 2, 3, 4, 5, 6, 7, 8";
                range "1..8";
              }
            }
            leaf req-multiplier {
              tailf:info
                "Request Multiplier";
              type uint8 {
                tailf:info
                  "<1-16>;;1, 2, 4, 8, 16";
                range "1|2|4|8|16";
              }
            }
          }
          container sid-cluster-switching {
            tailf:info
              "SID Cluster Switching parameters for Upstream Channel Bonding";
            leaf max-request {
              tailf:info
                "Max request";
              type uint8 {
                tailf:info
                  "<0-255>;;0 to 255";
              }
            }
            leaf max-time {
              tailf:info
                "Max time";
              type uint16 {
                tailf:info
                  "<0-65535>;;0 to 65535";
              }
            }
          }
          container divert-rate-limit {
            tailf:info
              "Set divert-rate-limit parameters";
            tailf:cli-compact-syntax;
            tailf:cli-sequence-commands {
              tailf:cli-reset-siblings;
            }
            leaf rate {
              tailf:info
                "rate in packets/sec";
              tailf:cli-incomplete-command;
              type uint16 {
                tailf:info
                  "<1-65535>;;rate in packets/second";
              }
            }
            leaf limit {
              tailf:info
                "limit in packets";
              type uint16 {
                tailf:info
                  "<4-4194>;;limit in packets";
              }
            }
          }
          container privacy {
            tailf:info
              "Cable Privacy";
            leaf mandatory {
              tailf:info
                "force privacy be mandatory";
              type empty;
            }
            leaf bpi-plus-policy {
              tailf:info
                "Privacy requires BPI+";
              type enumeration {
                enum "capable-enforcement" {
                  tailf:info
                    "BPI+ required for all capable modems with BPI+ enabled (policy 1)";
                }
                enum "d11-enabled-enforcement" {
                  tailf:info
                    "BPI+ required for all D1.1 and later modems with BPI+ enabled (policy 2)";
                }
                enum "d11-enforcement" {
                  tailf:info
                    "BPI+ required for all D1.1 and later modems (policy 3)";
                }
                enum "total-enforcement" {
                  tailf:info
                    "BPI+ required for all modems (policy 4)";
                }
              }
            }
            leaf accept-self-signed-certificate {
              tailf:info
                "Accept Self signed Manufacturer certificate";
              type empty;
            }
            leaf eae-policy {
              tailf:info
                "Select EAE Policy";
              type enumeration {
                enum "capability-enforcement" {
                  tailf:info
                    "Enforce on EAE capable modems (policy 3)";
                  value 3;
                }
                enum "disable-enforcement" {
                  tailf:info
                    "Disable EAE (policy 1)";
                  value 1;
                }
                enum "ranging-enforcement" {
                  tailf:info
                    "Enforce on DOCSIS 3.0 modems (policy 2)";
                  value 2;
                }
                enum "total-enforcement" {
                  tailf:info
                    "Enforce EAE on all modems (policy 4)";
                  value 4;
                }
              }
            }
          }
        }
      }
      list Video {
        tailf:info
          "video service interface";
        tailf:cli-allow-join-with-key {
          tailf:cli-display-joined;
        }
        tailf:cli-mode-name "config-if";
        tailf:cli-suppress-key-abbreviation;
        key "name";
        leaf name {
          type string {
            pattern '[0-9]+.*';
          }
        }
        uses interface-common-pre-grouping;
        uses interface-common-grouping;
      }
      list Integrated-Cable {
        tailf:info
          "Integrated Cable interface";
        tailf:cli-allow-join-with-key {
          tailf:cli-display-joined;
        }
        tailf:cli-mode-name "config-if";
        tailf:cli-suppress-key-abbreviation;
        key "name";
        leaf name {
          type string {
            pattern '[0-9]+.*';
          }
        }
        uses interface-common-pre-grouping;
        uses interface-common-grouping;
        container cable {
          tailf:info
            "Integrated-Cable interface subcommands";
          leaf bundle {
            tailf:info
              "Bundle number for bundling of IC cable interfaces";
            type uint8 {
              tailf:info
                "<1-255>;;Bundle number";
              range "1..255";
            }
          }
          container rf-bandwidth-percent {
            tailf:info
              "% of reserved RF channel bandwidth";
            leaf percent-value {
              tailf:cli-drop-node-name;
              type uint8 {
                tailf:info
                  "<1-100>;;% bandwidth";
                range "1..100";
              }
            }
          }
        }
      }
      list Modular-Cable {
        tailf:info
          "Modular Cable interface";
        tailf:cli-allow-join-with-key {
          tailf:cli-display-joined;
        }
        tailf:cli-mode-name "config-if";
        tailf:cli-suppress-key-abbreviation;
        key "name";
        leaf name {
          type string {
            pattern '[0-9]+.*';
          }
        }
        uses interface-common-pre-grouping;
        uses interface-common-grouping;
        container cable {
          tailf:info
            "MC Cable interface subcommands";
          leaf bundle {
            tailf:info
              "Bundle number for bundling of MC cable interfaces";
            type uint8 {
              tailf:info
                "<1-255>;;Bundle number";
              range "1..255";
            }
          }
          container rf-bandwidth-percent {
            tailf:info
              "% of RF channel bandwidth reserved for this MC interface";
            tailf:cli-compact-syntax;
            tailf:cli-sequence-commands {
              tailf:cli-reset-siblings;
            }
            leaf percent-value {
              tailf:cli-drop-node-name;
              type uint8 {
                tailf:info
                  "<1-96>;;% bandwidth";
                range "1..96";
              }
            }
            container remaining {
              tailf:info
                "ratio of the remaining bandwidth";
              tailf:cli-flatten-container;
              tailf:cli-compact-syntax;
              leaf ratio {
                tailf:info
                  "ratio for sharing excess bandwidth";
                type uint8 {
                  tailf:info
                    "<1-100>;;Ratio";
                }
              }
            }
          }
          container cm-status {
            tailf:info
              "CM-STATUS events";
            container enable {
              tailf:info
                "enable CM-STATUS events";
              leaf no-list {
                tailf:info
                  "'no  cable cm-status enable' entry";
                tailf:cli-multi-value;
                tailf:cli-preformatted;
                tailf:cli-full-command;
                type string {
                  tailf:info
                    "<grouplist>;;CM-STATUS event list to disable";
                }
              }
            }
          }
        }
      }
      list Wideband-Cable {
        tailf:info
          "Wideband CMTS interface";
        tailf:cli-allow-join-with-key {
          tailf:cli-display-joined;
        }
        tailf:cli-mode-name "config-if";
        tailf:cli-suppress-key-abbreviation;
        key "name";
        leaf name {
          type string {
            pattern '[0-9]+.*';
          }
        }
        uses interface-common-pre-grouping;
        uses interface-common-grouping;
        container cable {
          tailf:info
            "Cable interface subcommands";
          leaf bundle {
            tailf:info
              "Bundle number for bundling of cable interfaces";
            tailf:cli-remove-before-change;
            type uint8 {
              tailf:info
                "<1-255>;;Bundle number";
              range "1..255";
            }
          }
          container privacy {
            tailf:info
              "Cable Privacy";
            leaf accept-self-signed-certificate {
              tailf:info
                "Accept Self signed Manufacturer certificate";
              type empty;
            }
          }
          leaf ds-resiliency {
            tailf:info
              "Downstream resiliency bonding group";
            type empty;
          }
          container rf-channel {
            tailf:info
              "RF channel associated with this Wideband interface";
            list rf-channel-list {
              tailf:cli-drop-node-name;
              tailf:cli-suppress-mode;
              tailf:cli-delete-when-empty;
              tailf:cli-compact-syntax;
              tailf:cli-sequence-commands {
                tailf:cli-reset-siblings;
              }
              key "rf-port";
              leaf rf-port {
                type uint8 {
                  tailf:info
                    "<0-23>;;RF channel number";
                  range "0..23";
                }
              }
              leaf bandwidth-percent {
                tailf:info
                  "% bandwidth of RF channel reserved for this Wideband interface";
                type uint8 {
                  tailf:info
                    "<1-100>;;% bandwidth";
                  range "1..100";
                }
              }
              container remaining {
                tailf:info
                  "ratio of the remaining bandwidth";
                tailf:cli-flatten-container;
                tailf:cli-compact-syntax;
                leaf ratio {
                  tailf:info
                    "ratio for sharing excess bandwidth";
                  type uint8 {
                    tailf:info
                      "<1-100>;;Ratio";
                  }
                }
              }
            }
          }
          container rf-channels {
            tailf:info
              "rf-channels associated with this Wideband interface";
            list channel-list {
              tailf:info
                "Configure list of individual rf-channels and ranges of rf-channels";
              tailf:cli-suppress-mode;
              tailf:cli-delete-when-empty;
              tailf:cli-compact-syntax;
              tailf:cli-sequence-commands;
              key "bandwidth-percent";
              leaf bandwidth-percent {
                tailf:cli-expose-key-name;
                tailf:info
                  "% bandwidth of RF channel reserved for this Wideband interface";
                type uint8 {
                  tailf:info
                    "<1-100>;;% bandwidth";
                  range "1..100";
                }
              }
              leaf-list group-list {
                tailf:cli-drop-node-name;
                tailf:cli-prefix-key;
                tailf:cli-range-list-syntax;
                type uint8 {
                  tailf:info
                    "<grouplist>;;List of individual rf-channels and ranges of rf-channels";
                }
              }
            }
            list controller {
              tailf:info
                "Specify controller for rf-channels";
              tailf:cli-suppress-mode;
              tailf:cli-delete-when-empty;
              tailf:cli-compact-syntax;
              tailf:cli-sequence-commands;
              tailf:cli-incomplete-command;
              key "id";
              leaf id {
                type uint8 {
                  tailf:info
                    "<0-3>;;Enter controller number";
                  range "0..3";
                }
              }
              leaf-list channel-list {
                tailf:info
                  "Configure list of individual rf-channels and ranges of rf-channels";
                tailf:cli-range-list-syntax;
                tailf:cli-incomplete-command;
                tailf:cli-incomplete-no;
                type uint8 {
                  tailf:info
                    "<grouplist>;;List of individual rf-channels and ranges of rf-channels";
                }
              }
              leaf bandwidth-percent {
                tailf:info
                  "% bandwidth of RF channel reserved for this Wideband interface";
                type uint8 {
                  tailf:info
                    "<1-100>;;% bandwidth";
                  range "1..100";
                }
              }
            }
          }
          container downstream {
            tailf:info
              "Downstream parameter configuration";
            leaf attribute-mask {
              tailf:info
                "Downstream channel provisioned Attribute Mask";
              type string {
                tailf:info
                  "<0-FFFFFFFF>;;The attribute bitmap in hex";
              }
            }
          }
        }
      }
      list Bundle {
        tailf:info
          "Virtual Bundle";
        tailf:cli-allow-join-with-key {
          tailf:cli-display-joined;
        }
        tailf:cli-mode-name "config-if";
        tailf:cli-suppress-key-abbreviation;
        key "name";
        leaf name {
          type uint8 {
            tailf:info
              "<1-255>;;Bundle interface number";
            range "1..255";
          }
        }
        uses interface-common-pre-grouping;
        uses interface-common-grouping;
        container cable {
          tailf:info
            "Cable interface subcommands";
          leaf nd {
            tailf:info
              "Enable IPv6 ND gleaning";
            tailf:cli-boolean-no;
            tailf:cli-full-command;
            type boolean;
            default "true";
          }
          container arp {
            tailf:info
              "Enable arp request";
            container filter {
              tailf:info
                "Filter arp packets";
              container request-send {
                tailf:info
                  "send x arp requests every y seconds or none";
                tailf:cli-show-no;
                tailf:cli-compact-syntax;
                tailf:cli-sequence-commands;
                tailf:cli-delete-when-empty;
                tailf:cli-incomplete-command;
                presence "true";
                leaf number {
                  tailf:cli-drop-node-name;
                  tailf:cli-incomplete-command;
                  type uint8 {
                    tailf:info
                      "<0-20>;;number of arp request packets";
                  }
                }
                leaf window-size {
                  tailf:cli-drop-node-name;
                  type uint8 {
                    tailf:info
                      "<1-5>;;size of time window in seconds";
                  }
                }
              }
              container reply-accept {
                tailf:info
                  "accept x arp replies every y seconds or none";
                tailf:cli-show-no;
                tailf:cli-compact-syntax;
                tailf:cli-sequence-commands;
                tailf:cli-delete-when-empty;
                tailf:cli-incomplete-command;
                presence "true";
                leaf number {
                  tailf:cli-drop-node-name;
                  tailf:cli-incomplete-command;
                  type uint8 {
                    tailf:info
                      "<0-20>;;number of arp reply packets";
                  }
                }
                leaf window-size {
                  tailf:cli-drop-node-name;
                  type uint8 {
                    tailf:info
                      "<1-5>;;size of time window in seconds";
                  }
                }
              }
            }
          }
          container conf {
            tailf:cli-drop-node-name;
            leaf arp {
              tailf:cli-boolean-no;
              tailf:cli-full-command;
              type boolean;
              default "true";
            }
          }
          container ipv6 {
            tailf:info
              "IPv6 related configuration";
            container source-verify {
              tailf:info
                "Enable verification of source of IPv6 packets";
              container dhcp {
                tailf:info
                  "Verify address with the DHCPv6 server";
                presence "true";
                leaf server {
                  tailf:info
                    "Specify the lease query server where the DHCPv6 lease queries should be sent";
                  type inet:ipv6-address {
                    tailf:info
                      "X:X:X:X::X;;IPv6 Address of the lease query server";
                  }
                }
              }
              container leasequery-filter {
                tailf:info
                  "Filter x IPv6 lease query requests every y seconds or none";
                container upstream {
                  tailf:info
                    "IPv6 Lease query for upstream pkts";
                  tailf:cli-compact-syntax;
                  tailf:cli-sequence-commands;
                  leaf threshold {
                    tailf:cli-drop-node-name;
                    tailf:cli-incomplete-command;
                    type uint8 {
                      tailf:info
                        "<0-20>;;Number of IPv6 lease queries per sid";
                      range "0..20";
                    }
                  }
                  leaf interval {
                    tailf:cli-drop-node-name;
                    type uint8 {
                      tailf:info
                        "<1-5>;;size of time window in seconds for IPv6";
                      range "1..5";
                    }
                  }
                }
              }
              leaf leasetimer {
                tailf:info
                  "Specify the IPv6 lease timer value";
                type uint8 {
                  tailf:info
                    "<1-240>;;IPv6 Time in minutes";
                  range "1..240";
                }
              }
            }
          }
          leaf source-verify {
            tailf:info
              "Enable verification of source of packets";
            tailf:cli-full-command;
            type empty;
          }
          container source-verify-conf {
            tailf:cli-drop-node-name;
            container source-verify {
              tailf:info
                "Enable verification of source of packets";
              tailf:cli-incomplete-command;
              tailf:cli-incomplete-no;
              container dhcp {
                tailf:info
                  "Verify address with the DHCPv4 server";
                presence "true";
                leaf server {
                  tailf:info
                    "Specify the lease query server where the DHCPv4 lease queries should be sent";
                  type inet:ipv4-address {
                    tailf:info
                      "A.B.C.D;;IPv4 Address of the lease query server";
                  }
                }
              }
              container leasequery-filter {
                tailf:info
                  "Filter x IPv4 lease query requests every y seconds or none";
                container upstream {
                  tailf:info
                    "Lease query for upstream pkts";
                  tailf:cli-compact-syntax;
                  tailf:cli-sequence-commands;
                  leaf threshold {
                    tailf:cli-drop-node-name;
                    tailf:cli-incomplete-command;
                    type uint8 {
                      tailf:info
                        "<0-20>;;Number of IPv4 lease queries per sid";
                      range "0..20";
                    }
                  }
                  leaf interval {
                    tailf:cli-drop-node-name;
                    type uint8 {
                      tailf:info
                        "<1-5>;;size of time window in seconds for IPv4";
                      range "1..5";
                    }
                  }
                }
              }
              leaf leasetimer {
                tailf:info
                  "Specify the IPv4 lease timer value";
                type uint8 {
                  tailf:info
                    "<1-240>;;IPv4 Time in minutes";
                  range "1..240";
                }
              }
            }
          }
          container dhcp-parse {
            tailf:info
              "DHCP parse option";
            leaf option-43 {
              tailf:info
                "DHCP parse option 43";
              type empty;
            }
            leaf option-60 {
              tailf:info
                "DHCP parse option 60";
              type empty;
            }
          }
          container dhcp-giaddr {
            tailf:info
              "Control of giaddr in relayed DHCP requests";
            choice dhcp-giaddr-choice {
              container policy {
                tailf:info
                  "Use primary address for CMs, secondary addresses for hosts";
                presence "true";
              }
              leaf primary {
                tailf:info
                  "Use primary address for all devices";
                type empty;
              }
            }
          }
          list helper-address {
            tailf:info
              "Specify a destination address for UDP broadcasts";
            tailf:cli-suppress-mode;
            tailf:cli-delete-when-empty;
            key "IP-address";
            leaf IP-address {
              type inet:ipv4-address {
                tailf:info
                  "A.B.C.D;;IP destination address";
              }
            }
          }
        }
      }
      list Cellular {
        tailf:info
          "Cellular WAN interface";
        tailf:cli-allow-join-with-key {
          tailf:cli-display-joined;
        }
        tailf:cli-mode-name "config-if";
        tailf:cli-suppress-key-abbreviation;
        key "name";
        leaf name {
          type string {
            pattern '[0-9]+.*';
          }
        }
        uses interface-common-pre-grouping;
        uses interface-common-grouping;
        uses interface-pointtopoint-grouping;
      }
      list Qam-red {
        tailf:info
          "QAM red interface";
        tailf:cli-allow-join-with-key {
          tailf:cli-display-joined;
        }
        tailf:cli-mode-name "config-if";
        tailf:cli-suppress-key-abbreviation;
        key "name";
        leaf name {
          type string {
            pattern '[0-9]+.*';
          }
        }
        uses interface-common-pre-grouping;
        uses interface-common-grouping;
        container cable {
          tailf:info
            "cable config for qam subinterfaces";
          leaf carrier-id {
            tailf:info
              "QAM carrier id. 1-192 ids are for QAM block 1, 193-384 for QAM block 2";
            type uint16 {
              tailf:info
                "<1-384>;;QAM Carrier id per line card";
              range "1..384";
            }
          }
          container mode {
            tailf:info
              "Setup qam channel mode to DEPI or Video";
            container depi {
              tailf:info
                "DEPI mode";
              choice depi-choice {
                container local {
                  tailf:info
                    "Sessions are configured locally";
                }
                container remote {
                  tailf:info
                    "Sessions are configured remotely";
                  tailf:cli-delete-when-empty;
                  presence "true";
                  leaf learn {
                    tailf:info
                      "QAM can be configured remotely";
                    type empty;
                  }
                }
              }
            }
          }
          container downstream {
            tailf:info
              "downstream port of the line card";
            leaf max-carriers {
              tailf:info
                "max carriers per port";
              tailf:cli-full-command;
              type uint8 {
                tailf:info
                  "<1-128>;;max carriers per port";
                range "1..128";
              }
            }
            leaf lqam-group {
              tailf:info
                "Logical QAM group";
              type uint8 {
                tailf:info
                  "<1-48>;;QAM Logical group per line card";
                range "1..48";
              }
            }
            leaf tsid {
              tailf:info
                "set the downstream transport stream id";
              tailf:cli-full-command;
              type uint16 {
                tailf:info
                  "<1-65535>;;transport stream id";
              }
            }
          }
        }
        container depi {
          tailf:info
            "DEPI Session commands";
          leaf depi-tunnel {
            tailf:info
              "Name to use for DEPI Tunnel";
            tailf:cli-full-command;
            type string {
              tailf:info
                "WORD;;Enter DEPI Tunnel Name";
            }
          }
        }
      }
      list Asi {
        tailf:info
          "ASI interface";
        tailf:cli-allow-join-with-key {
          tailf:cli-display-joined;
        }
        tailf:cli-mode-name "config-if";
        tailf:cli-suppress-key-abbreviation;
        key "name";
        leaf name {
          type string {
            pattern '[0-9]+.*';
          }
        }
        uses interface-common-pre-grouping;
        uses interface-common-grouping;
      }
      list Vlan {
        tailf:info
          "Catalyst Vlans";
        tailf:cli-allow-join-with-key {
          tailf:cli-display-joined;
        }
        tailf:cli-diff-dependency "../../vlan/vlan-list" {
          tailf:xpath-root 3;
        }
        key "name";
        leaf name {
          type uint16 {
            tailf:info
              "<1-4094>;;Vlan interface number";
            range "1..4094";
          }
        }
        uses interface-common-pre-grouping;
        uses interface-ethernet-pre-grouping;
        uses interface-ethernet-grouping;
        uses interface-common-grouping;
        uses interface-ethernet-post-grouping;
      }
      list Async {
        tailf:info
          "Async interface";
        tailf:cli-allow-join-with-key {
          tailf:cli-display-joined;
        }
        key "name";
        leaf name {
          type string {
            tailf:info
              "WORD;;Async interface id";
            pattern '[0-9]+.*';
          }
        }
        uses interface-common-pre-grouping;
        uses interface-common-grouping;
        uses interface-pointtopoint-grouping;
      }
      list Group-Async {
        tailf:info
          "Async Group interface";
        tailf:cli-allow-join-with-key {
          tailf:cli-display-joined;
        }
        key "name";
        leaf name {
          type uint16 {
            tailf:info
              "<0-64>;;Group-Async interface number";
            range "0..64";
          }
        }
        uses interface-common-pre-grouping;
        uses interface-common-grouping;
        uses interface-pointtopoint-grouping;
      }
      list POS {
        tailf:info
          "POS interface";
        tailf:cli-allow-join-with-key {
          tailf:cli-display-joined;
        }
        tailf:cli-mode-name "config-if";
        tailf:cli-suppress-key-abbreviation;
        key "name";
        leaf name {
          type string {
            pattern '[0-9]+.*';
          }
        }
        uses interface-common-pre-grouping;
        uses interface-common-grouping;
        uses interface-pointtopoint-grouping;
        container aps {
          tailf:info
            "Configure APS";
          leaf group {
            tailf:info
              "Group association";
            type uint8 {
              tailf:info
                "Number of the group. Range is from 1 through 255.";
              range "1..255";
            }
          }
          list protect {
            tailf:info
              "Protect specified circuit";
            tailf:cli-suppress-mode;
            tailf:cli-delete-when-empty;
            key "circuit-number ip-address";
            leaf circuit-number {
              type uint32 {
                tailf:info
                  "Number of the circuit to enable as a protect interface.";
              }
            }
            leaf ip-address {
              type inet:ip-address {
                tailf:info
                  "IP address of the router that has the working POS interface.";
              }
            }
          }
          leaf working {
            tailf:info
              "Working channel number";
            type uint32 {
              tailf:info
                "Circuit number associated with this working interface.";
            }
          }
        }
        container pos {
          tailf:info
            "Modify POS parameters";
          leaf ais-shut {
            tailf:info
              "Enable sending SONET/SDH LAIS when shutdown";
            tailf:cli-full-command;
            type empty;
          }
          leaf framing {
            tailf:info
              "specify framing";
            tailf:cli-full-command;
            type enumeration {
              enum "sdh" {
                tailf:info
                  "Select sdh framing";
              }
              enum "sonet" {
                tailf:info
                  "Select sonet framing(default)";
              }
            }
            default "sonet";
          }
          container report {
            tailf:info
              "Configure SONET/SDH path alarm reporting";
            leaf rdool {
              type empty;
            }
            leaf lais {
              tailf:info
                "Set Path Alarm Indication Signal reporting status";
              type empty;
            }
            leaf lrdi {
              type empty;
            }
            leaf pais {
              tailf:info
                "Set Path Alarm Indication Signal reporting status";
              type empty;
            }
            leaf prdi {
              tailf:info
                "Set Path Remote Defect Indication reporting status";
              type empty;
            }
            leaf sd-ber {
              type empty;
            }
          }
          leaf scramble-atm {
            tailf:info
              "Enable ATM scrambling";
            tailf:cli-full-command;
            type empty;
          }
          container threshold {
            tailf:info
              "Configure SONET/SDH section/line BER threshold values";
            leaf sf-ber {
              tailf:info
                "Set Signal Fail BER threshold";
              tailf:cli-full-command;
              type uint8 {
                tailf:info
                  "<3-9>;;Bit error rate (10 to the minus n) (default 3)";
                range "3..9";
              }
              default "3";
            }
          }
          container flag {
            tailf:info
              "Specify byte value";
            leaf c2 {
              tailf:info
                "Path overhead byte";
              tailf:cli-full-command;
              type uint8 {
                tailf:info
                  "<0-255>;;byte value";
              }
            }
            leaf j0 {
              tailf:info
                "Section trace byte (default is 0x01)";
              tailf:cli-full-command;
              type uint8 {
                tailf:info
                  "<0-255>;;byte value";
              }
            }
            leaf s1s0 {
              tailf:info
                "Specify bit S1 and S0 of H1 (default is 0)";
              type uint8 {
                tailf:info
                  "<0-3>;;S1 & S0 bits (default is 0)";
                range "0..3";
              }
              default "0";
            }
          }
          container delay {
            tailf:info
              "Delay POS alarm triggers";
            container triggers {
              tailf:info
                "Triggers line protocol to go down";
              leaf line {
                tailf:info
                  "Specify delay for SONET LINE level triggers (S-LOS, S-LOF, L-AIS)";
                type uint16 {
                  tailf:info
                    "<0-60000>;;Holdoff time, in msec";
                  range "0..60000";
                }
              }
              leaf path {
                tailf:info
                  "Enable SONET PATH level triggers (P-AIS, P-LOP, P-RDI), with optional delay";
                type uint16 {
                  tailf:info
                    "<0-60000>;;Holdoff time, in msec";
                  range "0..60000";
                }
              }
            }
          }
        }
      }
      list Serial {
        tailf:info
          "Serial interface";
        tailf:cli-allow-join-with-key {
          tailf:cli-display-joined;
        }
        tailf:cli-mode-name "config-if";
        tailf:cli-suppress-key-abbreviation;
        key "name";
        leaf name {
          type string {
            pattern '[0-9]+(/[\.0-9]+)*(:[0-9]+)?';
          }
        }
        uses interface-common-pre-grouping;
        uses interface-common-grouping;
        uses interface-pointtopoint-grouping;
      }
      container Serial-subinterface {
        tailf:cli-drop-node-name;
        list Serial {
          tailf:info
            "Serial interface";
          tailf:cli-allow-join-with-key {
            tailf:cli-display-joined;
          }
          tailf:cli-mode-name "config-subif";
          tailf:cli-suppress-key-abbreviation;
          tailf:cli-incomplete-command;
          key "name";
          leaf name {
            tailf:cli-diff-dependency "../../../Serial" {
              tailf:xpath-root 3;
            }
            type string {
              pattern '[0-9]+(/[\.0-9]+)*(:[0-9]+)?\.[0-9]+';
            }
          }
          leaf type {
            tailf:cli-drop-node-name;
            tailf:cli-hide-in-submode;
            type enumeration {
              enum "multipoint" {
                tailf:info
                  "Treat as a multipoint link";
              }
              enum "point-to-point" {
                tailf:info
                  "Treat as a point-to-point link";
              }
            }
          }
          uses interface-common-pre-grouping;
          uses sub-interface-common-grouping;
          uses interface-pointtopoint-grouping;
        }
      }
      list Virtual-Template {
        tailf:info
          "Virtual Template interface";
        tailf:cli-allow-join-with-key {
          tailf:cli-display-joined;
        }
        tailf:cli-mode-name "config-if";
        tailf:cli-suppress-key-abbreviation;
        tailf:cli-recursive-delete;
        tailf:cli-explicit-exit;
        key "name";
        leaf name {
          type uint16 {
            tailf:info
              "<1-4095>;;Virtual-Template interface number";
            range "1..4095";
          }
        }
        leaf type {
          tailf:info
            "type of the virtual-template";
          tailf:cli-hide-in-submode;
          type enumeration {
            enum "ethernet" {
              tailf:info
                "Set VT type as ethernet";
            }
            enum "serial" {
              tailf:info
                "Set VT type as serial";
            }
            enum "tunnel" {
              tailf:info
                "Set VT type as tunnel";
            }
          }
        }
        uses interface-common-pre-grouping;
        uses interface-ethernet-pre-grouping;
        uses interface-ethernet-grouping;
        uses interface-common-grouping;
        uses interface-ethernet-post-grouping;
        uses interface-pointtopoint-grouping;
        uses interface-tunnel-grouping;
      }
      list pseudowire {
        tailf:info
          "Pseudowire Interface";
        tailf:cli-allow-join-with-key {
          tailf:cli-display-joined;
        }
        tailf:cli-mode-name "config-if";
        tailf:cli-suppress-key-abbreviation;
        key "name";
        leaf name {
          type uint32 {
            tailf:info
              "<1-231072>;;pseudowire interface number";
            range "1..231072";
          }
        }
        leaf description {
          tailf:info
            "Interface specific description";
          tailf:cli-multi-value;
          tailf:cli-preformatted;
          tailf:cli-full-command;
          type string {
            tailf:info
              "WORD;;Description string";
            length "0..200";
          }
        }
        leaf shutdown {
          tailf:info
            "Shutdown the selected interface";
          tailf:cli-show-no;
          tailf:cli-full-command;
          type empty;
        }
        container source {
          tailf:info
            "Get config from another source";
          container template {
            tailf:info
              "Get config from a template";
            tailf:cli-compact-syntax;
            tailf:cli-sequence-commands {
              tailf:cli-reset-siblings;
            }
            leaf type {
              tailf:info
                "Type of the template";
              type enumeration {
                enum "pseudowire" {
                  tailf:info
                    "Template customized interface pseudowire";
                }
              }
            }
            leaf name {
              tailf:cli-drop-node-name;
              tailf:non-strict-leafref {
                path "../../../../../template/name";
              }
              type string {
                tailf:info
                  "WORD;;Template name";
              }
            }
          }
        }
        leaf encapsulation {
          tailf:info
            "Data encapsulation method";
          tailf:cli-full-command;
          type enumeration {
            enum "l2tpv3" {
              tailf:info
                "Use L2TPv3 encapsulation";
            }
            enum "mpls" {
              tailf:info
                "Use MPLS encapsulation";
            }
          }
        }
        container signaling {
          tailf:info
            "Signaling options";
          leaf protocol {
            tailf:info
              "Signaling protocol to use";
            type enumeration {
              enum "ldp" {
                tailf:info
                  "Use LDP signaling";
              }
              enum "none" {
                tailf:info
                  "No signaling, use manually configured pseudowires";
              }
            }
          }
        }
        container neighbor {
          tailf:info
            "Neighbor options";
          tailf:cli-compact-syntax;
          tailf:cli-sequence-commands;
          leaf address {
            tailf:cli-drop-node-name;
            tailf:cli-incomplete-command;
            type inet:ipv4-address {
              tailf:info
                "A.B.C.D;;IP address of the peer PE";
            }
          }
          leaf vcid {
            tailf:cli-drop-node-name;
            type uint32 {
              tailf:info
                "<1-4294967295>;;Peer VC ID value";
              range "1..4294967295";
            }
          }
        }
        leaf mtu {
          tailf:info
            "set Maximum Transmission Unit";
          tailf:cli-full-command;
          type uint16 {
            tailf:info
              "<64-65535>;;Maximum Transmission Unit value";
            range "64..65535";
          }
        }
        leaf control-word {
          tailf:info
            "Control-word options";
          type enumeration {
            enum "exclude" {
              tailf:info
                "Exclude control-word in pseudowire packets";
            }
            enum "include" {
              tailf:info
                "Include control-word in pseudowire packets";
            }
          }
        }
        container label {
          tailf:info
            "MPLS local and remote pseudowire static labels";
          tailf:cli-compact-syntax;
          tailf:cli-sequence-commands;
          tailf:cli-diff-dependency "../../../mpls/label/range" {
            tailf:xpath-root 3;
          }
          leaf local-pseudowire-label {
            tailf:cli-drop-node-name;
            tailf:cli-incomplete-command;
            type uint32 {
              tailf:info
                "<0-4294967295>;;Local pseudowire label";
            }
          }
          leaf remote-pseudowire-label {
            tailf:cli-drop-node-name;
            type uint32 {
              tailf:info
                "<16-1048575>;;Remote pseudowire label";
              range "16..1048575";
            }
          }
        }
        container pseudowire {
          tailf:info
            "Pseudowire parameters";
          tailf:cli-diff-dependency "../signaling/protocol" {
            tailf:xpath-root 3;
          }
          leaf type {
            tailf:info
              "Pseudowire type";
            type string {
              tailf:info
                "XY;;Pseudowire Type in hex format";
            }
          }
        }
        container service-policy {
          tailf:info
            "Configure Service Policy";
          uses service-policy-grouping;
        }
      }
      list LISP {
        tailf:info
          "Locator/ID Separation Protocol Virtual Interface";
        tailf:cli-allow-join-with-key {
          tailf:cli-display-joined;
        }
        tailf:cli-mode-name "config-if";
        tailf:cli-suppress-key-abbreviation;
        key "name";
        leaf name {
          type uint16 {
            tailf:info
              "<0-1999>;;LISP interface number";
            range "0..1999";
          }
        }
        uses interface-common-pre-grouping;
        uses interface-common-grouping;
      }
      container LISP-subinterface {
        tailf:cli-drop-node-name;
        list LISP {
          tailf:cli-allow-join-with-key {
            tailf:cli-display-joined;
          }
          tailf:cli-mode-name "config-subif";
          tailf:cli-suppress-key-abbreviation;
          key "name";
          leaf name {
            tailf:cli-diff-dependency "../../../LISP" {
              tailf:xpath-root 3;
            }
            type string {
              pattern '[0-9]+\.[0-9]+';
            }
          }
          uses interface-common-pre-grouping;
          uses sub-interface-common-grouping;
        }
      }
      list vasileft {
        tailf:info
          "VasiLeft interface";
        tailf:cli-full-command;
        tailf:cli-allow-join-with-key {
          tailf:cli-display-joined;
        }
        tailf:cli-mode-name "config-if";
        tailf:cli-suppress-key-abbreviation;
        key "name";
        leaf name {
          type uint16 {
            tailf:info
              "<1-1000>;;vasileft interface number";
            range "1..1000";
          }
        }
        uses interface-common-pre-grouping;
        uses interface-common-grouping;
      }
      list vasiright {
        tailf:info
          "VasiRight interface";
        tailf:cli-allow-join-with-key {
          tailf:cli-display-joined;
        }
        tailf:cli-mode-name "config-if";
        tailf:cli-suppress-key-abbreviation;
        key "name";
        leaf name {
          type uint16 {
            tailf:info
              "<1-1000>;;vasiright interface number";
            range "1..1000";
          }
        }
        uses interface-common-pre-grouping;
        uses interface-common-grouping;
      }
      list AppNav-Compress {
        tailf:info
          "Service-Context Virtual Interface Compress";
        tailf:cli-full-command;
        tailf:cli-allow-join-with-key {
          tailf:cli-display-joined;
        }
        tailf:cli-mode-name "config-if";
        tailf:cli-suppress-key-abbreviation;
        tailf:cli-diff-dependency "../../service-insertion/service-context" {
          tailf:xpath-root 3;
        }
        key "name";
        leaf name {
          type uint16 {
            tailf:info
              "<1-1000>;;AppNav-Compress interface number";
            range "1..1000";
          }
        }
        uses interface-common-pre-grouping;
        uses interface-common-grouping;
      }
      list AppNav-UnCompress {
        tailf:info
          "Service-Context Virtual interface UnCompress";
        tailf:cli-full-command;
        tailf:cli-allow-join-with-key {
          tailf:cli-display-joined;
        }
        tailf:cli-mode-name "config-if";
        tailf:cli-suppress-key-abbreviation;
        tailf:cli-diff-dependency "../../service-insertion/service-context" {
          tailf:xpath-root 3;
        }
        key "name";
        leaf name {
          type uint16 {
            tailf:info
              "<1-1000>;;AppNav-UnCompress interface number";
            range "1..1000";
          }
        }
        uses interface-common-pre-grouping;
        uses interface-common-grouping;
      }
      list ucse {
        tailf:info
          "Cisco ucse server";
        tailf:cli-allow-join-with-key {
          tailf:cli-display-joined;
        }
        tailf:cli-mode-name "config-if";
        tailf:cli-suppress-key-abbreviation;
        key "name";
        leaf name {
          tailf:cli-suppress-range;
          type string {
            pattern '[0-9]+.*';
          }
        }
        uses interface-common-pre-grouping;
        uses interface-ethernet-pre-grouping;
        uses interface-switch-grouping;
        uses interface-ethernet-switch-grouping;
        uses interface-common-switch-grouping;
        uses interface-ethernet-post-grouping;
      }
    }
    container access-list {
      tailf:ncs-device-type "cli-ned";
      tailf:display-when "not(../../ncs:module) or ../../ncs:module[ncs:name='tailf-ned-cisco-ios']";
      tailf:info
        "Add an access list entry";
      tailf:cli-incomplete-command;
      list access-list {
        tailf:cli-drop-node-name;
        tailf:cli-suppress-mode;
        tailf:cli-delete-when-empty;
        tailf:cli-compact-syntax;
        tailf:cli-incomplete-command;
        tailf:meta-data "replace-list" {
          tailf:meta-value "access-list :: rule :: rule";
        }
        tailf:ned-data "." {
          tailf:xpath-root 3;
          tailf:transaction to;
        }
        key "id";
        leaf id {
          tailf:cli-incomplete-no;
          tailf:cli-suppress-range;
          type union {
            type uint16 {
              tailf:info
                "<1-99>;;IP standard access list";
              range "1..99";
            }
            type uint16 {
              tailf:info
                "<100-199>;;IP extended access list";
              range "100..199";
            }
            type uint16 {
              tailf:info
                "<200-299>;;Protocol type-code access list";
              range "200..299";
            }
            type uint16 {
              tailf:info
                "<600-699>;;Appletalk access list";
              range "600..699";
            }
            type uint16 {
              tailf:info
                "<700-799>;;48-bit MAC address access list";
              range "700..799";
            }
            type uint16 {
              tailf:info
                "<800-899>;;IPX standard access list";
              range "800..899";
            }
            type uint16 {
              tailf:info
                "<900-999>;;IPX extended access list";
              range "900..999";
            }
            type uint16 {
              tailf:info
                "<1000-1099>;;IPX SAP access list";
              range "1000..1099";
            }
            type uint16 {
              tailf:info
                "<1100-1199>;;Extended 48-bit MAC address access list";
              range "1100..1199";
            }
            type uint16 {
              tailf:info
                "<1200-1299>;;IPX summary address access list";
              range "1200..1299";
            }
            type uint16 {
              tailf:info
                "<1300-1999>;;IP standard access list (expanded range)";
              range "1300..1999";
            }
            type uint16 {
              tailf:info
                "<2000-2699>;;IP extended access list (expanded range)";
              range "2000..2699";
            }
            type uint16 {
              tailf:info
                "<2700-2799>;;MPLS access list";
              range "2700..2799";
            }
          }
        }
        list rule {
          tailf:cli-drop-node-name;
          tailf:cli-suppress-mode;
          tailf:cli-delete-when-empty;
          tailf:cli-compact-syntax;
          tailf:cli-show-long-obu-diffs;
          ordered-by user;
          key "rule";
          leaf rule {
            tailf:cli-multi-word-key;
            type string {
              tailf:info
                "<RULE>;;deny <options> | permit <options> | remark <comment>";
              pattern '(permit.*)|(deny.*)|(remark.*)|(dynamic.*)';
            }
          }
          leaf seq {
            tailf:cli-drop-node-name;
            tailf:cli-prefix-key;
            type uint32 {
              tailf:info
                "<1-2147483647>;;Sequence Number [with ip access-list persistent]";
              range "1..2147483647";
            }
          }
        }
      }
      leaf dynamic-extended {
        tailf:info
          "Extend the dynamic ACL absolute timer";
        tailf:cli-full-command;
        type empty;
      }
    }
    container arp {
      tailf:ncs-device-type "cli-ned";
      tailf:display-when "not(../../ncs:module) or ../../ncs:module[ncs:name='tailf-ned-cisco-ios']";
      tailf:info
        "Set a static ARP entry";
      uses arp-grouping;
      list vrf {
        tailf:info
          "Configure static ARP for a VPN Routing/Forwarding instance";
        tailf:cli-suppress-mode;
        tailf:cli-delete-when-empty;
        tailf:cli-compact-syntax;
        tailf:cli-incomplete-command;
        key "name";
        leaf name {
          tailf:cli-diff-dependency "../../../ip/vrf" {
            tailf:xpath-root 3;
          }
          tailf:cli-diff-dependency "../../../vrf/definition" {
            tailf:xpath-root 3;
          }
          type string {
            tailf:info
              "WORD;;VPN Routing/Forwarding instance name";
          }
        }
        uses arp-grouping;
      }
      list access-list {
        tailf:info
          "Named access-list";
        tailf:cli-mode-name "config-arp-nacl";
        tailf:cli-full-command;
        key "name";
        leaf name {
          type string {
            tailf:info
              "WORD;;access-list name";
          }
        }
        list access-list-rule {
          tailf:cli-suppress-mode;
          tailf:cli-delete-when-empty;
          tailf:cli-drop-node-name;
          tailf:cli-compact-syntax;
          tailf:cli-show-long-obu-diffs;
          tailf:cli-case-sensitive;
          ordered-by user;
          key "rule";
          leaf rule {
            tailf:cli-drop-node-name;
            tailf:cli-multi-word-key;
            type string {
              tailf:info
                "deny;;Specify packets to reject
                 permit;;Specify packets to forwards";
              pattern '(deny .*)|(permit .*)';
            }
          }
        }
      }
    }
    list virtual-service {
      tailf:ncs-device-type "cli-ned";
      tailf:display-when "not(../ncs:module) or ../ncs:module[ncs:name='tailf-ned-cisco-ios']";
      tailf:info
        "Configure virtual service";
      tailf:cli-mode-name "config-virt-serv";
      tailf:cli-explicit-exit;
      tailf:cli-recursive-delete;
      tailf:cli-diff-dependency "../interface/VirtualPortGroup" {
        tailf:xpath-root 3;
      }
      key "name";
      leaf name {
        type string {
          tailf:info
            "WORD;;Virtual service name (up to 63 characters)";
        }
      }
      leaf description {
        tailf:info
          "Virtual service description";
        tailf:cli-multi-value;
        tailf:cli-preformatted;
        tailf:cli-full-command;
        type string {
          tailf:info
            "LINE;;Description of this virtual service (up to 191 characters)";
          length "0..191";
        }
      }
      container ip {
        tailf:info
          "Share IP address with a host interface";
        container shared {
          tailf:info
            "Share IP address with a host interface";
          container host-interface {
            tailf:info
              "Host interface to share IP address with";
            leaf GigabitEthernet {
              tailf:info
                "GigabitEthernet IEEE 802.3z";
              tailf:cli-allow-join-with-value {
                tailf:cli-display-joined;
              }
              tailf:non-strict-leafref {
                path "../../../../../interface/GigabitEthernet/name";
              }
              type string {
                tailf:info
                  "WORD;;GigabitEthernet interface id";
                pattern '[0-9]+.*';
              }
            }
          }
        }
      }
      leaf profile {
        tailf:info
          "Specify the resource profile for virtual service";
        tailf:cli-remove-before-change;
        tailf:cli-full-command;
        type enumeration {
          enum "ISR-WAAS-1300" {
            tailf:info
              "ISR-WAAS profile for 1300 TCP connections";
          }
          enum "ISR-WAAS-750" {
            tailf:info
              "ISR-WAAS profile for 750 TCP connections";
          }
          enum "ISR-WAAS-2500" {
            tailf:info
              "ISR-WAAS profile for 2500 TCP connections";
          }
          enum "high" {
            tailf:info
              "CSR UTD IPS/IDS HIGH profile";
          }
          enum "low" {
            tailf:info
              "CSR UTD IPS/IDS LOW profile";
          }
          enum "medium" {
            tailf:info
              "CSR UTD IPS/IDS MEDIUM profile";
          }
          enum "urlf-low" {
            tailf:info
              "CSR UTD URL Filtering LOW profile";
          }
        }
      }
      container vnic {
        tailf:info
          "Guest vnic configuration";
        container gateway {
          tailf:info
            "Gateway interface to connect to the guest vnic";
          list VirtualPortGroup {
            tailf:info
              "Virtual Port Group";
            tailf:cli-allow-join-with-key {
              tailf:cli-display-joined;
            }
            tailf:cli-mode-name "config-virt-serv-vnic";
            tailf:cli-suppress-key-abbreviation;
            key "name";
            leaf name {
              tailf:non-strict-leafref {
                path "../../../../../interface/VirtualPortGroup/name";
              }
              type uint8 {
                tailf:info
                  "<0-31>;;VirtualPortGroup interface number";
              }
            }
            container guest {
              tailf:info
                "Configure guest vnic address";
              container ip {
                tailf:info
                  "Guest vnic IP address";
                leaf address {
                  tailf:info
                    "Set the IP address of virtual interface on guest";
                  type inet:ipv4-address {
                    tailf:info
                      "A.B.C.D;;IP address";
                  }
                }
              }
            }
          }
        }
      }
      leaf activate {
        tailf:info
          "Activate configured virtual service";
        tailf:cli-diff-dependency "../profile" {
          tailf:xpath-root 3;
        }
        tailf:cli-diff-dependency "../vnic" {
          tailf:xpath-root 3;
        }
        type empty;
      }
    }
    list route-map {
      tailf:ncs-device-type "cli-ned";
      tailf:display-when "not(../ncs:module) or ../ncs:module[ncs:name='tailf-ned-cisco-ios']";
      tailf:info
        "Route map tag";
      tailf:cli-mode-name "config-route-map";
      tailf:cli-compact-syntax;
      tailf:cli-full-command;
      tailf:cli-diff-dependency "../ip/community-list" {
        tailf:xpath-root 3;
      }
      tailf:cli-diff-dependency "../ip/extcommunity-list" {
        tailf:xpath-root 3;
      }
      key "name sequence";
      leaf name {
        type string {
          tailf:info
            "WORD;;Route map tag";
        }
      }
      leaf sequence {
        tailf:cli-drop-node-name;
        type uint16 {
          tailf:info
            "<0-65535>;;Sequence to insert to/delete from existing route-map entry";
          range "0..65535";
        }
      }
      leaf operation {
        tailf:cli-drop-node-name;
        tailf:cli-prefix-key {
          tailf:cli-before-key 2;
        }
        type enumeration {
          enum "deny" {
            tailf:code-name "op_deny";
            tailf:info
              "Route map denies set operations";
          }
          enum "permit" {
            tailf:code-name "op_internet";
            tailf:info
              "Route map permits set operations";
          }
        }
      }
      leaf description {
        tailf:info
          "Route-map comment";
        tailf:cli-multi-value;
        tailf:cli-preformatted;
        tailf:cli-full-command;
        type string {
          tailf:info
            "LINE;;Comment up to 100 characters";
          length "0..100";
        }
      }
      container match {
        tailf:info
          "Match values from routing table";
        leaf-list as-path {
          tailf:info
            "Match BGP AS path list";
          tailf:cli-flat-list-syntax;
          ordered-by user;
          type string {
            tailf:info
              "WORD;;Access-list number or name";
          }
        }
        container ip {
          tailf:info
            "IP specific information";
          container address {
            tailf:info
              "Match address of route or match packet";
            leaf-list access-list {
              tailf:cli-drop-node-name;
              tailf:cli-flat-list-syntax;
              tailf:cli-disallow-value "prefix-list";
              ordered-by user;
              type exp-ip-acl-type;
            }
            leaf-list prefix-list {
              tailf:info
                "Match entries of prefix-lists";
              tailf:cli-flat-list-syntax;
              tailf:non-strict-leafref {
                path "../../../../../ip/prefix-list/prefixes/name";
              }
              ordered-by user;
              type string {
                tailf:info
                  "WORD;;IP prefix-list name";
              }
            }
          }
          container next-hop {
            tailf:info
              "Match next-hop address of route";
            leaf-list access-list {
              tailf:cli-drop-node-name;
              tailf:cli-flat-list-syntax;
              tailf:cli-disallow-value "prefix-list";
              ordered-by user;
              type std-ip-acl-type;
            }
            leaf-list prefix-list {
              tailf:info
                "Match entries of prefix-lists";
              tailf:cli-flat-list-syntax;
              tailf:non-strict-leafref {
                path "../../../../../ip/prefix-list/prefixes/name";
              }
              ordered-by user;
              type string {
                tailf:info
                  "WORD;;IP prefix-list name";
              }
            }
          }
          container route-source {
            tailf:info
              "Match advertising source address of route";
            leaf-list access-list {
              tailf:cli-drop-node-name;
              tailf:cli-flat-list-syntax;
              tailf:cli-disallow-value "prefix-list";
              ordered-by user;
              type std-ip-acl-type;
            }
            leaf-list prefix-list {
              tailf:info
                "Match entries of prefix-lists";
              tailf:cli-flat-list-syntax;
              tailf:non-strict-leafref {
                path "../../../../../ip/prefix-list/prefixes/name";
              }
              ordered-by user;
              type string {
                tailf:info
                  "WORD;;IP prefix-list name";
              }
            }
          }
        }
        container ipv6 {
          tailf:info
            "IPv6 specific information";
          container address {
            tailf:info
              "Match address of route";
            leaf access-list {
              tailf:cli-drop-node-name;
              tailf:cli-disallow-value "prefix-list";
              tailf:cli-remove-before-change;
              tailf:cli-full-command;
              tailf:cli-diff-dependency "../prefix-list" {
                tailf:xpath-root 3;
                tailf:cli-trigger-on-set;
              }
              type string {
                tailf:info
                  "WORD;;IPv6 access-list name";
              }
            }
            leaf prefix-list {
              tailf:info
                "IPv6 prefix-list";
              tailf:cli-remove-before-change;
              tailf:cli-full-command;
              tailf:cli-diff-dependency "../access-list" {
                tailf:xpath-root 3;
                tailf:cli-trigger-on-set;
              }
              tailf:non-strict-leafref {
                path "../../../../../ipv6/prefix-list/prefixes/name";
              }
              type string {
                tailf:info
                  "WORD;;Name of a IPv6 prefix list";
              }
            }
          }
          container next-hop {
            tailf:info
              "Match next-hop address of route";
            leaf access-list {
              tailf:cli-drop-node-name;
              tailf:cli-disallow-value "prefix-list";
              type string {
                tailf:info
                  "WORD;;IPv6 access-list name";
              }
            }
            leaf prefix-list {
              tailf:info
                "IPv6 prefix-list";
              tailf:non-strict-leafref {
                path "../../../../../ipv6/prefix-list/prefixes/name";
              }
              type string {
                tailf:info
                  "WORD;;Name of a IPv6 prefix list";
              }
            }
          }
          container route-source {
            tailf:info
              "Match advertising source address of route";
            leaf access-list {
              tailf:cli-drop-node-name;
              tailf:cli-disallow-value "prefix-list";
              type string {
                tailf:info
                  "WORD;;IPv6 access-list name";
              }
            }
            leaf prefix-list {
              tailf:info
                "IPv6 prefix-list";
              tailf:non-strict-leafref {
                path "../../../../../ipv6/prefix-list/prefixes/name";
              }
              type string {
                tailf:info
                  "WORD;;Name of a IPv6 prefix list";
              }
            }
          }
        }
        leaf-list community {
          tailf:info
            "Match BGP community list";
          tailf:cli-flat-list-syntax;
          ordered-by user;
          type string {
            tailf:info
              "WORD;;Community-list number or name";
          }
        }
        leaf-list extcommunity {
          tailf:info
            "Match BGP/VPN extended community list";
          tailf:cli-flat-list-syntax;
          ordered-by user;
          type string {
            tailf:info
              "WORD;;Community-list number or name";
          }
        }
        leaf-list tag {
          tailf:info
            "Match tag of route";
          tailf:cli-flat-list-syntax;
          ordered-by user;
          type uint32 {
            tailf:info
              "<0-4294967295>;;Tag value";
          }
        }
        container clns {
          tailf:info
            "CLNS information";
          leaf-list address {
            tailf:info
              "Match address of route or match packet";
            tailf:cli-flat-list-syntax;
            type string {
              tailf:info
                "WORD;;OSI filter set";
            }
          }
        }
        leaf-list interface {
          tailf:info
            "Match first hop interface of route";
          tailf:cli-flat-list-syntax;
          ordered-by user;
          type string {
            tailf:info
              "WORD;;Interface name";
          }
        }
        leaf-list source-protocol {
          tailf:info
            "Match source-protocol of route";
          tailf:cli-flat-list-syntax;
          ordered-by user;
          type union {
            type enumeration {
              enum "bgp" {
                tailf:info
                  "Border Gateway Protocol (BGP)";
              }
              enum "connected" {
                tailf:info
                  "Connected";
              }
              enum "eigrp" {
                tailf:info
                  "Enhanced Interior Gateway Routing Protocol (EIGRP)";
              }
              enum "isis" {
                tailf:info
                  "ISO IS-IS";
              }
              enum "lisp" {
                tailf:info
                  "Locator ID Separation Protocol (LISP)";
              }
              enum "mobile" {
                tailf:info
                  "Mobile routes";
              }
              enum "ospf" {
                tailf:info
                  "Open Shortest Path First (OSPF)";
              }
              enum "ospfv3" {
                tailf:info
                  "OSPFv3";
              }
              enum "rip" {
                tailf:info
                  "Routing Information Protocol (RIP)";
              }
              enum "static" {
                tailf:info
                  "Static routes";
              }
            }
            type string {
              tailf:info
                "WORD;;Router id, e.g. AS number, process id etc.";
            }
          }
        }
        list route-type {
          tailf:info
            "Match route-type of route";
          tailf:cli-suppress-mode;
          tailf:cli-delete-when-empty;
          tailf:cli-show-long-obu-diffs;
          ordered-by user;
          key "tag";
          leaf tag {
            tailf:cli-multi-word-key;
            type string {
              tailf:info
                "WORD;external|internal|level-1|level-2|local|nssa-external|type-1|type-2";
            }
          }
        }
        leaf-list local-preference {
          tailf:info
            "Local preference for route";
          tailf:cli-flat-list-syntax;
          ordered-by user;
          type uint32 {
            tailf:info
              "<0-4294967295>;;Local preference value";
          }
        }
      }
      container set {
        tailf:info
          "Set values in destination routing protocol";
        leaf global {
          tailf:info
            "Set to global routing table";
          tailf:cli-full-command;
          type empty;
        }
        container as-path {
          tailf:info
            "Prepend string for a BGP AS-path attribute";
          container prepend {
            tailf:info
              "Prepend to the as-path";
            leaf as-list {
              tailf:cli-drop-node-name;
              tailf:cli-multi-value;
              type string {
                tailf:info
                  "<1-4294967295>|<1-65535>[.<0-65535>];;AS number";
                pattern '(([0-9]+\.)?([0-9]+) )*(([0-9]+\.)?([0-9]+))';
              }
            }
            leaf last-as {
              tailf:info
                "Prepend last AS to the as-path";
              tailf:cli-full-command;
              type uint8 {
                tailf:info
                  "<1..10>;;number of last-AS prepends";
                range "1..10";
              }
            }
          }
          container tag {
            tailf:info
              "Set the tag as an AS-path attribute";
            tailf:cli-full-command;
            presence "true";
          }
        }
        container comm-list {
          tailf:info
            "set BGP community list (for deletion)";
          tailf:cli-compact-syntax;
          tailf:cli-sequence-commands {
            tailf:cli-reset-siblings;
          }
          leaf name {
            tailf:cli-drop-node-name;
            tailf:cli-incomplete-command;
            type union {
              type uint16 {
                tailf:info
                  "<1-99>;;Community-list number (standard)";
                range "1..99";
              }
              type uint16 {
                tailf:info
                  "<100-500>;;Community-list number (expanded)";
                range "100..500";
              }
              type string {
                tailf:info
                  "WORD;;Community-list name";
              }
            }
          }
          leaf delete {
            tailf:info
              "Delete matching communities";
            type empty;
          }
        }
        container community {
          tailf:info
            "BGP community attribute";
          tailf:cli-compact-syntax;
          tailf:cli-sequence-commands {
            tailf:cli-reset-siblings;
          }
          choice set-community-choice {
            leaf none {
              tailf:info
                "No community attribute";
              tailf:cli-full-command;
              type empty;
            }
            leaf-list community-number {
              tailf:cli-drop-node-name;
              tailf:cli-flat-list-syntax;
              ordered-by user;
              type union {
                type uint32 {
                  tailf:info
                    "<1-4294967295>;;community number";
                  range "1..4294967295";
                }
                type string {
                  tailf:info
                    "aa:nn;;community number in aa:nn format";
                  pattern '[0-9]+:[0-9]+';
                }
                type enumeration {
                  enum "additive" {
                    tailf:info
                      "Add to the existing community";
                  }
                  enum "internet" {
                    tailf:info
                      "Internet (well-known community)";
                  }
                  enum "local-AS" {
                    tailf:info
                      "Do not send outside local AS (well-known community)";
                  }
                  enum "no-advertise" {
                    tailf:info
                      "Do not advertise to any peer (well-known community)";
                  }
                  enum "no-export" {
                    tailf:info
                      "Do not export to next AS (well-known community)";
                  }
                }
              }
            }
          }
        }
        container extcomm-list {
          tailf:info
            "Set BGP/VPN extended community list (for deletion)";
          tailf:cli-compact-syntax;
          tailf:cli-sequence-commands {
            tailf:cli-reset-siblings;
          }
          leaf name {
            tailf:cli-drop-node-name;
            tailf:cli-incomplete-command;
            type union {
              type uint16 {
                tailf:info
                  "<1-99>;;Extended community-list number (standard)";
                range "1..99";
              }
              type uint16 {
                tailf:info
                  "<100-500>;;Extended community-list number (expanded)";
                range "100..500";
              }
              type string {
                tailf:info
                  "WORD;;extcommunity-list name";
              }
            }
          }
          leaf delete {
            tailf:info
              "Delete matching extended communities";
            type empty;
          }
        }
        container extcommunity {
          tailf:info
            "BGP extended community attribute";
          tailf:cli-compact-syntax;
          leaf-list rt {
            tailf:info
              "Route Target extended community";
            tailf:cli-flat-list-syntax;
            ordered-by user;
            type union {
              type asn-ip-type {
                tailf:info
                  "ASN:nn or IP-address:nn;;VPN extended community";
              }
              type enumeration {
                enum "range" {
                  tailf:info
                    "Specify a range of extended community";
                }
                enum "additive" {
                  tailf:info
                    "Add to the existing community";
                }
              }
            }
          }
        }
        container ip {
          tailf:info
            "IP specific information";
          container next-hop {
            tailf:info
              "Next hop address";
            leaf self {
              tailf:info
                "Use self address (for BGP only)";
              type empty;
            }
            container verify-availability-conf {
              tailf:cli-drop-node-name;
              list verify-availability {
                tailf:info
                  "Verify if nexthop is reachable";
                tailf:cli-suppress-mode;
                tailf:cli-delete-when-empty;
                tailf:cli-compact-syntax;
                tailf:cli-sequence-commands;
                tailf:cli-incomplete-command;
                key "address";
                leaf address {
                  type inet:ipv4-address {
                    tailf:info
                      "A.B.C.D;;IP address of next hop";
                  }
                }
                leaf sequence {
                  tailf:cli-drop-node-name;
                  tailf:cli-incomplete-command;
                  type uint16 {
                    tailf:info
                      "<1-65535>;;Sequence to insert into next-hop list";
                    range "1..65535";
                  }
                }
                leaf track {
                  tailf:info
                    "set the next hop depending on the state of a tracked object";
                  type uint16 {
                    tailf:info
                      "<1-1000>;;tracked object number";
                    range "1..1000";
                  }
                }
              }
            }
            leaf peer-address {
              tailf:info
                "Use peer address (for BGP only)";
              tailf:cli-full-command;
              tailf:cli-diff-dependency "../address" {
                tailf:xpath-root 3;
                tailf:cli-trigger-on-set;
              }
              type empty;
            }
            leaf-list address {
              tailf:cli-drop-node-name;
              tailf:cli-flat-list-syntax;
              tailf:cli-full-command;
              tailf:cli-diff-dependency "../peer-address" {
                tailf:xpath-root 3;
                tailf:cli-trigger-on-set;
              }
              ordered-by user;
              type inet:ipv4-address {
                tailf:info
                  "A.B.C.D;;IP address of next hop";
              }
            }
            leaf verify-availability {
              tailf:info
                "Verify if nexthop is reachable";
              tailf:cli-full-command;
              type empty;
            }
            container dynamic {
              tailf:info
                "application dynamically sets next hop";
              leaf dhcp {
                tailf:info
                  "DHCP learned next hop";
                type empty;
              }
            }
            container recursive {
              tailf:info
                "Recursive next-hop";
              tailf:cli-compact-syntax;
              tailf:cli-sequence-commands {
                tailf:cli-reset-siblings;
              }
              choice global-or-vrf-choice {
                leaf global {
                  tailf:info
                    "global routing table";
                  tailf:cli-optional-in-sequence;
                  tailf:cli-incomplete-command;
                  type empty;
                }
                leaf vrf {
                  tailf:info
                    "VRF name";
                  tailf:cli-optional-in-sequence;
                  tailf:cli-incomplete-command;
                  type string {
                    tailf:info
                      "WORD;;VRF name";
                  }
                }
              }
              leaf address {
                tailf:cli-drop-node-name;
                tailf:cli-full-command;
                type inet:ipv4-address {
                  tailf:info
                    "A.B.C.D;;IP address of recursive next hop";
                }
              }
            }
            container encapsulate {
              tailf:info
                "Encapsulation profile for VPN nexthop";
              leaf l3vpn {
                tailf:info
                  "L3VPN";
                type string {
                  tailf:info
                    "WORD;;Encapsulation profile name";
                }
              }
            }
          }
          container df {
            tailf:info
              "Set DF bit";
            tailf:cli-delete-when-empty;
            presence "true";
            leaf bit {
              tailf:cli-drop-node-name;
              type uint8 {
                tailf:info
                  "<0-1>;;DF bit";
                range "0..1";
              }
            }
          }
          leaf precedence {
            tailf:info
              "Set precedence field";
            tailf:cli-full-command;
            type precedence-type;
          }
          leaf qos-group {
            tailf:info
              "Set QOS Group ID";
            type uint8 {
              tailf:info
                "<0-99>;;QOS Group ID";
              range "0..99";
            }
          }
        }
        container ipv6 {
          tailf:info
            "IPv6 specific information";
          container next-hop {
            tailf:info
              "IPv6 Next hop";
            choice next-hop-choice {
              leaf-list address {
                tailf:cli-drop-node-name;
                tailf:cli-flat-list-syntax;
                type inet:ipv6-address {
                  tailf:info
                    "X:X:X:X::X;;Next hop address";
                }
              }
              leaf peer-address {
                tailf:info
                  "Use peer address (for BGP only)";
                tailf:cli-full-command;
                type empty;
              }
            }
          }
        }
        container local-preference {
          tailf:info
            "BGP local preference path attribute";
          tailf:cli-delete-when-empty;
          presence "true";
          leaf value {
            tailf:cli-drop-node-name;
            type uint32 {
              tailf:info
                "<0-4294967295>;;Preference value";
            }
          }
        }
        leaf-list metric {
          tailf:info
            "Metric value for destination routing protocol";
          tailf:cli-flat-list-syntax;
          tailf:cli-replace-all;
          ordered-by user;
          type string {
            tailf:info
              "+/-<metric>;;Add or subtract metric
               <0-4294967295>;;Metric value or Bandwidth in Kbits per second";
            pattern '[+-]?[0-9]*';
          }
        }
        leaf metric-type {
          tailf:info
            "Type of metric for destination routing protocol";
          type enumeration {
            enum "external" {
              tailf:info
                "IS-IS external metric";
            }
            enum "internal" {
              tailf:info
                "IS-IS internal metric or Use IGP metric as the MED for BGP";
            }
            enum "type-1" {
              tailf:info
                "OSPF external type 1 metric";
            }
            enum "type-2" {
              tailf:info
                "OSPF external type 2 metric";
            }
          }
        }
        leaf weight {
          tailf:info
            "BGP weight for routing table";
          type uint32 {
            tailf:info
              "<0-65535>;;Weight value";
            range "0..65535";
          }
        }
        container origin {
          tailf:info
            "BGP origin code";
          choice origin-choice {
            leaf origin-value {
              tailf:cli-drop-node-name;
              type enumeration {
                enum "igp" {
                  tailf:info
                    "local IGP";
                }
                enum "incomplete" {
                  tailf:info
                    "unknown heritage";
                }
              }
            }
            leaf egp {
              tailf:info
                "remote EGP";
              type uint32 {
                tailf:info
                  "<0-65535>;;remote AS";
                range "0..65535";
              }
            }
          }
        }
        leaf vrf {
          tailf:info
            "Define VRF name";
          tailf:cli-diff-dependency "../../../ip/vrf" {
            tailf:xpath-root 3;
          }
          tailf:cli-diff-dependency "../../../vrf/definition" {
            tailf:xpath-root 3;
          }
          type string {
            tailf:info
              "WORD;;VPN Routing/Forwarding instance name";
          }
        }
        leaf tag {
          tailf:info
            "Tag value for destination routing protocol";
          type uint32 {
            tailf:info
              "<0-4294967295>;;Tag value";
          }
        }
        leaf mpls-label {
          tailf:info
            "Set MPLS label for prefix";
          type empty;
        }
        leaf-list interface {
          tailf:info
            "Output interface";
          tailf:cli-flat-list-syntax;
          ordered-by user;
          type string {
            tailf:info
              "WORD;;Interface name";
          }
        }
        container default {
          tailf:info
            "Set default information";
          container interface {
            tailf:info
              "Default output interface";
            tailf:cli-compact-syntax;
            uses interface-name-grouping;
          }
        }
      }
      container continue {
        tailf:info
          "Continue on a different entry within the route-map";
        tailf:cli-delete-when-empty;
        presence "true";
        leaf sequence-number {
          tailf:cli-drop-node-name;
          type uint16 {
            tailf:info
              "<0-65535>;;Route-map entry sequence number";
          }
        }
      }
    }
    container dialer {
      tailf:ncs-device-type "cli-ned";
      tailf:display-when "not(../../ncs:module) or ../../ncs:module[ncs:name='tailf-ned-cisco-ios']";
      tailf:info
        "Dialer commands";
      list watch-list {
        tailf:info
          "Dialer watch list";
        tailf:cli-suppress-mode;
        tailf:cli-delete-when-empty;
        key "id";
        leaf id {
          type uint16 {
            tailf:info
              "<1-255>;;Dialer watch group number";
            range "1..255";
          }
        }
        list ip {
          tailf:info
            "IP";
          tailf:cli-suppress-mode;
          tailf:cli-delete-when-empty;
          key "address";
          leaf address {
            type inet:ipv4-address {
              tailf:info
                "A.B.C.D;;Protocol specific address";
            }
          }
          leaf mask {
            tailf:cli-drop-node-name;
            tailf:cli-no-value-on-delete;
            type inet:ipv4-address {
              tailf:info
                "A.B.C.D;;IP subnet mask";
            }
          }
        }
        container delay {
          tailf:info
            "Dialer watch delay";
          container route-check {
            tailf:info
              "Interval for checking watched route";
            leaf initial {
              tailf:info
                "Delay for initial check of watched route after boot";
              type uint32 {
                tailf:info
                  "<1-2147483>;;Delay time in seconds";
              }
            }
          }
          leaf connect {
            tailf:info
              "Interval before dialing the secondary route";
            type uint32 {
              tailf:info
                "<1-2147483>;;Delay time in seconds";
              range "1..2147483";
            }
          }
          leaf disconnect {
            tailf:info
              "Interval before disconnecting the secondary route";
            type uint32 {
              tailf:info
                "<1-2147483>;;Delay time in seconds";
              range "1..2147483";
            }
          }
        }
      }
    }
    list dialer-list {
      tailf:ncs-device-type "cli-ned";
      tailf:display-when "not(../ncs:module) or ../ncs:module[ncs:name='tailf-ned-cisco-ios']";
      tailf:info
        "Create a dialer list entry";
      tailf:cli-suppress-mode;
      tailf:cli-delete-when-empty;
      tailf:cli-compact-syntax;
      key "id";
      leaf id {
        type uint16 {
          tailf:info
            "<1-128>;;Dialer group number";
        }
      }
      container protocol {
        tailf:info
          "Permit or Deny based on protocols";
        leaf ip {
          tailf:info
            "IP";
          type enumeration {
            enum "deny" {
              tailf:info
                "Deny specified protocol";
            }
            enum "list" {
              tailf:info
                "Add access list to dialer list";
            }
            enum "permit" {
              tailf:info
                "Permit specified protocol";
            }
          }
        }
      }
    }
    container authentication {
      tailf:ncs-device-type "cli-ned";
      tailf:display-when "not(../../ncs:module) or ../../ncs:module[ncs:name='tailf-ned-cisco-ios']";
      tailf:info
        "Auth Manager Global Configuration Commands";
      container mac-move {
        leaf permit {
          type empty;
        }
      }
    }
    container banner {
      tailf:ncs-device-type "cli-ned";
      tailf:display-when "not(../../ncs:module) or ../../ncs:module[ncs:name='tailf-ned-cisco-ios']";
      tailf:info
        "Define a login banner";
      leaf exec {
        tailf:info
          "Set EXEC process creation banner. ";
        tailf:cli-no-value-on-delete;
        type string {
          tailf:info
            "LINE;;Quoted string. Use \\r\\n for newline. delimeter ^ is added automatically.";
        }
      }
      leaf login {
        tailf:info
          "Set login banner.";
        tailf:cli-no-value-on-delete;
        type string {
          tailf:info
            "LINE;;Quoted string. Use \\r\\n for newline. delimeter ^ is added automatically.";
        }
      }
      leaf lcd {
        tailf:info
          "Set Message for LCD banner";
        tailf:cli-no-value-on-delete;
        type string {
          tailf:info
            "LINE;;Quoted string. Use \\r\\n for newline. delimeter ^ is added automatically.";
        }
      }
      leaf prompt-timeout {
        tailf:info
          "Set Message for login authentication timeout.";
        tailf:cli-no-value-on-delete;
        type string {
          tailf:info
            "LINE;;Quoted string. Use \\r\\n for newline. delimeter ^ is added automatically.";
        }
      }
      leaf motd {
        tailf:info
          "Set Message of the Day banner.";
        tailf:cli-no-value-on-delete;
        type string {
          tailf:info
            "LINE;;Quoted string. Use \\r\\n for newline. delimeter ^ is added automatically.";
        }
      }
    }
    list pseudowire-class {
      tailf:ncs-device-type "cli-ned";
      tailf:display-when "not(../ncs:module) or ../ncs:module[ncs:name='tailf-ned-cisco-ios']";
      tailf:info
        "Pseudowire-class configuration";
      tailf:cli-mode-name "config-pw-class";
      tailf:cli-full-command;
      key "name";
      leaf name {
        type string {
          tailf:info
            "WORD;;Pseudowire-class name";
        }
      }
      leaf encapsulation {
        tailf:info
          "Data encapsulation method";
        type enumeration {
          enum "l2tpv2" {
            tailf:info
              "Use L2TPv2 encapsulation";
          }
          enum "l2tpv3" {
            tailf:info
              "Use L2TPv3 encapsulation";
          }
          enum "mpls" {
            tailf:info
              "Use MPLS encapsulation";
          }
        }
      }
      leaf interworking {
        tailf:info
          "Interworking options for pseudowire";
        tailf:cli-full-command;
        type enumeration {
          enum "ethernet" {
            tailf:info
              "Ethernet interworking";
          }
          enum "ip" {
            tailf:info
              "IP interworking";
          }
          enum "vlan" {
            tailf:info
              "VLAN interworking";
          }
        }
      }
      leaf control-word {
        tailf:info
          "Include control-word in pseudowire packets";
        type empty;
      }
      container sequencing {
        tailf:info
          "Sequencing options for pseudowire";
        choice sequencing-choice {
          leaf both {
            tailf:info
              "Transmit and receive sequence numbers";
            type empty;
          }
          leaf receive {
            tailf:info
              "Receive sequence numbers";
            type empty;
          }
          container resync {
            tailf:info
              "Enable Rx sequencing out-of-order detection/recovery";
            presence "true";
          }
          leaf transmit {
            tailf:info
              "Transmit sequence numbers";
            type empty;
          }
        }
      }
      container status {
        tailf:info
          "Pseudowire status capabilities";
        container peer {
          tailf:info
            "peer status configuration";
          container topology {
            tailf:info
              "change status behaviour based on peer topology";
            leaf dual-homed {
              tailf:info
                "Our peer(s) are participating in a redundant solution with some form of redundancy protocol running between the peer routers";
              type empty;
            }
          }
        }
      }
      container protocol {
        tailf:info
          "Signaling protocol to use";
        choice protocol-choice {
          leaf none {
            tailf:info
              "No signaling, use manually configured sessions";
            type empty;
          }
          leaf l2tpv3 {
            tailf:info
              "Use L2TPv3 signaling";
            tailf:non-strict-leafref {
              path "../../../l2tp-class/l2tp-class-name";
            }
            type string {
              tailf:info
                "WORD;;l2tp-class name";
            }
          }
        }
      }
      container ip {
        tailf:info
          "Specify IP parameters";
        container local {
          tailf:info
            "Specify local information";
          container interface {
            tailf:info
              "Source interface for pseudowire";
            tailf:cli-compact-syntax;
            uses interface-name-grouping;
          }
        }
      }
    }
    container control-plane-host {
      tailf:ncs-device-type "cli-ned";
      tailf:display-when "not(../../ncs:module) or ../../ncs:module[ncs:name='tailf-ned-cisco-ios']";
      tailf:cli-drop-node-name;
      container control-plane {
        tailf:info
          "Configure control plane services";
        container host {
          tailf:info
            "Host traffic control-plane configuration";
          tailf:cli-add-mode;
          tailf:cli-mode-name "config-cp-host";
          presence "true";
          list management-interface {
            tailf:info
              "Configure interface for receiving network management traffic";
            tailf:cli-suppress-mode;
            tailf:cli-delete-when-empty;
            tailf:cli-incomplete-command;
            tailf:cli-diff-dependency "../../../../interface" {
              tailf:xpath-root 3;
            }
            key "interface";
            leaf interface {
              type string {
                tailf:info
                  "WORD;;Interface name";
              }
            }
            leaf-list allow {
              tailf:info
                "Allowed network management protocols on selected interface";
              tailf:cli-flat-list-syntax;
              type enumeration {
                enum "beep" {
                  tailf:info
                    "Beep Protocol";
                }
                enum "ftp" {
                  tailf:info
                    "File Transfer Protocol";
                }
                enum "http" {
                  tailf:info
                    "HTTP Protocol";
                }
                enum "https" {
                  tailf:info
                    "HTTPS Protocol";
                }
                enum "snmp" {
                  tailf:info
                    "Simple Network Management Protocol";
                }
                enum "ssh" {
                  tailf:info
                    "Secure Shell Protocol";
                }
                enum "telnet" {
                  tailf:info
                    "Telnet Protocol";
                }
                enum "tftp" {
                  tailf:info
                    "Trivial File Transfer Protocol";
                }
                enum "tl1" {
                  tailf:info
                    "Transaction Language Session Protocol";
                }
              }
            }
          }
        }
      }
    }
    container control-plane {
      tailf:ncs-device-type "cli-ned";
      tailf:display-when "not(../../ncs:module) or ../../ncs:module[ncs:name='tailf-ned-cisco-ios']";
      tailf:info
        "Configure control plane services";
      tailf:cli-add-mode;
      tailf:cli-mode-name "config-cp";
      presence "true";
      container service-policy {
        tailf:info
          "Configure QOS Service Policy";
        uses service-policy-grouping;
      }
    }
    container cops {
      tailf:ncs-device-type "cli-ned";
      tailf:display-when "not(../../ncs:module) or ../../ncs:module[ncs:name='tailf-ned-cisco-ios']";
      tailf:info
        "Common Open Policy Service (COPS)";
      container listener {
        tailf:info
          "Incoming connections from policy decision points (PDPs)";
        leaf access-list {
          tailf:info
            "Rules for PDPs connecting to local COPS listeners";
          type exp-ip-acl-type;
        }
      }
      container ip {
        tailf:info
          "IP parameters for COPS connections";
        leaf dscp {
          tailf:info
            "Differentiated Services Code Point marking for COPS messages";
          type dscp-type;
        }
      }
    }
    list connect {
      tailf:ncs-device-type "cli-ned";
      tailf:display-when "not(../ncs:module) or ../ncs:module[ncs:name='tailf-ned-cisco-ios']";
      tailf:info
        "cross-connect two interfaces";
      tailf:cli-mode-name "config-connection";
      tailf:cli-compact-syntax;
      tailf:cli-sequence-commands;
      key "interface1 interface2";
      leaf name {
        tailf:cli-drop-node-name;
        tailf:cli-prefix-key;
        type string {
          tailf:info
            "WORD;;Name for this connection";
        }
      }
      leaf interface1 {
        type string {
          tailf:info
            "WORD;;First interface name";
        }
      }
      leaf number1 {
        tailf:cli-drop-node-name;
        tailf:cli-prefix-key {
          tailf:cli-before-key 2;
        }
        tailf:cli-optional-in-sequence;
        type uint16 {
          tailf:info
            "<1-8184>;;Service Instance Identifier";
          range "1..8184";
        }
      }
      leaf interface2 {
        type string {
          tailf:info
            "WORD;;Second interface name";
        }
      }
      leaf number2 {
        tailf:cli-drop-node-name;
        tailf:cli-hide-in-submode;
        type uint16 {
          tailf:info
            "<1-8184>;;Service Instance Identifier";
          range "1..8184";
        }
      }
      container backup {
        tailf:cli-break-sequence-commands;
        tailf:info
          "Xconnect backup configuration commands";
        container peer {
          tailf:info
            "Backup pseudowire";
          tailf:cli-compact-syntax;
          tailf:cli-sequence-commands {
            tailf:cli-reset-siblings;
          }
          leaf peer-router-ip-addr {
            tailf:cli-drop-node-name;
            tailf:cli-incomplete-command;
            type inet:ipv4-address {
              tailf:info
                "A.B.C.D;;IP address of peer";
            }
          }
          leaf vcid {
            tailf:cli-drop-node-name;
            type uint32 {
              tailf:info
                "<1-4294967295>;;Peer VC ID value";
              range "1..4294967295";
            }
          }
          leaf pw-class {
            tailf:cli-optional-in-sequence;
            tailf:non-strict-leafref {
              path "../../../../pseudowire-class/name";
            }
            type string {
              tailf:info
                "Optional Pseudowire-class to use for backup pseudowire";
            }
          }
        }
      }
      uses xconnect-grouping;
    }
    list voice-port {
      tailf:ncs-device-type "cli-ned";
      tailf:display-when "not(../ncs:module) or ../ncs:module[ncs:name='tailf-ned-cisco-ios']";
      tailf:info
        "Configure a specific voice-port";
      tailf:cli-mode-name "config-voiceport";
      key "name";
      leaf name {
        type string {
          tailf:info
            "<0-0>;;Voice interface slot #";
        }
      }
      container timeouts {
        tailf:info
          "Configure voice timeout parameters";
        leaf interdigit {
          tailf:info
            "Interdigit Timeout duration in seconds";
          type uint8 {
            tailf:info
              "<0-120>;;seconds";
            range "0..120";
          }
        }
      }
      leaf shutdown {
        tailf:cli-full-command;
        type empty;
      }
      container busyout {
        tailf:info
          "Configure busyout trigger event & procedure";
        leaf action {
          tailf:cli-full-command;
          type string;
        }
        container monitor {
          tailf:info
            "The event of this interface triggers busyout";
          container action {
            tailf:info
              "busyout action when monitoring triggered";
            choice action-choice {
              leaf graceful {
                tailf:info
                  "graceful busyout when monitoring triggered";
                type empty;
              }
              leaf shutdown {
                tailf:info
                  "shutdown D channel when monitoring triggered";
                type empty;
              }
              container alarm {
                tailf:info
                  "Use alarm generation";
                leaf blue {
                  tailf:info
                    "Use blue alarm";
                  type empty;
                }
              }
            }
          }
          list state {
            tailf:cli-drop-node-name;
            tailf:cli-suppress-mode;
            tailf:cli-delete-when-empty;
            tailf:cli-compact-syntax;
            key "name";
            leaf name {
              type string {
                tailf:info
                  "WORD;;Interface name";
              }
            }
            leaf in-service {
              tailf:info
                "Inverted logic trigger by interface back up or in service";
              type empty;
            }
          }
        }
      }
    }
    container dial-peer {
      tailf:ncs-device-type "cli-ned";
      tailf:display-when "not(../../ncs:module) or ../../ncs:module[ncs:name='tailf-ned-cisco-ios']";
      tailf:info
        "Dial Map (Peer) configuration commands";
      list voice {
        tailf:info
          "Voice type";
        tailf:cli-mode-name "config-dial-peer";
        tailf:cli-incomplete-command;
        tailf:cli-sequence-commands;
        key "id";
        leaf id {
          type uint32 {
            tailf:info
              "<1-2147483647>;;Voice dial-peer tag";
            range "1..2147483647";
          }
        }
        leaf peer {
          tailf:cli-drop-node-name;
          tailf:cli-hide-in-submode;
          type enumeration {
            enum "mmoip" {
              tailf:info
                "Multi Media Over IP";
            }
            enum "pots" {
              tailf:info
                "Telephony";
            }
            enum "voatm" {
              tailf:info
                "Voice over ATM";
            }
            enum "vofr" {
              tailf:info
                "Voice over Frame Relay";
            }
            enum "voip" {
              tailf:info
                "Voice over IP";
            }
          }
        }
        leaf answer-address {
          tailf:cli-break-sequence-commands;
          tailf:info
            "The Call Destination Number";
          tailf:cli-full-command;
          type string {
            tailf:info
              "WORD;;A string of digits including wild cards";
          }
        }
        leaf trunkgroup {
          tailf:info
            "trunk groups associated with this peer";
          tailf:non-strict-leafref {
            path "../../../trunk/group/name";
          }
          type string {
            tailf:info
              "WORD;;trunkgroup id";
          }
        }
        leaf description {
          tailf:info
            "Dialpeer specific description";
          tailf:cli-multi-value;
          tailf:cli-preformatted;
          tailf:cli-full-command;
          type string {
            tailf:info
              "LINE;;Up to 64 characters describing this dialpeer";
            length "1..64";
          }
        }
        container translation-profile {
          tailf:info
            "Translation profile";
          leaf incoming {
            tailf:info
              "Translation Profile for incoming call leg";
            tailf:cli-full-command;
            type string {
              tailf:info
                "WORD;;Profile name";
            }
          }
          leaf outgoing {
            tailf:info
              "Translation Profile for outgoing call leg";
            tailf:cli-full-command;
            type string {
              tailf:info
                "WORD;;Profile name";
            }
          }
        }
        leaf huntstop {
          tailf:info
            "Stop hunting on Dial-Peers";
          tailf:cli-full-command;
          type empty;
        }
        leaf max-conn {
          tailf:info
            "Sets the maximum connections per peer, negation sets to unlimited";
          tailf:cli-full-command;
          type uint32 {
            tailf:info
              "<1-2147483647>;;Maximum connections, negation sets to unlimited";
          }
        }
        leaf destination-pattern {
          tailf:info
            "A full E.164 telephone number prefix";
          tailf:cli-full-command;
          type string {
            tailf:info
              "WORD;;A sequence of digits - representing the prefix or full telephone number";
          }
        }
        container modem {
          tailf:info
            "Modem commands through this peer";
          container passthrough {
            tailf:info
              "Pass modem traffic via clear channel";
            choice passthrough-choice {
              leaf system {
                tailf:info
                  "Use global configuration";
                tailf:cli-boolean-no;
                tailf:cli-full-command;
                type boolean;
                default "true";
              }
              container nse {
                tailf:info
                  "Use Named Signaling Events (NSE)";
                tailf:cli-compact-syntax;
                leaf payload-type {
                  tailf:info
                    "Configure NSE payload type";
                  type uint32 {
                    tailf:info
                      "<98-117>;;Payload type value";
                  }
                }
                leaf codec {
                  tailf:info
                    "Codec selections for upspeed";
                  type enumeration {
                    enum "g711ulaw" {
                      tailf:info
                        "G.711 u Law 64000 bp";
                    }
                    enum "g711alaw" {
                      tailf:info
                        "G.711 A Law 64000 bps";
                    }
                  }
                }
                leaf redundancy {
                  tailf:info
                    "Use Packet Redundancy (RFC2198) for modem traffic";
                  type empty;
                }
              }
            }
          }
        }
        container session {
          tailf:info
            "The session [ target | protocol | transport ] for this peer";
          leaf protocol {
            tailf:info
              "The session protocol to be used in getting to this peer";
            type enumeration {
              enum "aal2-trunk";
              enum "cisco" {
                tailf:info
                  "Cisco Session Protocol";
              }
              enum "sipv2" {
                tailf:info
                  "IETF Session Initiation Protocol";
              }
              enum "smtp";
              enum "multicast" {
                tailf:info
                  "Multicast Session Protocol(voice conferencing)";
              }
            }
          }
          leaf target {
            tailf:info
              "The session target for this peer";
            tailf:cli-multi-value;
            tailf:cli-full-command;
            type string {
              tailf:info
                "WORD;;A string specifying the session target";
            }
          }
        }
        container dtmf-relay {
          tailf:info
            "Transport DTMF digits across IP link. Enter DTMF Relay options in order of preference.";
          tailf:cli-compact-syntax;
          tailf:cli-reset-container;
          leaf cisco-rtp {
            tailf:info
              "Cisco Proprietary RTP";
            type empty;
          }
          leaf h245-alphanumeric {
            tailf:info
              "DTMF Relay via H245 Alphanumeric IE";
            type empty;
          }
          leaf h245-signal {
            tailf:info
              "DTMF Relay via H245 Signal IE";
            type empty;
          }
          leaf rtp-nte {
            tailf:info
              "RTP Named Telephone Event RFC 2833";
            type empty;
          }
        }
        container incoming {
          tailf:info
            "Incoming called number";
          leaf called-number {
            tailf:info
              "An incoming called number pattern";
            type string {
              tailf:info
                "WORD;;A sequence of digits representing a phone number prefix";
            }
          }
        }
        leaf direct-inward-dial {
          type empty;
        }
        leaf forward-digits {
          type union {
            type uint8;
            type enumeration {
              enum "all";
              enum "extra";
            }
          }
        }
        container codec {
          tailf:info
            "The codec rate to be attempted in getting to this peer";
          tailf:cli-compact-syntax;
          tailf:cli-sequence-commands {
            tailf:cli-reset-siblings;
          }
          leaf name {
            tailf:cli-drop-node-name;
            type string {
              tailf:info
                "WORD;;Codec name";
            }
          }
          leaf bytes {
            tailf:info
              "Specify number of voice data bytes per frame";
            tailf:cli-break-sequence-commands;
            type uint32;
          }
          leaf mode {
            tailf:info
              "Specify the value of the mode";
            type uint32 {
              tailf:info
                "20 = 15.2 kbps, 30 = 13.33 kbps";
            }
          }
        }
        container fax {
          tailf:info
            "Configure fax";
          container protocol {
            tailf:info
              "The fax protocol to be attempted in getting to this peer";
            choice protocol-option {
              leaf none {
                tailf:info
                  "No FAX protocol";
                type empty;
              }
              leaf cisco {
                tailf:info
                  "Use Cisco proprietary protocol";
                type empty;
              }
              leaf pass-through {
                tailf:info
                  "Use an audio codec for fax transport";
                type enumeration {
                  enum "g711ulaw" {
                    tailf:info
                      "G.711 u Law 64000 bps (for T1)";
                  }
                  enum "g711alaw" {
                    tailf:info
                      "G.711 A Law 64000 bps (for E1)";
                  }
                }
              }
            }
          }
        }
        container ip {
          tailf:info
            "Set ip packet options";
          container qos {
            tailf:info
              "Set ip QoS Parameters";
            list dscp {
              tailf:info
                "Specify ip DSCP";
              tailf:cli-compact-syntax;
              tailf:cli-suppress-mode;
              tailf:cli-delete-when-empty;
              tailf:cli-incomplete-command;
              key "name";
              leaf name {
                type string {
                  tailf:info
                    "WORD;;voice set";
                }
              }
              choice dscp-choice {
                leaf media {
                  tailf:info
                    "Apply DSCP to media payload packets";
                  type empty;
                }
                leaf signaling {
                  tailf:info
                    "Apply DSCP to signaling packets";
                  type empty;
                }
                leaf video {
                  tailf:info
                    "Apply DSCP to video packets";
                  type enumeration {
                    enum "rsvp-none" {
                      tailf:info
                        "Use this DSCP value if RSVP is not configured";
                    }
                    enum "rsvp-pass" {
                      tailf:info
                        "Use this DSCP value if RSVP reservation is successful";
                    }
                    enum "rsvp-fail" {
                      tailf:info
                        "Use this DSCP value if RSVP reservation fails";
                    }
                  }
                }
              }
            }
          }
        }
        leaf vad {
          tailf:info
            "Use VoiceActivityDetection as necessary option";
          tailf:cli-full-command;
          tailf:cli-boolean-no;
          type boolean;
          default "true";
        }
      }
      container outbound {
        tailf:info
          "Define the outbound options";
        container status-check {
          tailf:info
            "Enable or disable status checking";
          leaf pots {
            tailf:info
              "Telephony";
            tailf:cli-boolean-no;
            tailf:cli-full-command;
            type boolean;
            default "true";
          }
        }
      }
      container cor {
        container custom {
          tailf:cli-add-mode;
          presence "true";
          list name {
            tailf:cli-suppress-mode;
            tailf:cli-delete-when-empty;
            key "name";
            leaf name {
              type string;
            }
          }
        }
      }
    }
    leaf config-register {
      tailf:ncs-device-type "cli-ned";
      tailf:display-when "not(../../ncs:module) or ../../ncs:module[ncs:name='tailf-ned-cisco-ios']";
      tailf:info
        "Define the configuration register";
      type string {
        tailf:info
          "<0x0-0xFFFF>;;Config register number";
        pattern '[0-9xXa-fA-F].*';
      }
    }
    container network-clock-participate {
      tailf:ncs-device-type "cli-ned";
      tailf:display-when "not(../../ncs:module) or ../../ncs:module[ncs:name='tailf-ned-cisco-ios']";
      tailf:info
        "Participate in Network Clocking";
      container wic {
        tailf:info
          "WIC Module";
        list wic-enabled {
          tailf:cli-drop-node-name;
          tailf:cli-suppress-mode;
          tailf:cli-delete-when-empty;
          key "slot";
          leaf slot {
            type uint8 {
              tailf:info
                "<0-3>;;Slot Number (physical)";
              range "0..3";
            }
          }
        }
        list wic-disabled {
          tailf:cli-suppress-mode;
          tailf:cli-delete-when-empty;
          key "slot";
          leaf slot {
            type uint8 {
              tailf:info
                "<0-3>;;Slot Number (physical)";
              range "0..3";
            }
          }
        }
      }
      list T1 {
        tailf:cli-suppress-mode;
        tailf:cli-delete-when-empty;
        key "name";
        leaf name {
          type string {
            pattern '[0-9]+.*';
          }
        }
      }
    }
    container service-routing {
      tailf:ncs-device-type "cli-ned";
      tailf:display-when "not(../../ncs:module) or ../../ncs:module[ncs:name='tailf-ned-cisco-ios']";
      tailf:info
        "Configure service-routing";
      leaf capabilities-manager {
        tailf:info
          "Service-Routing Capabilities Manager configuration";
        tailf:cli-boolean-no;
        tailf:cli-full-command;
        type boolean;
        default "true";
      }
    }
    container mgcp {
      tailf:ncs-device-type "cli-ned";
      tailf:display-when "not(../../ncs:module) or ../../ncs:module[ncs:name='tailf-ned-cisco-ios']";
      tailf:info
        "Enable Media Gateway Control Protocol";
      container fax {
        tailf:info
          "Configure MGCP Fax Parameters";
        container t38 {
          tailf:info
            "Configure MGCP Fax T.38 Parameters";
          leaf ecm {
            tailf:info
              "Enable Error Correction Mode (ECM)";
            tailf:cli-full-command;
            type empty;
          }
        }
      }
      list behavior {
        tailf:info
          "Set MGCP message behavior";
        tailf:cli-suppress-mode;
        tailf:cli-delete-when-empty;
        key "category";
        leaf category {
          type string {
            tailf:info
              "WORD;;Set the category for this behavior";
          }
        }
        leaf version {
          tailf:cli-drop-node-name;
          type string {
            tailf:info
              "WORD;;Set the version for this behavior category";
          }
        }
      }
      list profile {
        tailf:info
          "MGCP profile configuration mode";
        tailf:cli-mode-name "config-mgcp-profile";
        tailf:cli-delete-when-empty;
        key "name";
        leaf name {
          type union {
            type enumeration {
              enum "default" {
                tailf:info
                  "Configure MGCP default profile";
              }
            }
            type string {
              tailf:info
                "Enter the name(is limited to 32 characters) of the profile";
              length "0..32";
            }
          }
        }
      }
    }
    container gatekeeper {
      tailf:ncs-device-type "cli-ned";
      tailf:display-when "not(../../ncs:module) or ../../ncs:module[ncs:name='tailf-ned-cisco-ios']";
      tailf:info
        "Enter gatekeeper configuration mode";
      tailf:cli-add-mode;
      tailf:cli-mode-name "config-gk";
      leaf shutdown {
        tailf:info
          "Shutdown Gatekeeper";
        type empty;
      }
    }
    container parser {
      tailf:ncs-device-type "cli-ned";
      tailf:display-when "not(../../ncs:module) or ../../ncs:module[ncs:name='tailf-ned-cisco-ios']";
      tailf:info
        "Configure parser";
      leaf cache {
        tailf:info
          "Configure parser cache";
        tailf:cli-boolean-no;
        tailf:cli-full-command;
        type boolean;
        default "true";
      }
    }
    container line {
      tailf:ncs-device-type "cli-ned";
      tailf:display-when "not(../../ncs:module) or ../../ncs:module[ncs:name='tailf-ned-cisco-ios']";
      tailf:info
        "Configure a terminal line";
      list console {
        tailf:info
          "Primary terminal line";
        tailf:cli-full-command;
        tailf:cli-mode-name "config-line";
        key "first";
        max-elements 1;
        leaf first {
          type enumeration {
            enum "0" {
              tailf:info
                "<0-0>;;First Line number";
            }
          }
        }
        uses line-grouping;
      }
      list aux {
        tailf:info
          "Auxiliary line";
        tailf:cli-full-command;
        tailf:cli-mode-name "config-line";
        key "first";
        max-elements 1;
        leaf first {
          type enumeration {
            enum "0" {
              tailf:info
                "<0-0>;;First Line number";
            }
          }
        }
        uses line-grouping;
      }
      container vty-single-conf {
        tailf:cli-drop-node-name;
        list vty {
          tailf:info
            "Virtual terminal";
          tailf:cli-full-command;
          tailf:cli-mode-name "config-line";
          key "first";
          leaf first {
            type uint16 {
              tailf:info
                "<0-1869>;;First Line number";
              range "0..1869";
            }
          }
          uses line-grouping;
        }
      }
      list vty {
        tailf:info
          "Virtual terminal";
        tailf:cli-full-command;
        tailf:cli-mode-name "config-line";
        key "first last";
        leaf first {
          type uint16 {
            tailf:info
              "<0-1869>;;First Line number";
            range "0..1869";
          }
        }
        leaf last {
          type uint16 {
            tailf:info
              "<1-1869>;;Last Line number";
            range "1..1869";
          }
        }
        uses line-grouping;
      }
      list number-single-list {
        tailf:cli-drop-node-name;
        tailf:cli-full-command;
        tailf:cli-mode-name "config-line";
        key "first";
        leaf first {
          tailf:cli-suppress-range;
          tailf:cli-disallow-value "con|console|aux|vty";
          type string {
            tailf:info
              "Line number";
          }
        }
        uses line-grouping;
      }
      list number-list {
        tailf:cli-drop-node-name;
        tailf:cli-full-command;
        tailf:cli-mode-name "config-line";
        key "first last";
        leaf first {
          type string {
            tailf:info
              "WORD;;First Line id";
          }
        }
        leaf last {
          type string {
            tailf:info
              "WORD;;Last Line id";
          }
        }
        uses line-grouping;
      }
    }
    container exception {
      tailf:ncs-device-type "cli-ned";
      tailf:display-when "not(../../ncs:module) or ../../ncs:module[ncs:name='tailf-ned-cisco-ios']";
      tailf:info
        "Exception handling";
      container data-corruption {
        tailf:info
          "Data error exception handling";
        container buffer {
          tailf:info
            "Set buffer corruption behavior";
          leaf truncate {
            tailf:info
              "Truncate buffer overwrites";
            type empty;
          }
        }
      }
      container crashinfo {
        tailf:info
          "Crashinfo collection";
        leaf file {
          tailf:info
            "crashinfo file name in bootflash or PCMCIA slot";
          type string {
            tailf:info
              "<WORD>;;device:file name (up to 38 characters)";
          }
        }
        leaf buffersize {
          tailf:info
            "crashinfo log buffer size";
          type uint16 {
            tailf:info
              "<32-256>;;buffer size in Kbytes 256K or less (default is 32K)";
            range "32..256";
          }
        }
      }
    }
    container pnp {
      tailf:ncs-device-type "cli-ned";
      tailf:display-when "not(../../ncs:module) or ../../ncs:module[ncs:name='tailf-ned-cisco-ios']";
      tailf:info
        "Configure PNP";
      list profile {
        tailf:info
          "PNP profile";
        tailf:cli-mode-name "config-pnp-init";
        key "name";
        leaf name {
          type string {
            tailf:info
              "WORD;;PNP Profile name";
          }
        }
        container transport {
          tailf:info
            "The transport to use";
          tailf:cli-compact-syntax;
          tailf:cli-sequence-commands {
            tailf:cli-reset-siblings;
          }
          leaf protocol {
            tailf:cli-drop-node-name;
            type enumeration {
              enum "http" {
                tailf:info
                  "Use http (plaintext) transport";
              }
              enum "https" {
                tailf:info
                  "Use https (encrypted) transport";
              }
              enum "xmpp" {
                tailf:info
                  "Use XMPP transport";
              }
            }
          }
          leaf over {
            tailf:cli-drop-node-name;
            when "../protocol = 'xmpp'" {
              tailf:xpath-root 3;
              tailf:dependency "../protocol";
            }
            type enumeration {
              enum "socket" {
                tailf:info
                  "xmpp over plain socket (no encryption)";
              }
              enum "starttls" {
                tailf:info
                  "xmpp starttls";
              }
              enum "tls" {
                tailf:info
                  "xmpp over tls (encrypted)";
              }
            }
          }
          choice address-choice {
            leaf host {
              tailf:info
                "hostname of server";
              type inet:host {
                tailf:info
                  "WORD;;Hostname of the server";
              }
            }
            leaf ipv4 {
              tailf:info
                "ipv4 address";
              type inet:ipv4-address {
                tailf:info
                  "WORD;;IP address of the server";
              }
            }
            leaf ipv6 {
              tailf:info
                "IPv6 address";
              type inet:ipv6-address {
                tailf:info
                  "X:X:X:X::X;;IPv6 address of server";
              }
            }
          }
          leaf port {
            tailf:info
              "port number";
            type uint16 {
              tailf:info
                "<1-65535>;;Port number to use";
            }
          }
          leaf vrf {
            tailf:info
              "Bind port to VRF";
            tailf:cli-optional-in-sequence;
            type string {
              tailf:info
                "WORD;;VRF name";
            }
          }
          container source {
            tailf:info
              "Bind port to interface";
            tailf:cli-optional-in-sequence;
            tailf:cli-flatten-container;
            tailf:cli-compact-syntax;
            uses interface-name-grouping;
          }
          leaf localcert {
            tailf:info
              "Local certificate";
            tailf:cli-optional-in-sequence;
            type string {
              tailf:info
                "WORD;;Trustpoint name";
            }
          }
          leaf remotecert {
            tailf:info
              "Remote certificate validation";
            type string {
              tailf:info
                "WORD;;Trustpoint name";
            }
          }
        }
        container reconnect {
          tailf:info
            "Pause to wait before reconnecting";
          leaf seconds {
            tailf:cli-drop-node-name;
            type uint32 {
              tailf:info
                "<1-2000000>;;Pause in seconds";
              range "1..2000000";
            }
          }
        }
      }
      leaf startup-vlan {
        tailf:info
          "PNP startup-vlan";
        tailf:cli-full-command;
        type uint16 {
          tailf:info
            "PNP vlan id;default vlan is 1";
          range "2..4094";
        }
      }
      leaf tag {
        tailf:info
          "PNP tag";
        tailf:cli-full-command;
        type string {
          tailf:info
            "WORD;;PNP tag name";
        }
      }
    }
    container onep {
      tailf:ncs-device-type "cli-ned";
      tailf:display-when "not(../../ncs:module) or ../../ncs:module[ncs:name='tailf-ned-cisco-ios']";
      tailf:info
        "ONEP functionality";
      tailf:cli-add-mode;
      leaf start {
        tailf:cli-boolean-no;
        tailf:cli-full-command;
        type boolean;
      }
      container transport {
        tailf:info
          "Transport type";
        container tipc {
          tailf:info
            "tipc transport";
          presence "true";
        }
      }
    }
    container logging {
      tailf:ncs-device-type "cli-ned";
      tailf:display-when "not(../../ncs:module) or ../../ncs:module[ncs:name='tailf-ned-cisco-ios']";
      tailf:info
        "Modify message logging facilities";
      list discriminator {
        tailf:info
          "Create or modify a message discriminator";
        tailf:cli-suppress-mode;
        tailf:cli-delete-when-empty;
        tailf:cli-compact-syntax;
        key "discr-name";
        leaf discr-name {
          type string {
            tailf:info
              "WORD;;discriminator name; string; max. 8 characters";
          }
        }
        container mnemonics {
          tailf:info
            "Mnemonics pattern for messsage filtering";
          tailf:cli-flatten-container;
          tailf:cli-compact-syntax;
          choice mnemonics-choice {
            leaf drops {
              tailf:info
                "To drop messages including the specified regexp string";
              type string {
                tailf:info
                  "WORD;;Specify a regular expression string for message filtering";
              }
            }
            leaf includes {
              tailf:info
                "To deliver messages including the specified regexp string";
              type string {
                tailf:info
                  "WORD;;Specify a regular expression string for message filtering";
              }
            }
          }
        }
        container msg-body {
          tailf:info
            "Msg-body pattern for messsage filtering";
          tailf:cli-flatten-container;
          tailf:cli-compact-syntax;
          choice msg-body-choice {
            leaf drops {
              tailf:info
                "To drop messages including the specified regexp string";
              type string {
                tailf:info
                  "WORD;;Specify a regular expression string for message filtering";
              }
            }
            leaf includes {
              tailf:info
                "To deliver messages including the specified regexp string";
              type string {
                tailf:info
                  "WORD;;Specify a regular expression string for message filtering";
              }
            }
          }
        }
      }
      container cmts {
        tailf:info
          "CMTS config commands";
        container ipc-cable {
          tailf:info
            "Cable IPC config commands";
          leaf log-level {
            tailf:info
              "cable ipc log level config commands";
            type logging-level-type;
          }
        }
        container sea {
          tailf:info
            "SEA config commands";
          leaf syslog-level {
            tailf:info
              "Specify syslog loggging level";
            type logging-level-type;
          }
        }
      }
      leaf alarm {
        tailf:info
          "Configure syslog for alarms";
        tailf:cli-full-command;
        type union {
          type uint8 {
            tailf:info
              "<1-4>;;Alarm Logging severity level";
            range "1..4";
          }
          type enumeration {
            enum "critical" {
              tailf:info
                "Service affecting Condition       (severity=1)";
            }
            enum "informational" {
              tailf:info
                "Informational messages            (severity=4)";
            }
            enum "major" {
              tailf:info
                "Immediate action needed           (severity=2)";
            }
            enum "minor" {
              tailf:info
                "Minor warning conditions          (severity=3)";
            }
          }
        }
      }
      container message-counter {
        tailf:info
          "Configure log message to include certain counter value";
        leaf log {
          tailf:info
            "counter of accumulated logging messages received by logger";
          tailf:cli-full-command;
          type empty;
        }
        leaf debug {
          tailf:info
            "counter of accumulated buginf messages received by logger";
          tailf:cli-full-command;
          type empty;
        }
        leaf syslog {
          tailf:info
            "counter of current lines of syslog messages sent";
          tailf:cli-boolean-no;
          tailf:cli-full-command;
          type boolean;
          default "true";
        }
      }
      container buffered {
        tailf:info
          "Set buffered logging parameters";
        tailf:cli-compact-syntax;
        tailf:cli-sequence-commands {
          tailf:cli-reset-siblings;
        }
        leaf xxml {
          tailf:alt-name "xml";
          tailf:info
            "Enable logging in XML to XML logging buffer";
          tailf:cli-optional-in-sequence;
          type empty;
        }
        leaf discriminator {
          when "not(../xxml)" {
            tailf:xpath-root 3;
            tailf:dependency "../xxml";
          }
          tailf:info
            "Establish MD-Console association";
          tailf:cli-optional-in-sequence;
          tailf:non-strict-leafref {
            path "../../../logging/discriminator/discr-name";
          }
          type string {
            tailf:info
              "WORD;;discriminator name; string; max. 8 characters";
          }
        }
        leaf buffer-size {
          tailf:cli-drop-node-name;
          tailf:cli-optional-in-sequence;
          type uint32 {
            tailf:info
              "<4096-2147483647>;;Logging buffer size";
            range "4096..2147483647";
          }
        }
        leaf severity-level {
          tailf:cli-drop-node-name;
          type logging-level-type;
        }
      }
      container persistent {
        tailf:info
          "Set persistent logging parameters";
        tailf:cli-compact-syntax;
        leaf url {
          tailf:info
            "URL to store logging messages";
          type string {
            tailf:info
              "WORD;;Filesystem name";
          }
        }
        leaf size {
          tailf:info
            "Set disk space for writing log messages";
          type uint32 {
            tailf:info
              "<16384-256503808>;;Logging filesystem size";
            range "16384..256503808";
          }
        }
        leaf filesize {
          tailf:info
            "Set size of individual log files";
          type uint32 {
            tailf:info
              "<8192-256503808>;;Logging file size";
            range "8192..256503808";
          }
        }
      }
      container queue-limit {
        tailf:info
          "Set logger message queue size";
        leaf queuesize {
          tailf:cli-drop-node-name;
          tailf:cli-full-command;
          type uint32 {
            tailf:info
              "<100-2147483647>;;Set new queue size";
            range "100..2147483647";
          }
        }
      }

      grouping logging-common-grouping {
        leaf xxml {
          tailf:alt-name "xml";
          tailf:info
            "Enable logging in XML to XML logging buffer";
          tailf:cli-optional-in-sequence;
          type empty;
        }
        leaf discriminator {
          when "not(../xxml)" {
            tailf:xpath-root 3;
            tailf:dependency "../xxml";
          }
          tailf:info
            "Establish MD-Console association";
          tailf:cli-optional-in-sequence;
          tailf:non-strict-leafref {
            path "../../../logging/discriminator/discr-name";
          }
          type string {
            tailf:info
              "WORD;;discriminator name; string; max. 8 characters";
          }
        }
        leaf filtered {
          tailf:info
            "Enable filtered logging";
          tailf:cli-optional-in-sequence;
          type empty;
        }
        leaf severity-level {
          tailf:cli-drop-node-name;
          type logging-level-type;
        }
      }
      container console {
        tailf:info
          "Set console logging parameters";
        tailf:cli-compact-syntax;
        tailf:cli-sequence-commands {
          tailf:cli-reset-siblings;
        }
        uses logging-common-grouping;
      }
      container monitor {
        tailf:info
          "Set terminal line (monitor) logging parameters";
        tailf:cli-compact-syntax;
        tailf:cli-sequence-commands {
          tailf:cli-reset-siblings;
        }
        uses logging-common-grouping;
      }
      container snmp-trap {
        tailf:info
          "Set syslog level for sending snmp trap";
        leaf emergencies {
          tailf:info
            "System is not stable               (severity=0)";
          type empty;
        }
        leaf critical {
          tailf:info
            "Critical conditions               (severity=2)";
          type empty;
        }
        leaf errors {
          tailf:info
            "Error conditions                  (severity=3)";
          type empty;
        }
        leaf informational {
          tailf:info
            "Informational messages            (severity=6)";
          type empty;
        }
        leaf alerts {
          tailf:info
            "Immediate action needed           (severity=1)";
          type empty;
        }
        leaf warnings {
          tailf:info
            "Warning conditions                (severity=4)";
          type empty;
        }
        leaf notifications {
          tailf:info
            "Normal but significant conditions (severity=5)";
          type empty;
        }
        leaf debugging {
          tailf:info
            "Debugging messages                (severity=7)";
          type empty;
        }
      }
      leaf snmp-authfail {
        tailf:cli-full-command;
        type empty;
      }
      container event {
        tailf:info
          "Global interface events";
        container link-status {
          tailf:info
            "Globally enable/disable link UPDOWN message";
          leaf boot {
            tailf:info
              "Supress/Allow link UPDOWN messages during boot";
            type empty;
          }
          leaf global {
            type empty;
          }
          leaf default {
            tailf:info
              "Link UPDOWN messages for all interfaces";
            type empty;
          }
        }
        container trunk-status {
          tailf:info
            "trunk status logging event";
          leaf global {
            tailf:info
              "global trunk status logging event";
            type empty;
          }
        }
      }
      container esm {
        tailf:info
          "Set ESM filter restrictions";
        leaf config {
          tailf:info
            "Permit/Deny configuration changes from ESM filters";
          type empty;
        }
      }
      leaf facility {
        tailf:info
          "Facility parameter for syslog messages";
        tailf:cli-full-command;
        type enumeration {
          enum "auth" {
            tailf:info
              "Authorization system";
          }
          enum "cron" {
            tailf:info
              "Cron/at facility";
          }
          enum "daemon" {
            tailf:info
              "System daemons";
          }
          enum "kern" {
            tailf:info
              "Kernel";
          }
          enum "local0" {
            tailf:info
              "Local use";
          }
          enum "local1" {
            tailf:info
              "Local use";
          }
          enum "local2" {
            tailf:info
              "Local use";
          }
          enum "local3" {
            tailf:info
              "Local use";
          }
          enum "local4" {
            tailf:info
              "Local use";
          }
          enum "local5" {
            tailf:info
              "Local use";
          }
          enum "local6" {
            tailf:info
              "Local use";
          }
          enum "local7" {
            tailf:info
              "Local use";
          }
          enum "lpr" {
            tailf:info
              "Line printer system";
          }
          enum "mail" {
            tailf:info
              "Mail system";
          }
          enum "news" {
            tailf:info
              "USENET news";
          }
          enum "sys10" {
            tailf:info
              "System use";
          }
          enum "sys11" {
            tailf:info
              "System use";
          }
          enum "sys12" {
            tailf:info
              "System use";
          }
          enum "sys13" {
            tailf:info
              "System use";
          }
          enum "sys14" {
            tailf:info
              "System use";
          }
          enum "sys9" {
            tailf:info
              "System use";
          }
          enum "syslog" {
            tailf:info
              "Syslog itself";
          }
          enum "user" {
            tailf:info
              "User process";
          }
          enum "uucp" {
            tailf:info
              "Unix-to-Unix copy system";
          }
        }
        default "local7";
      }
      container history {
        tailf:info
          "Configure syslog history table";
        leaf size {
          tailf:info
            "Set history table size";
          type uint16 {
            tailf:info
              "<0-500>;History size";
          }
        }
        leaf severity-level {
          tailf:cli-drop-node-name;
          type logging-level-type;
        }
      }
      list hostname {
        tailf:info
          "Hostname or A.B.C.D;;IP address of the logging host";
        tailf:cli-drop-node-name;
        tailf:cli-suppress-mode;
        tailf:cli-delete-when-empty;
        key "host";
        leaf host {
          tailf:cli-disallow-value "esm|alarm|buffered|facility|history|rate-limit|source-interface|host|console";
          tailf:cli-full-command;
          type inet:host {
            tailf:info
              "Hostname or A.B.C.D;;IP address of the logging host";
          }
        }
      }
      container host {
        tailf:info
          "Set syslog server IP address and parameters";
        list ipv4 {
          tailf:cli-drop-node-name;
          tailf:cli-suppress-mode;
          tailf:cli-delete-when-empty;
          tailf:cli-compact-syntax;
          key "host";
          leaf host {
            tailf:cli-disallow-value "ipv6";
            type inet:host {
              tailf:info
                "Hostname or A.B.C.D;;IP address of the syslog server";
            }
          }
          uses logging-host-grouping;
        }
        list ipv4-vrf {
          tailf:cli-drop-node-name;
          tailf:cli-suppress-mode;
          tailf:cli-delete-when-empty;
          tailf:cli-compact-syntax;
          key "host vrf";
          leaf host {
            tailf:cli-disallow-value "ipv6";
            type inet:host {
              tailf:info
                "Hostname or A.B.C.D;;IP address of the syslog server";
            }
          }
          leaf vrf {
            tailf:info
              "Set VRF option";
            tailf:cli-expose-key-name;
            tailf:cli-diff-dependency "../../../../ip/vrf" {
              tailf:xpath-root 3;
            }
            tailf:cli-diff-dependency "../../../../vrf/definition" {
              tailf:xpath-root 3;
            }
            type string {
              tailf:info
                "WORD;;VPN Routing/Forwarding instance name";
            }
          }
          uses logging-host-grouping;
        }
        list ipv6 {
          tailf:info
            "Configure IPv6 syslog server";
          tailf:cli-suppress-mode;
          tailf:cli-delete-when-empty;
          tailf:cli-compact-syntax;
          key "host";
          leaf host {
            type inet:host {
              tailf:info
                "Hostname or X:X:X:X::X;;IPv6 address of the syslog server";
            }
          }
          uses logging-host-grouping;
        }
        container ipv6-vrf {
          tailf:cli-drop-node-name;
          list ipv6 {
            tailf:info
              "Configure IPv6 syslog server";
            tailf:cli-suppress-mode;
            tailf:cli-delete-when-empty;
            tailf:cli-compact-syntax;
            key "host vrf";
            leaf host {
              type inet:host {
                tailf:info
                  "Hostname or X:X:X:X::X;;IPv6 address of the syslog server";
              }
            }
            leaf vrf {
              tailf:info
                "Set VRF option";
              tailf:cli-expose-key-name;
              tailf:cli-diff-dependency "../../../../../vrf/definition" {
                tailf:xpath-root 3;
              }
              type string {
                tailf:info
                  "WORD;;VPN Routing/Forwarding instance name";
              }
            }
            uses logging-host-grouping;
          }
        }
      }
      choice rate-limit-choice {
        leaf rate-limit {
          tailf:cli-boolean-no;
          tailf:cli-full-command;
          type boolean;
          default "true";
        }
        container rate-limit-conf {
          tailf:cli-drop-node-name;
          container rate-limit {
            tailf:info
              "Set messages per second limit";
            tailf:cli-compact-syntax;
            tailf:cli-sequence-commands {
              tailf:cli-reset-siblings;
            }
            tailf:cli-incomplete-command;
            tailf:cli-incomplete-no;
            leaf console {
              tailf:info
                "Rate limit only console messages";
              tailf:cli-optional-in-sequence;
              tailf:cli-incomplete-command;
              type empty;
            }
            leaf all {
              tailf:info
                "Rate limit all messages, including debug messages";
              tailf:cli-optional-in-sequence;
              tailf:cli-incomplete-command;
              type empty;
            }
            leaf rate {
              tailf:cli-drop-node-name;
              type uint16 {
                tailf:info
                  "<1-10000>;;Messages per second";
                range "1..10000";
              }
            }
            leaf except {
              tailf:info
                "Messages of this severity or higher";
              type logging-level-type;
            }
          }
        }
      }
      list source-interface {
        tailf:info
          "Specify interface for source address in logging transactions";
        tailf:cli-suppress-mode;
        tailf:cli-delete-when-empty;
        tailf:cli-compact-syntax;
        key "name";
        leaf name {
          tailf:cli-diff-dependency "../../../interface" {
            tailf:xpath-root 3;
          }
          type string {
            tailf:info
              "WORD;;Interface name";
          }
        }
        leaf vrf {
          tailf:info
            "Specify the vrf of source interface for logging transactions";
          tailf:cli-diff-dependency "../../../ip/vrf" {
            tailf:xpath-root 3;
          }
          tailf:cli-diff-dependency "../../../vrf/definition" {
            tailf:xpath-root 3;
          }
          type string {
            tailf:info
              "WORD;;VPN Routing/Forwarding instance name";
          }
        }
      }
      leaf trap {
        tailf:info
          "Set syslog server logging level";
        tailf:cli-full-command;
        type logging-level-type;
        default "informational";
      }
      container origin-id {
        tailf:info
          "Add origin ID to syslog messages";
        choice origin-id-choice {
          leaf hostname {
            tailf:info
              "Use origin hostname as ID";
            type empty;
          }
          leaf ip {
            tailf:info
              "Use origin IP address as ID";
            type empty;
          }
          leaf ipv6 {
            tailf:info
              "Use origin IPv6 address as ID";
            type empty;
          }
          leaf string {
            tailf:info
              "Define a unique text string as ID";
            type string {
              tailf:info
                "WORD;;Text string";
            }
          }
        }
      }
      container linecard {
        tailf:info
          "specify logging parameters for a linecard messages";
        leaf size {
          tailf:cli-drop-node-name;
          tailf:cli-full-command;
          type uint32 {
            tailf:info
              "<4096-65536>;;number of bytes of message log per slot";
            range "4096..65535";
          }
          default "8192";
        }
        leaf level {
          tailf:cli-drop-node-name;
          tailf:cli-full-command;
          type logging-level-type;
        }
      }
    }
    container firewall {
      tailf:ncs-device-type "cli-ned";
      tailf:display-when "not(../../ncs:module) or ../../ncs:module[ncs:name='tailf-ned-cisco-ios']";
      tailf:info
        "Specify secure VLANs groups and tie them to firewall modules";
      leaf multiple-vlan-interfaces {
        tailf:info
          "Enable multiple vlan interfaces mode for firewall modules";
        type empty;
      }
      list vlan-group {
        tailf:info
          "Secure group which VLANs will be tied to";
        tailf:cli-suppress-mode;
        tailf:cli-delete-when-empty;
        tailf:cli-incomplete-command;
        key "id";
        leaf id {
          type uint16 {
            tailf:info
              "<1-65535>;;group-number";
            range "1..65535";
          }
        }
        leaf-list vlan {
          tailf:cli-drop-node-name;
          tailf:cli-range-list-syntax;
          type uint16 {
            tailf:info
              "WORD;;vlan range (2-1001,1006-4094) ex: 2-65,72,300-320";
          }
        }
      }
    }
    container cpd {
      tailf:ncs-device-type "cli-ned";
      tailf:display-when "not(../../ncs:module) or ../../ncs:module[ncs:name='tailf-ned-cisco-ios']";
      tailf:info
        "Global Control Point Discovery Configuration";
      tailf:cli-display-separated;
      presence "true";
      leaf cr-id {
        tailf:info
          "Control Relationship Identifier";
        type uint16 {
          tailf:info
            "<1-65535>;;Control Relationship Identifier Value";
          range "1..65535";
        }
      }
    }
    container nls {
      tailf:ncs-device-type "cli-ned";
      tailf:display-when "not(../../ncs:module) or ../../ncs:module[ncs:name='tailf-ned-cisco-ios']";
      tailf:info
        "Global Network Layer Signaling Configuration";
      tailf:cli-display-separated;
      presence "true";
      leaf resp-timeout {
        tailf:info
          "NLS Response Timeout";
        type uint8 {
          tailf:info
            "<1-60>;;NLS Response Timeout Value";
          range "1..60";
        }
      }
    }
    list flow-sampler-map {
      tailf:ncs-device-type "cli-ned";
      tailf:display-when "not(../ncs:module) or ../ncs:module[ncs:name='tailf-ned-cisco-ios']";
      tailf:info
        "Flow sampler configuration";
      tailf:cli-mode-name "config-sampler";
      key "name";
      leaf name {
        type string {
          tailf:info
            "WORD;;Name of the flow sampler";
        }
      }
      container mode {
        tailf:info
          "Mode of packet sampling for netflow processing";
        container random {
          tailf:info
            "Random mode of sampling";
          leaf one-out-of {
            tailf:info
              "Select one packet out of";
            type uint16 {
              tailf:info
                "<1-65535>;number of sequential packets to select one packet from";
              range "1..65535";
            }
          }
        }
      }
    }
    container frame-relay {
      tailf:ncs-device-type "cli-ned";
      tailf:display-when "not(../../ncs:module) or ../../ncs:module[ncs:name='tailf-ned-cisco-ios']";
      tailf:info
        "global frame relay configuration commands";
      leaf switching {
        tailf:info
          "enable frame relay pvc switching";
        type empty;
      }
    }
    container scheduler {
      tailf:ncs-device-type "cli-ned";
      tailf:display-when "not(../../ncs:module) or ../../ncs:module[ncs:name='tailf-ned-cisco-ios']";
      tailf:info
        "Scheduler parameters";
      container allocate {
        tailf:info
          "Guarantee CPU time for processes";
        tailf:cli-compact-syntax;
        tailf:cli-sequence-commands;
        leaf interrupt-time {
          tailf:cli-drop-node-name;
          tailf:cli-incomplete-command;
          type uint16 {
            tailf:info
              "<400-60000>;;Microseconds handling network interrupts";
            range "400..60000";
          }
        }
        leaf process-time {
          tailf:cli-drop-node-name;
          type uint16 {
            tailf:info
              "<100-4000>;;Microseconds running processes";
            range "100..4000";
          }
        }
      }
      leaf isr-watchdog {
        tailf:info
          "Detect ISR Hang";
        type empty;
      }
      container runtime {
        tailf:info
          "Process runtime controls";
        leaf netinput {
          tailf:info
            "Enable packet process-switching run time";
          type uint16 {
            tailf:info
              "<100-40000>;;Process-switching run time (in milliseconds)";
            range "100..40000";
          }
        }
      }
    }
    container wsma {
      tailf:ncs-device-type "cli-ned";
      tailf:display-when "not(../../ncs:module) or ../../ncs:module[ncs:name='tailf-ned-cisco-ios']";
      tailf:info
        "Configure Web Services Management Agents";
      list agent {
        tailf:info
          "Configure WSMA agents";
        key "name";
        leaf name {
          type enumeration {
            enum "config" {
              tailf:info
                "Start WSMA config agent";
            }
            enum "exec" {
              tailf:info
                "Start WSMA exec agent";
            }
            enum "filesys" {
              tailf:info
                "Start WSMA file system agent";
            }
            enum "notify" {
              tailf:info
                "Start WSMA notify agent";
            }
          }
        }
        list profile {
          tailf:info
            "Profile to use";
          tailf:cli-suppress-mode;
          tailf:cli-delete-when-empty;
          key "name";
          leaf name {
            type string {
              tailf:info
                "WORD;;Profile name";
            }
          }
        }
      }
      container profile {
        tailf:info
          "Configure WSMA profil";
        list listener {
          tailf:cli-mode-name "config-wsma-listen";
          key "name";
          leaf name {
            type string {
              tailf:info
                "WORD;;Listener profile name";
            }
          }
          container transport {
            tailf:info
              "The transport to use";
            choice transport-choice {
              container http {
                tailf:info
                  "Use http (plaintext) transport";
                presence "true";
              }
              container https {
                tailf:info
                  "Use https (encrypted) transport";
                presence "true";
              }
              container ssh {
                tailf:info
                  "Use SSH V2";
                presence "true";
              }
            }
          }
        }
        list initiator {
          tailf:cli-mode-name "config-wsma-init";
          key "name";
          leaf name {
            type string {
              tailf:info
                "WORD;;Initiator profile name";
            }
          }
          container transport {
            tailf:info
              "The transport to use";
            choice transport-choice {
              container http {
                tailf:info
                  "Use http (plaintext) transport";
                presence "true";
              }
              container https {
                tailf:info
                  "Use https (encrypted) transport";
                presence "true";
              }
              container ssh {
                tailf:info
                  "Use SSH V2";
                presence "true";
              }
            }
          }
        }
      }
    }
    container process {
      tailf:ncs-device-type "cli-ned";
      tailf:display-when "not(../../ncs:module) or ../../ncs:module[ncs:name='tailf-ned-cisco-ios']";
      tailf:info
        "Configure process";
      container cpu {
        tailf:info
          "Configure cpu parameters";
        container threshold {
          tailf:info
            "cpu threshold parameters";
          container type {
            tailf:info
              "cpu threshold type";
            tailf:cli-compact-syntax;
            container total {
              tailf:info
                "total cpu utilization";
              tailf:cli-compact-syntax;
              tailf:cli-sequence-commands {
                tailf:cli-reset-siblings;
              }
              uses process-cpu-threshold-grouping;
            }
            container interrupt {
              tailf:info
                "interrupt level utilization";
              tailf:cli-compact-syntax;
              tailf:cli-sequence-commands {
                tailf:cli-reset-siblings;
              }
              uses process-cpu-threshold-grouping;
            }
            container process {
              tailf:info
                "process level utilization";
              tailf:cli-compact-syntax;
              tailf:cli-sequence-commands {
                tailf:cli-reset-siblings;
              }
              uses process-cpu-threshold-grouping;
            }
          }
        }
        container statistics {
          tailf:info
            "cpu statistics";
          container limit {
            tailf:info
              "cpu utilization history";
            tailf:cli-compact-syntax;
            tailf:cli-sequence-commands {
              tailf:cli-reset-siblings;
            }
            leaf entry-percentage {
              tailf:info
                "cpu history entry percentage";
              type uint8 {
                tailf:info
                  "<1-100>";
                range "1..100";
              }
            }
            leaf size {
              tailf:info
                "cpu history size in seconds";
              type uint32 {
                tailf:info
                  "<5-86400>";
                range "5..86400";
              }
            }
          }
        }
      }
    }
    container ntp {
      tailf:ncs-device-type "cli-ned";
      tailf:display-when "not(../../ncs:module) or ../../ncs:module[ncs:name='tailf-ned-cisco-ios']";
      tailf:info
        "Configure NTP";
      leaf max-associations {
        tailf:info
          "Set maximum number of associations";
        tailf:cli-full-command;
        type uint32 {
          tailf:info
            "<0-4294967295>;;Number of associations";
        }
      }
      leaf passive {
        tailf:info
          "NTP passive mode";
        tailf:cli-full-command;
        type empty;
      }
      leaf logging {
        tailf:info
          "Enable NTP message logging";
        tailf:cli-full-command;
        type empty;
      }
      container panic {
        tailf:info
          "Reject time updates > panic threshold (default 1000Sec)";
        leaf update {
          tailf:info
            "Reject time updates > panic threshold (default 1000Sec)";
          type empty;
        }
      }
      list authentication-key {
        tailf:info
          "Authentication key for trusted time sources";
        tailf:cli-suppress-mode;
        tailf:cli-delete-when-empty;
        tailf:cli-sequence-commands;
        tailf:cli-compact-syntax;
        tailf:cli-incomplete-command;
        key "number";
        leaf number {
          type uint32 {
            tailf:info
              "<1-4294967295>;;Key number";
            range "1..4294967295";
          }
        }
        container md5 {
          tailf:info
            "MD5 authentication";
          tailf:cli-flatten-container;
          tailf:cli-compact-syntax;
          tailf:cli-sequence-commands;
          leaf secret {
            tailf:cli-drop-node-name;
            tailf:cli-reset-container;
            tailf:meta-data "secret-password";
            type string {
              tailf:info
                "WORD;;Authentication key";
            }
          }
          leaf type {
            tailf:cli-drop-node-name;
            type uint32 {
              tailf:info
                "<0-4294967295>;;Authentication key encryption type";
            }
          }
        }
      }
      leaf authenticate {
        tailf:info
          "Authenticate time sources";
        tailf:cli-full-command;
        type empty;
      }
      list trusted-key {
        tailf:info
          "Key numbers for trusted time sources";
        tailf:cli-suppress-mode;
        tailf:cli-delete-when-empty;
        tailf:cli-compact-syntax;
        tailf:cli-sequence-commands;
        key "key-number";
        leaf key-number {
          type uint16 {
            tailf:info
              "<1-65535>;;Key number";
            range "1..65535";
          }
        }
        leaf hyphen {
          tailf:info
            "hyphen";
          tailf:alt-name "-";
          tailf:cli-incomplete-command;
          type empty;
        }
        leaf end-key-number {
          tailf:cli-drop-node-name;
          type uint16 {
            tailf:info
              "<1-65535>;;End Key range";
            range "1..65535";
          }
        }
      }
      leaf orphan {
        tailf:info
          "Threshold Stratum for orphan mode";
        tailf:cli-full-command;
        type uint8 {
          tailf:info
            "<1-16>;;Orphan stratum";
          range "1..16";
        }
      }
      leaf mindistance {
        tailf:info
          "Minimum distance to consider for clockhop";
        tailf:cli-full-command;
        type uint16 {
          tailf:info
            "<1-500>;;Minimum distance to consider for clockhop";
          range "1..500";
        }
      }
      leaf maxdistance {
        tailf:info
          "Maximum Distance for synchronization";
        tailf:cli-full-command;
        type uint8 {
          tailf:info
            "<1-16>;;Maximum distance for synchronization";
          range "1..16";
        }
      }
      leaf broadcastdelay {
        tailf:info
          "Estimated round-trip delay";
        tailf:cli-full-command;
        type uint32 {
          tailf:info
            "<1-999999>;;Round-trip delay in microseconds";
          range "1..999999";
        }
      }
      container source {
        tailf:info
          "Configure interface for source address";
        uses interface-name-grouping;
      }
      container access-group {
        tailf:info
          "Control NTP access";
        container peer {
          tailf:info
            "Provide full access";
          tailf:cli-compact-syntax;
          tailf:cli-sequence-commands;
          leaf access-list {
            tailf:cli-drop-node-name;
            type std-ip-acl-type;
          }
          leaf kod {
            tailf:info
              "Send a Kiss-o-Death packet for failing peers";
            type empty;
          }
        }
        container query-only {
          tailf:info
            "Allow only control queries";
          tailf:cli-compact-syntax;
          tailf:cli-sequence-commands;
          leaf access-list {
            tailf:cli-drop-node-name;
            type std-ip-acl-type;
          }
          leaf kod {
            tailf:info
              "Send a Kiss-o-Death packet for failing peers";
            type empty;
          }
        }
        container serve {
          tailf:info
            "Provide server and query access";
          tailf:cli-compact-syntax;
          tailf:cli-sequence-commands;
          leaf access-list {
            tailf:cli-drop-node-name;
            type std-ip-acl-type;
          }
          leaf kod {
            tailf:info
              "Send a Kiss-o-Death packet for failing peers";
            type empty;
          }
        }
        container serve-only {
          tailf:info
            "Provide only server access";
          tailf:cli-compact-syntax;
          tailf:cli-sequence-commands;
          leaf access-list {
            tailf:cli-drop-node-name;
            type std-ip-acl-type;
          }
          leaf kod {
            tailf:info
              "Send a Kiss-o-Death packet for failing peers";
            type empty;
          }
        }
        container ipv6 {
          tailf:info
            "ipv6 access lists";
          container peer {
            tailf:info
              "Provide full access";
            tailf:cli-compact-syntax;
            tailf:cli-sequence-commands;
            leaf access-list {
              tailf:cli-drop-node-name;
              type std-ip-acl-type;
            }
            leaf kod {
              tailf:info
                "Send a Kiss-o-Death packet for failing peers";
              type empty;
            }
          }
        }
      }
      container master {
        tailf:info
          "Act as NTP master clock";
        tailf:cli-delete-when-empty;
        presence "true";
        leaf stratum {
          tailf:cli-drop-node-name;
          type uint8 {
            tailf:info
              "<1-15>;;Stratum number";
            range "1..15";
          }
        }
      }
      container peer {
        tailf:info
          "Configure NTP peer";
        uses ntp-peer-grouping;
        container ip {
          tailf:info
            "Use IP for DNS resolution";
          tailf:cli-compact-syntax;
          uses ntp-peer-grouping;
        }
        container ipv6 {
          tailf:info
            "Use IPv6 for DNS resolution";
          tailf:cli-compact-syntax;
          uses ntp-peer-grouping;
        }
        list vrf {
          tailf:info
            "VPN Routing/Forwarding Information";
          tailf:cli-suppress-mode;
          tailf:cli-delete-when-empty;
          tailf:cli-compact-syntax;
          tailf:cli-incomplete-command;
          key "name";
          leaf name {
            tailf:cli-diff-dependency "../../../../ip/vrf" {
              tailf:xpath-root 3;
            }
            tailf:cli-diff-dependency "../../../../vrf/definition" {
              tailf:xpath-root 3;
            }
            type string {
              tailf:info
                "WORD;;VPN Routing/Forwarding instance name";
            }
          }
          uses ntp-peer-grouping;
        }
      }
      container server {
        tailf:info
          "Configure NTP server";
        uses ntp-peer-grouping;
        container ip {
          tailf:info
            "Use IP for DNS resolution";
          tailf:cli-compact-syntax;
          uses ntp-peer-grouping;
        }
        container ipv6 {
          tailf:info
            "Use IPv6 for DNS resolution";
          tailf:cli-compact-syntax;
          uses ntp-peer-grouping;
        }
        list vrf {
          tailf:info
            "VPN Routing/Forwarding Information";
          tailf:cli-suppress-mode;
          tailf:cli-delete-when-empty;
          tailf:cli-compact-syntax;
          tailf:cli-reset-container;
          tailf:cli-incomplete-command;
          key "name";
          leaf name {
            tailf:cli-diff-dependency "../../../../ip/vrf" {
              tailf:xpath-root 3;
            }
            tailf:cli-diff-dependency "../../../../vrf/definition" {
              tailf:xpath-root 3;
            }
            type string {
              tailf:info
                "WORD;;VPN Routing/Forwarding instance name";
            }
          }
          uses ntp-peer-grouping;
        }
      }
      container allow {
        tailf:info
          "Allow processing of packets";
        container mode {
          tailf:info
            "Allow processing of particular mode packets";
          leaf private {
            tailf:info
              "Allow processing private mode packets";
            type empty;
          }
        }
      }
      leaf update-calendar {
        tailf:info
          "Periodically update calendar with NTP time";
        type empty;
      }
    }
    container sntp {
      tailf:ncs-device-type "cli-ned";
      tailf:display-when "not(../../ncs:module) or ../../ncs:module[ncs:name='tailf-ned-cisco-ios']";
      tailf:info
        "Configure SNTP";
      tailf:cli-incomplete-no;
      leaf logging {
        tailf:info
          "Enable SNTP message logging";
        tailf:cli-full-command;
        type empty;
      }
      list authentication-key {
        tailf:info
          "Authentication key for trusted time sources";
        tailf:cli-suppress-mode;
        tailf:cli-delete-when-empty;
        tailf:cli-sequence-commands;
        tailf:cli-compact-syntax;
        tailf:cli-incomplete-command;
        key "number";
        leaf number {
          type uint32 {
            tailf:info
              "<1-4294967295>;;Key number";
            range "1..4294967295";
          }
        }
        leaf md5 {
          tailf:info
            "MD5 authentication";
          type string {
            tailf:info
              "WORD;;Authentication key";
          }
        }
        leaf encryption-type {
          tailf:cli-drop-node-name;
          type uint32 {
            tailf:info
              "<0-4294967295>;;Authentication key encryption type";
          }
        }
      }
      leaf authenticate {
        tailf:info
          "Authenticate time sources";
        tailf:cli-full-command;
        type empty;
      }
      list trusted-key {
        tailf:info
          "Key numbers for trusted time sources";
        tailf:cli-suppress-mode;
        tailf:cli-delete-when-empty;
        tailf:cli-sequence-commands;
        tailf:cli-compact-syntax;
        key "key-number";
        leaf key-number {
          type uint16 {
            tailf:info
              "<1-65535>;;Key number";
            range "1..65535";
          }
        }
        leaf hyphen {
          tailf:info
            "hyphen";
          tailf:alt-name "-";
          tailf:cli-incomplete-command;
          type empty;
        }
        leaf end-key-number {
          tailf:cli-drop-node-name;
          type uint16 {
            tailf:info
              "<1-65535>;;End Key range";
            range "1..65535";
          }
        }
      }
      container server {
        tailf:info
          "Configure SNTP server";
        uses sntp-server-grouping;
        container ip {
          tailf:info
            "Use IP for DNS resolution";
          tailf:cli-compact-syntax;
          uses sntp-server-grouping;
        }
        container ipv6 {
          tailf:info
            "Use IPv6 for DNS resolution";
          tailf:cli-compact-syntax;
          uses sntp-server-grouping;
        }
        list vrf {
          tailf:info
            "VPN Routing/Forwarding Information";
          tailf:cli-suppress-mode;
          tailf:cli-delete-when-empty;
          tailf:cli-compact-syntax;
          tailf:cli-reset-container;
          tailf:cli-incomplete-command;
          key "name";
          leaf name {
            tailf:cli-diff-dependency "../../../../ip/vrf" {
              tailf:xpath-root 3;
            }
            tailf:cli-diff-dependency "../../../../vrf/definition" {
              tailf:xpath-root 3;
            }
            type string {
              tailf:info
                "WORD;;VPN Routing/Forwarding instance name";
            }
          }
          uses sntp-server-grouping;
        }
      }
      container broadcast {
        tailf:info
          "Configure SNTP broadcast services";
        leaf client {
          tailf:info
            "Enable SNTP broadcast client mode";
          type empty;
        }
      }
      container multicast {
        tailf:info
          "Configure SNTP multicast services";
        container client {
          tailf:info
            "Enable SNTP multicast client mode";
          tailf:cli-delete-when-empty;
          tailf:cli-reset-container;
          presence "true";
          leaf address {
            tailf:cli-drop-node-name;
            type union {
              type inet:ipv4-address {
                tailf:info
                  "A.B.C.D;;Multicast client IP address";
              }
              type inet:ipv6-address {
                tailf:info
                  "X:X:X:X::X;;Multicast client IPv6 address";
              }
            }
          }
        }
      }
      container source-interface {
        tailf:info
          "Configure interface for source address";
        uses interface-name-grouping;
      }
    }
    container ptp {
      tailf:ncs-device-type "cli-ned";
      tailf:display-when "not(../../ncs:module) or ../../ncs:module[ncs:name='tailf-ned-cisco-ios']";
      tailf:info
        "Precision Time Protocol";
      container clock {
        tailf:info
          "Configure PTP clock";
        list profile {
          tailf:info
            "Create a PTP Clock Profile";
          tailf:cli-mode-name "config-ptp";
          key "id";
          leaf id {
            type uint8 {
              tailf:info
                "<0-63>;;RPD PTP Ds Domain Number";
              range "0..63";
            }
          }
          container clock-source1 {
            tailf:info
              "Clock Source";
            tailf:cli-compact-syntax;
            tailf:cli-sequence-commands;
            leaf address {
              tailf:cli-drop-node-name;
              tailf:cli-incomplete-command;
              type inet:ipv4-address {
                tailf:info
                  "A.B.C.D;;Source IP addr";
              }
            }
            leaf gw {
              tailf:info
                "Clock Source Gateway";
              type inet:ipv4-address {
                tailf:info
                  "A.B.C.D;;Source Gateway addr";
              }
            }
          }
        }
        container ordinary {
          tailf:info
            "Configure PTP Ordinary clock";
          list domain {
            tailf:info
              "PTP domain";
            tailf:cli-mode-name "config-ptp-clk";
            key "id";
            max-elements 1;
            leaf id {
              type uint8 {
                tailf:info
                  "<0-127>;;Domain number";
                range "0..127";
              }
            }
            leaf hybrid {
              tailf:info
                "Hybrid Mode";
              tailf:cli-hide-in-submode;
              type empty;
            }
            leaf priority1 {
              tailf:info
                "Set priority1";
              tailf:cli-full-command;
              type uint8 {
                tailf:info
                  "<0-255>;;Priority1";
                range "0..255";
              }
            }
            leaf priority2 {
              tailf:info
                "Set priority2";
              tailf:cli-full-command;
              type uint8 {
                tailf:info
                  "<0-255>;;Priority2";
                range "0..255";
              }
            }
            container time-properties {
              tailf:info
                "Set the PTP timePropertiesDS";
              container gps {
                tailf:cli-compact-syntax;
                tailf:cli-sequence-commands {
                  tailf:cli-reset-siblings;
                }
                leaf timeScale {
                  tailf:cli-drop-node-name;
                  tailf:cli-incomplete-command;
                  type enumeration {
                    enum "timeScaleFALSE" {
                      tailf:info
                        "Set the timepropertiesDS.timeScale to FALSE";
                    }
                    enum "timeScaleTRUE" {
                      tailf:info
                        "Set the timepropertiesDS.timeScale to TRUE";
                    }
                  }
                }
                leaf currentUtcOffsetValid {
                  tailf:cli-drop-node-name;
                  tailf:cli-incomplete-command;
                  type enumeration {
                    enum "currentUtcOffsetValidFALSE" {
                      tailf:info
                        "Set the timepropertiesDS.currentUtcOffsetValidto FALSE";
                    }
                    enum "currentUtcOffsetValidTRUE" {
                      tailf:info
                        "Set the timepropertiesDS.currentUtcOffsetValidto TRUE";
                    }
                  }
                }
                leaf leap59 {
                  tailf:cli-drop-node-name;
                  tailf:cli-incomplete-command;
                  type enumeration {
                    enum "leap59FALSE" {
                      tailf:info
                        "Set the timepropertiesDS.leap59 to FALSE";
                    }
                    enum "leap59TRUE" {
                      tailf:info
                        "Set the timepropertiesDS.leap59 to TRUE";
                    }
                  }
                }
                leaf leap61 {
                  tailf:cli-drop-node-name;
                  tailf:cli-incomplete-command;
                  type enumeration {
                    enum "leap61FALSE" {
                      tailf:info
                        "Set the timepropertiesDS.leap61 to FALSE";
                    }
                    enum "leap61TRUE" {
                      tailf:info
                        "Set the timepropertiesDS.leap61 to TRUE";
                    }
                  }
                }
                leaf currentUtcOffset {
                  tailf:cli-drop-node-name;
                  type uint16 {
                    tailf:info
                      "<0-1000>;;Set the timepropertiesDS.currentUtcOffset (in seconds)";
                    range "0..1000";
                  }
                }
              }
            }
            list clock-port {
              tailf:info
                "Configure clock port";
              tailf:cli-mode-name "config-ptp-port";
              key "name mode";
              leaf name {
                type string {
                  tailf:info
                    "WORD;;Port name";
                }
              }
              leaf mode {
                type enumeration {
                  enum "master" {
                    tailf:info
                      "Configure as Master";
                  }
                  enum "slave" {
                    tailf:info
                      "Configure as Slave";
                  }
                }
              }
              leaf profile {
                tailf:info
                  "PTP profile";
                tailf:cli-hide-in-submode;
                type enumeration {
                  enum "g8265.1" {
                    tailf:info
                      "Telecom Profile ITU-T G.8265.1";
                  }
                }
              }
              container transport {
                tailf:info
                  "Set port transport parameters";
                tailf:cli-compact-syntax;
                tailf:cli-sequence-commands {
                  tailf:cli-reset-siblings;
                }
                leaf proto {
                  tailf:cli-drop-node-name;
                  tailf:cli-incomplete-command;
                  type enumeration {
                    enum "ethernet" {
                      tailf:info
                        "Use Ethernet encapsulation";
                    }
                    enum "ipv4" {
                      tailf:info
                        "Use IPv4 encapsulation";
                    }
                  }
                }
                leaf unicast {
                  tailf:info
                    "Use unicast communication channel";
                  type empty;
                }
                leaf interface {
                  tailf:info
                    "Transport interface";
                  when "../proto = 'ipv4'" {
                    tailf:xpath-root 3;
                    tailf:dependency "../proto";
                  }
                  type string {
                    tailf:info
                      "WORD;;Abbreviated interface name";
                  }
                }
                leaf negotiation {
                  tailf:info
                    "Enable unicast negotiation";
                  type empty;
                }
              }
              container clock {
                tailf:info
                  "Set clock parameters";
                leaf source {
                  tailf:info
                    "Local clock address";
                  type string {
                    tailf:info
                      "WORD;;MAC/IP address";
                  }
                }
              }
            }
          }
        }
      }
    }
    container mac-address-table {
      tailf:ncs-device-type "cli-ned";
      tailf:display-when "not(../../ncs:module) or ../../ncs:module[ncs:name='tailf-ned-cisco-ios']";
      tailf:info
        "Configure the MAC address table";
      container notification {
        tailf:info
          "Enable a Notification feature";
        leaf mac-move {
          tailf:info
            "Enable Mac Move Notification";
          type empty;
        }
      }
      container move {
        tailf:info
          "Move keyword";
        container update {
          tailf:info
            "Notification keyword";
          leaf transmit {
            tailf:info
              "Transmit keyword";
            type empty;
          }
          leaf receive {
            tailf:info
              "Receive keyword";
            type empty;
          }
        }
      }
      container synchronize {
        tailf:info
          "Synchronize MAC address table entries in the system";
        tailf:cli-display-separated;
        presence "true";
        leaf activity-time {
          tailf:info
            "Set activity time for MAC entry synchronization";
          type uint16 {
            tailf:info
              "<0-1275>;;Enter time in seconds <160, 320, 640>";
          }
        }
      }
      container aging-type {
        tailf:info
          "Enable routed MAC entries aging";
        leaf routed-mac {
          tailf:info
            "Enable routed MAC entries aging";
          tailf:cli-boolean-no;
          type boolean;
          default "true";
        }
      }
      leaf aging-time {
        tailf:info
          "Set MAC address table entry maximum age";
        tailf:cli-full-command;
        type union {
          type uint32 {
            tailf:info
              "<0-0>;;Enter 0 to disable aging";
            range "0";
          }
          type uint32 {
            tailf:info
              "<10-1000000>;;Aging time in seconds";
            range "10..1000000";
          }
        }
      }
      container againg-time-routed-mac {
        tailf:cli-drop-node-name;
        container aging-time {
          tailf:info
            "Set MAC address table entry maximum age";
          tailf:cli-compact-syntax;
          tailf:cli-sequence-commands {
            tailf:cli-reset-siblings;
          }
          tailf:cli-incomplete-command;
          tailf:cli-incomplete-no;
          leaf speed {
            tailf:cli-drop-node-name;
            tailf:cli-incomplete-command;
            tailf:cli-incomplete-no;
            type union {
              type uint32 {
                tailf:info
                  "<0-0>;;Enter 0 to disable aging";
                range "0";
              }
              type uint32 {
                tailf:info
                  "<10-1000000>;;Aging time in seconds";
                range "10..1000000";
              }
            }
          }
          leaf routed-mac {
            tailf:info
              "Set RM Aging interval";
            tailf:cli-full-command;
            type empty;
          }
        }
      }
      container limit {
        tailf:info
          "Enter parameters for mac limit feature";
        list vlan {
          tailf:cli-suppress-mode;
          tailf:cli-delete-when-empty;
          tailf:cli-compact-syntax;
          key "id";
          leaf id {
            type uint16 {
              tailf:info
                "<1-4094>;;Enter VLAN Number";
              range "1..4094";
            }
          }
          leaf maximum {
            tailf:info
              "Enter max allowed entries";
            tailf:cli-no-name-on-delete;
            tailf:cli-no-value-on-delete;
            type uint16 {
              tailf:info
                "<5-16000>;;Max allowed entries";
            }
          }
          leaf action {
            tailf:info
              "Enter action";
            tailf:cli-no-name-on-delete;
            tailf:cli-no-value-on-delete;
            type enumeration {
              enum "warning";
              enum "limit";
              enum "shutdown";
            }
          }
          leaf flood {
            tailf:info
              "Disable flooding on this vlan";
            tailf:cli-no-name-on-delete;
            type empty;
          }
        }
        list bdomain {
          tailf:cli-suppress-mode;
          tailf:cli-delete-when-empty;
          tailf:cli-compact-syntax;
          key "id";
          leaf id {
            type uint16;
          }
          leaf maximum {
            tailf:info
              "Enter max allowed entries";
            type uint16 {
              tailf:info
                "<5-16000>;;Max allowed entries";
            }
          }
          leaf action {
            tailf:info
              "Enter action";
            type enumeration {
              enum "warning";
              enum "limit";
              enum "shutdown";
            }
          }
          leaf flood {
            tailf:info
              "Disable flooding on this vlan";
            type empty;
          }
        }
      }
      container learning {
        tailf:info
          "Enable a MAC table learning feature";
        container vlan {
          tailf:info
            "Layer 2 table learning per VLAN";
          list no-list {
            tailf:info
              "'no mac-address-table learning vlan' entry";
            tailf:cli-suppress-mode;
            tailf:cli-delete-when-empty;
            key "id";
            leaf id {
              type uint16 {
                tailf:info
                  "<1-4094>;;VLAN ID";
                range "1..4094";
              }
            }
            leaf module {
              tailf:info
                "Layer 2 table learning per VLAN per module";
              type uint8 {
                tailf:info
                  "<1-9>;;Module";
                range "1..9";
              }
            }
          }
        }
      }
    }
    container mac {
      tailf:ncs-device-type "cli-ned";
      tailf:display-when "not(../../ncs:module) or ../../ncs:module[ncs:name='tailf-ned-cisco-ios']";
      tailf:info
        "Global MAC configuration subcommands";
      container access-list {
        tailf:info
          "Named access-list";
        list extended {
          tailf:info
            "Extended Access List";
          tailf:cli-mode-name "config-ext-macl";
          tailf:cli-full-command;
          tailf:cli-explicit-exit;
          key "id";
          leaf id {
            type string {
              tailf:info
                "WORD;;access-list name";
            }
          }
          list entry {
            tailf:cli-drop-node-name;
            tailf:cli-suppress-mode;
            tailf:cli-delete-when-empty;
            tailf:cli-compact-syntax;
            tailf:cli-show-long-obu-diffs;
            ordered-by user;
            key "rule";
            leaf rule {
              tailf:cli-drop-node-name;
              tailf:cli-multi-word-key;
              type string {
                tailf:info
                  "deny;;Specify packets to reject
                   permit;;Specify packets to forwards";
                pattern '(permit .*)|(deny .*)';
              }
            }
          }
        }
      }
      container address-table {
        tailf:info
          "Configure the MAC address table";
        leaf aging-time {
          tailf:info
            "Set MAC address table entry maximum age";
          type union {
            type uint32 {
              tailf:info
                "<0-0>;;Enter 0 to disable aging";
              range "0";
            }
            type uint32 {
              tailf:info
                "<10-1000000>;;Aging time in seconds";
              range "10..1000000";
            }
          }
        }
        container notification {
          tailf:info
            "Enable/Disable MAC Notification on the switch";
          leaf change {
            tailf:info
              "Enable/Disable MAC Notification feature on the switch";
            type empty;
          }
          leaf mac-move {
            tailf:info
              "Enable Mac Move Notification";
            type empty;
          }
        }
        container move {
          tailf:info
            "Move keyword";
          container update {
            tailf:info
              "Notification keyword";
            leaf transmit {
              tailf:info
                "Transmit keyword";
              type empty;
            }
            leaf receive {
              tailf:info
                "Receive keyword";
              type empty;
            }
          }
        }
      }
    }
    container privilege {
      tailf:ncs-device-type "cli-ned";
      tailf:display-when "not(../../ncs:module) or ../../ncs:module[ncs:name='tailf-ned-cisco-ios']";
      tailf:info
        "Command privilege parameters";
      container exec {
        tailf:info
          "Exec mode";
        list level {
          tailf:info
            "Set privilege level of command";
          tailf:cli-suppress-mode;
          tailf:cli-delete-when-empty;
          tailf:cli-compact-syntax;
          tailf:cli-incomplete-command;
          tailf:cli-no-key-completion;
          key "privilege";
          leaf privilege {
            tailf:cli-incomplete-command;
            tailf:cli-incomplete-no;
            tailf:cli-suppress-range;
            type uint8 {
              tailf:info
                "<0-15>;;Privilege level";
            }
          }
          list command-list {
            tailf:cli-suppress-mode;
            tailf:cli-delete-when-empty;
            tailf:cli-drop-node-name;
            tailf:cli-compact-syntax;
            tailf:cli-show-long-obu-diffs;
            tailf:cli-no-key-completion;
            tailf:cli-suppress-key-abbreviation;
            tailf:cli-no-match-completion;
            ordered-by user;
            key "command";
            leaf command {
              tailf:cli-drop-node-name;
              tailf:cli-multi-word-key;
              type string {
                tailf:info
                  "LINE;;Initial keywords of the command to modify";
              }
            }
          }
        }
      }
    }
    container spanning-tree {
      tailf:ncs-device-type "cli-ned";
      tailf:display-when "not(../../ncs:module) or ../../ncs:module[ncs:name='tailf-ned-cisco-ios']";
      tailf:info
        "Spanning Tree Subsystem";
      container etherchannel {
        tailf:info
          "Spanning tree etherchannel specific configuration";
        container guard {
          tailf:info
            "Configure guard features for etherchannel";
          leaf misconfig {
            tailf:info
              "Enable guard to protect against etherchannel misconfiguration";
            type empty;
          }
        }
      }
      container extend {
        tailf:info
          "Spanning Tree 802.1t extensions";
        leaf system-id {
          tailf:info
            "Extend system-id into priority portion of the bridge id (PVST & Rapid PVST only)";
          type empty;
        }
      }
      container loopguard {
        tailf:info
          "Spanning tree loopguard options";
        leaf default {
          tailf:info
            "Enable loopguard by default on all ports";
          type empty;
        }
      }
      container mst {
        tailf:info
          "Multiple spanning tree configuration";
        list instance-range {
          tailf:cli-drop-node-name;
          tailf:cli-suppress-mode;
          tailf:cli-delete-when-empty;
          tailf:cli-incomplete-command;
          tailf:cli-range-list-syntax;
          tailf:meta-data "range-list-syntax" {
            tailf:meta-value "spanning-tree mst <ID> $3";
          }
          key "id";
          leaf id {
            type uint16 {
              tailf:info
                "<0-4094>;;MST instance id";
              range "0..4094";
            }
          }
          leaf priority {
            tailf:info
              "Set the bridge priority for the spanning tree";
            type uint16 {
              tailf:info
                "<0-61440>;;bridge priority in increments of 4096";
              range "0..61440";
            }
          }
        }
        container configuration {
          tailf:info
            "Enter MST configuration submode";
          tailf:cli-add-mode;
          tailf:cli-mode-name "config-mst";
          leaf revision {
            tailf:info
              "Set configuration revision number";
            tailf:cli-full-command;
            type uint16 {
              tailf:info
                "<0-65535>;;Configuration revision number";
            }
          }
          leaf name {
            tailf:info
              "Set configuration name";
            tailf:cli-full-command;
            type string {
              tailf:info
                "WORD;;Configuration name";
            }
          }
          list instance {
            tailf:info
              "Map vlans to an MST instance";
            tailf:cli-suppress-mode;
            tailf:cli-delete-when-empty;
            tailf:cli-incomplete-command;
            key "id";
            leaf id {
              type uint16 {
                tailf:info
                  "<0-4094>;;MST instance id";
                range "0..4094";
              }
            }
            leaf-list vlan {
              tailf:info
                "Range of vlans to add to the instance mapping";
              tailf:cli-range-list-syntax;
              type uint16 {
                tailf:info
                  "LINE;;vlan range ex: 1-65, 72, 300 -200";
              }
            }
          }
        }
        leaf forward-time {
          tailf:info
            "Set the forward delay for the spanning tree";
          type uint8 {
            tailf:info
              "<4-30>;;number of seconds for the forward delay timer";
            range "4..30";
          }
        }
      }
      container optimize {
        container bpdu {
          tailf:info
            "Optimize BPDU Handling";
          leaf transmission {
            tailf:info
              "Optimize transmission of BPDUs";
            tailf:cli-boolean-no;
            type boolean;
            default "true";
          }
        }
      }
      container portfast {
        tailf:info
          "Spanning tree portfast options";
        uses spanning-tree-portfast-grouping;
        container edge {
          uses spanning-tree-portfast-grouping;
        }
      }
      container uplinkfast-conf {
        tailf:cli-drop-node-name;
        container uplinkfast {
          tailf:info
            "Enable UplinkFast Feature";
          tailf:cli-incomplete-command;
          tailf:cli-incomplete-no;
          leaf max-update-rate {
            tailf:info
              "Rate at which station address updates are sent";
            type uint16 {
              tailf:info
                "<0-32000>;;Maximum number of update packets per second";
              range "0..32000";
            }
          }
        }
      }
      leaf uplinkfast {
        tailf:info
          "Enable UplinkFast Feature";
        tailf:cli-full-command;
        type empty;
      }
      container pathcost {
        tailf:info
          "Spanning tree pathcost options";
        leaf method {
          tailf:info
            "Method to calculate default port path cost";
          type enumeration {
            enum "long" {
              tailf:info
                "Use 32 bit based values for default port path costs";
            }
            enum "short" {
              tailf:info
                "Use 16 bit based values for default port path costs";
            }
          }
          default "short";
        }
      }
      leaf mode {
        tailf:info
          "Spanning tree operating mode";
        tailf:cli-full-command;
        type enumeration {
          enum "mst" {
            tailf:info
              "Multiple spanning tree mode";
          }
          enum "pvst" {
            tailf:info
              "Per-Vlan spanning tree mode";
          }
          enum "rapid-pvst" {
            tailf:info
              "Per-Vlan rapid spanning tree mode";
          }
        }
      }
      container vlan {
        tailf:info
          "VLAN Switch Spanning Tree";
        list no-list {
          tailf:info
            "'no spanning-tree vlan' list entry";
          tailf:cli-suppress-mode;
          tailf:cli-delete-when-empty;
          tailf:cli-range-list-syntax;
          tailf:meta-data "range-list-syntax" {
            tailf:meta-value "spanning-tree vlan no-list <ID>";
          }
          key "id";
          leaf id {
            type uint16 {
              tailf:info
                "<1-4094>;;Spanning tree VLAN id";
              range "1..4094";
            }
          }
        }
        list vlan-list {
          tailf:cli-drop-node-name;
          tailf:cli-suppress-mode;
          tailf:cli-delete-when-empty;
          tailf:cli-range-list-syntax;
          tailf:cli-incomplete-command;
          tailf:cli-incomplete-no;
          tailf:meta-data "range-list-syntax" {
            tailf:meta-value "spanning-tree vlan <ID> $3 $4";
          }
          key "id";
          leaf id {
            type uint16 {
              tailf:info
                "WORD;;vlan range, example: 1,3-5,7,9-11";
              range "1..4096";
            }
          }
          leaf hello-time {
            tailf:info
              "Set the hello interval for the spanning tree";
            type uint8 {
              tailf:info
                "<1-10>;;number of seconds between generation of config BPDUs";
              range "1..10";
            }
          }
          leaf priority {
            tailf:info
              "Set the bridge priority for the spanning tree";
            type uint16 {
              tailf:info
                "<0-65535>;;bridge priority";
            }
          }
          leaf forward-time {
            tailf:info
              "Set the forward delay for the spanning tree";
            type uint8 {
              tailf:info
                "<4-30>;;number of seconds for the forward delay timer";
              range "4..30";
            }
          }
          leaf max-age {
            tailf:info
              "Set the max age interval for the spanning tree";
            type uint8 {
              tailf:info
                "<6-40>;;maximum number of seconds the information in a BPDU is valid";
              range "6..40";
            }
          }
        }
      }
    }
    container dot1x {
      tailf:ncs-device-type "cli-ned";
      tailf:display-when "not(../../ncs:module) or ../../ncs:module[ncs:name='tailf-ned-cisco-ios']";
      tailf:info
        "IEEE 802.1X Global Configuration Commands";
      container critical {
        tailf:info
          "Set 802.1x Critical Authentication parameters";
        leaf eapol {
          tailf:info
            "Send EAPOL-Success on successful Critical Authentication";
          type empty;
        }
        container recovery {
          tailf:info
            "Set 802.1x Critical Authentication Recovery parameters";
          leaf delay {
            tailf:info
              "Set 802.1x Critical Authentication Recovery Delay period";
            type uint16 {
              tailf:info
                "<1-10000>;;802.1x Critical Authentication Recovery delay in milliseconds";
              range "1..10000";
            }
          }
        }
      }
      leaf system-auth-control {
        tailf:info
          "Enable or Disable SysAuthControl";
        type empty;
      }
    }
    container power {
      tailf:ncs-device-type "cli-ned";
      tailf:display-when "not(../../ncs:module) or ../../ncs:module[ncs:name='tailf-ned-cisco-ios']";
      tailf:info
        "Power configure";
      leaf redundancy-mode {
        tailf:info
          "set power supply redundancy mode";
        type enumeration {
          enum "combined" {
            tailf:info
              "combine power supply outputs (no redundancy)";
          }
          enum "redundant" {
            tailf:info
              "either power supply can operate system (redundancy)";
          }
        }
      }
    }
    container power-supply {
      tailf:ncs-device-type "cli-ned";
      tailf:display-when "not(../../ncs:module) or ../../ncs:module[ncs:name='tailf-ned-cisco-ios']";
      container dual {
        tailf:cli-delete-when-empty;
        presence "true";
        leaf dc-feed {
          type empty;
        }
      }
    }
    container parameter-map {
      tailf:ncs-device-type "cli-ned";
      tailf:display-when "not(../../ncs:module) or ../../ncs:module[ncs:name='tailf-ned-cisco-ios']";
      tailf:info
        "parameter map";
      container type {
        tailf:info
          "parameter map type";
        container inspect-global {
          tailf:info
            "Global Parameter Map Configuration";
          tailf:cli-add-mode;
          tailf:cli-mode-name "config-profile";
          uses parameter-map-grouping;
        }
        list inspect {
          tailf:info
            "inspect parameter-map";
          tailf:cli-mode-name "config-profile";
          key "name";
          leaf name {
            type string {
              tailf:info
                "WORD;;parameter-map name";
            }
          }
          uses parameter-map-grouping;
        }
        list inspect-vrf {
          tailf:info
            "inspect vrf parameter-map";
          tailf:cli-mode-name "config-profile";
          key "name";
          leaf name {
            type string {
              tailf:info
                "WORD;;parameter-map name";
            }
          }
          uses parameter-map-grouping;
        }
        list inspect-zone {
          tailf:info
            "inspect zone parameter-map";
          tailf:cli-mode-name "config-profile";
          key "name";
          leaf name {
            type string {
              tailf:info
                "WORD;;parameter-map name";
            }
          }
          uses parameter-map-grouping;
        }
        list regex {
          tailf:info
            "regex parameter-map";
          tailf:cli-mode-name "config-profile";
          key "name";
          leaf name {
            type string {
              tailf:info
                "WORD;;parameter-map name";
            }
          }
          list pattern {
            tailf:info
              "Configure pattern to match";
            tailf:cli-suppress-mode;
            tailf:cli-delete-when-empty;
            key "regexp";
            leaf regexp {
              type string {
                tailf:info
                  "WORD;;Specify the regex pattern";
              }
            }
          }
        }
      }
    }
    container vpdn {
      tailf:ncs-device-type "cli-ned";
      tailf:display-when "not(../../ncs:module) or ../../ncs:module[ncs:name='tailf-ned-cisco-ios']";
      tailf:info
        "Virtual Private Dialup Network";
      leaf authen-before-forward {
        tailf:info
          "Authenticate a user locally before tunnelling";
        type empty;
      }
      leaf enable {
        tailf:info
          "Enable VPDN";
        type empty;
      }
      leaf-list search-order {
        ordered-by user;
        tailf:info
          "Configure the order to search different VPDN tunnel types";
        type enumeration {
          enum "dnis" {
            tailf:info
              "Tunnel based on DNIS";
          }
          enum "domain" {
            tailf:info
              "Tunnel based on domain";
          }
          enum "multihop-hostname" {
            tailf:info
              "Tunnel based on peer hostname from ingress tunnel";
          }
        }
      }
    }
    list vpdn-group {
      tailf:ncs-device-type "cli-ned";
      tailf:display-when "not(../ncs:module) or ../ncs:module[ncs:name='tailf-ned-cisco-ios']";
      tailf:info
        "VPDN group configuration";
      key "name";
      leaf name {
        tailf:cli-diff-dependency "../../vpdn/enable" {
          tailf:xpath-root 3;
        }
        type string {
          tailf:info
            "WORD;;VPDN Group name";
        }
      }
      container accept-dialin {
        tailf:info
          "VPDN accept-dialin group configuration";
        tailf:cli-add-mode;
        tailf:cli-mode-name "config-vpdn-acc-in";
        leaf protocol {
          tailf:info
            "Tunneling protocol to be used";
          tailf:cli-no-value-on-delete;
          tailf:cli-remove-before-change;
          type enumeration {
            enum "any" {
              tailf:info
                "Use any protocol";
            }
            enum "l2tp" {
              tailf:info
                "Use L2TP";
            }
            enum "pptp" {
              tailf:info
                "Use PPTP";
            }
          }
        }
        leaf virtual-template {
          tailf:info
            "Virtual template to clone from";
          tailf:non-strict-leafref {
            path "../../../interface/Virtual-Template/name";
          }
          type uint16 {
            range "1..4095";
          }
        }
      }
      leaf description {
        tailf:info
          "Description for this VPDN group";
        tailf:cli-multi-value;
        tailf:cli-preformatted;
        tailf:cli-full-command;
        type string {
          tailf:info
            "LINE;;Description of vpdn-group (up to 60 characters)";
          length "1..60";
        }
      }
      leaf dsl-line-info-forwarding {
        tailf:info
          "Forward DSL Line Info attributes";
        type empty;
      }
      leaf force-local-chap {
        tailf:info
          "Force a CHAP challenge to be instigated locally";
        type empty;
      }
      container ip {
        tailf:info
          "IP settings for tunnel";
        leaf mtu {
          tailf:info
            "Set IP MTU settings";
          tailf:cli-full-command;
          type enumeration {
            enum "adjust" {
              tailf:info
                "Automatically adjust IP MTU for virtual-access";
            }
          }
        }
        leaf pmtu {
          tailf:info
            "Enable PMTU for tunnel";
          tailf:cli-full-command;
          type empty;
        }
        leaf precedence {
          tailf:info
            "Set IP Precedence value for tunneled traffic";
          tailf:cli-full-command;
          type enumeration {
            enum "critical" {
              tailf:info
                "Set critical precedence (5)";
            }
            enum "flash" {
              tailf:info
                "Set flash precedence (3)";
            }
            enum "flash-override" {
              tailf:info
                "Set flash override precedence (4)";
            }
            enum "immediate" {
              tailf:info
                "Set immediate precedence (2)";
            }
            enum "internet" {
              tailf:info
                "Set internetwork control precedence (6)";
            }
            enum "network" {
              tailf:info
                "Set network control precedence (7)";
            }
            enum "priority" {
              tailf:info
                "Set priority precedence (1)";
            }
            enum "routine" {
              tailf:info
                "Set routine precedence (0)";
            }
          }
          default "routine";
        }
        leaf tos {
          tailf:info
            "Set IP ToS value for tunneled traffic";
          tailf:cli-full-command;
          type union {
            type uint8 {
              range "3|5|9..15";
            }
            type enumeration {
              enum "max-reliability" {
                tailf:info
                  "Set max reliable ToS (2)";
              }
              enum "max-throughput" {
                tailf:info
                  "Set max throughput ToS (4)";
              }
              enum "min-delay" {
                tailf:info
                  "Set min delay ToS (8)";
              }
              enum "min-monetary-cost" {
                tailf:info
                  "Set min monetary cost ToS (1)";
              }
              enum "normal" {
                tailf:info
                  "Set normal ToS (0)";
              }
              enum "reflect" {
                tailf:info
                  "Reflect IP payload ToS on tunnel";
              }
            }
          }
          default "normal";
        }
      }
      container l2tp {
        tailf:info
          "L2TP specific commands";
        tailf:cli-diff-dependency "../accept-dialin/protocol" {
          tailf:xpath-root 3;
        }
        when "not(../accept-dialin/protocol='pptp')" {
          tailf:xpath-root 3;
          tailf:dependency "../accept-dialin/protocol";
        }
        container attribute {
          tailf:info
            "Configure AVP options";
          container clid {
            tailf:info
              "Options to apply on Calling Station Id";
            tailf:cli-compact-syntax;
            tailf:cli-sequence-commands {
              tailf:cli-reset-siblings;
            }
            container mask-method {
              tailf:info
                "Mask characters by method";
              container remove {
                tailf:info
                  "Remove CLID";
                presence "true";
                leaf match {
                  tailf:info
                    "Apply options only on substring match of username";
                  tailf:cli-full-command;
                  type string {
                    tailf:info
                      "WORD;;Substring of username";
                  }
                }
              }
              container right {
                tailf:info
                  "Mask from the right side";
                tailf:cli-compact-syntax;
                tailf:cli-sequence-commands {
                  tailf:cli-reset-siblings;
                }
                leaf character {
                  tailf:info
                    "CHAR;;Character used for masking";
                  tailf:cli-drop-node-name;
                  tailf:cli-incomplete-command;
                  type string {
                    length "1";
                  }
                }
                leaf bytes {
                  tailf:info
                    "<0-255>;;Number of bytes to mask";
                  tailf:cli-drop-node-name;
                  type uint8;
                }
                leaf match {
                  tailf:info
                    "Apply options only on substring match of username";
                  type string {
                    tailf:info
                      "WORD;;Substring of username";
                  }
                }
              }
            }
          }
        }
        leaf drop {
          tailf:info
            "Drop packets under certain conditions";
          tailf:cli-full-command;
          type enumeration {
            enum "out-of-order" {
              tailf:info
                "Drop out of order data packets";
            }
          }
        }
        leaf hidden {
          tailf:info
            "Allow AVPs to be hidden";
          tailf:cli-full-command;
          type empty;
        }
        leaf ignore {
          tailf:info
            "Ignore certain AVP values";
          tailf:cli-full-command;
          type enumeration {
            enum "tx-speed" {
              tailf:info
                "L2TPv2 AVP#24: Connect Speed";
            }
          }
        }
        container ip {
          tailf:info
            "IP specific commands";
          leaf udp {
            tailf:info
              "udp;;UDP specific commands";
            type enumeration {
              enum "checksum" {
                tailf:info
                  "perform checksum on data packets";
              }
            }
          }
        }
        container rx-speed {
          tailf:info
            "l2tp receive speed";
          tailf:cli-compact-syntax;
          tailf:cli-sequence-commands {
            tailf:cli-reset-siblings;
          }
          leaf ANCP {
            tailf:info
              "rx-speed source ANCP";
            tailf:cli-optional-in-sequence;
            type empty;
          }
          leaf RAM-min {
            tailf:info
              "rx-speed source Rate Adaptive Mode - Minimum";
            tailf:cli-optional-in-sequence;
            when "not(../ANCP)" {
              tailf:xpath-root 3;
              tailf:dependency "../ANCP";
            }
            type empty;
          }
          leaf rx-speed {
            tailf:info
              "<0-2147483>;;value of rx-speed in kbps";
            tailf:cli-drop-node-name;
            type uint32 {
              range "0..2147483";
            }
          }
        }
        leaf sequencing {
          tailf:info
            "Enable sequencing";
          tailf:cli-full-command;
          type empty;
        }
        container tunnel {
          tailf:info
            "L2TP tunnel commands";
          leaf authentication {
            tailf:info
              "Authenticate tunnel";
            tailf:cli-full-command;
            type empty;
          }
          container bearer {
            tailf:info
              "Bearer attributes";
            leaf capabilities {
              tailf:info
                "AVP#4 : Bearer capabilities";
              type enumeration {
                enum "all" {
                  tailf:info
                    "All bearer types";
                }
                enum "analog" {
                  tailf:info
                    "Analog bearer type";
                }
                enum "digital" {
                  tailf:info
                    "Digital bearer type";
                }
                enum "none" {
                  tailf:info
                    "No bearer type";
                }
              }
            }
          }
          container busy {
            tailf:info
              "Busy list commands";
            leaf timeout {
              tailf:info
                "Busy list timeout length";
              type uint16 {
                tailf:info
                  "<5-6000>;;Seconds";
                range "5..6000";
              }
            }
          }
          container framing {
            tailf:info
              "Framing attributes";
            leaf capabilities {
              tailf:info
                "AVP#3: Framing capabilities";
              type enumeration {
                enum "all" {
                  tailf:info
                    "All framing types";
                }
                enum "asynchronous" {
                  tailf:info
                    "Asynchronous framing";
                }
                enum "none" {
                  tailf:info
                    "No framing";
                }
                enum "synchronous" {
                  tailf:info
                    "Synchronous framing";
                }
              }
            }
          }
          leaf hello {
            tailf:info
              "Hello packet interval";
            type uint16 {
              tailf:info
                "<0-1000>;;seconds, default is 60";
              range "0..1000";
            }
            default "60";
          }
          container password {
            tailf:info
              "Tunnel password for authentication and/or AVP hiding";
            tailf:cli-compact-syntax;
            tailf:cli-sequence-commands;
            uses password-grouping;
          }
          leaf receive-window {
            tailf:info
              "Receive window size for control channel";
            tailf:cli-full-command;
            type uint16 {
              tailf:info
                "<1-8192>;;Number of packets";
              range "1..8192";
            }
          }
          leaf resync {
            tailf:info
              "Number of unacknowledged packets sent to the peer for SSO";
            tailf:cli-full-command;
            type uint16 {
              tailf:info
                "<1-1024>;;Number of packets";
              range "1..1024";
            }
          }
          container retransmit {
            tailf:info
              "Control packet retransmission parameters";
            container initial {
              tailf:info
                "SCCRQ control retries/timeout settings";
              leaf retries {
                tailf:info
                  "Number of initial retries before placing LNS on busy list";
                tailf:cli-full-command;
                type uint16 {
                  tailf:info
                    "<1-1000>;;Maximum SCCRQ retransmissions";
                  range "1..1000";
                }
              }
              container timeout {
                tailf:info
                  "SCCRQ retransmission timeout parameters";
                leaf max {
                  tailf:info
                    "Maximum timeout";
                  tailf:cli-full-command;
                  type uint8 {
                    range "0..8";
                  }
                }
                leaf min {
                  tailf:info
                    "Minimum timeout";
                  tailf:cli-full-command;
                  type uint8 {
                    range "0..8";
                  }
                }
              }
            }
            leaf retries {
              tailf:info
                "Number of retries before tearing down a tunnel";
              tailf:cli-full-command;
              type uint16 {
                tailf:info
                  "<5-1000>;;Maximum retransmissions";
                range "5..1000";
              }
            }
            container timeout {
              tailf:info
                "Control packet retransmission timeout parameters";
              leaf max {
                tailf:info
                  "Maximum timeout";
                tailf:cli-full-command;
                type uint8 {
                  range "0..8";
                }
              }
              leaf min {
                tailf:info
                  "Minimum timeout";
                tailf:cli-full-command;
                type uint8 {
                  range "0..8";
                }
              }
            }
          }
          container timeout {
            tailf:info
              "Tunnel timeout values";
            leaf no-session {
              tailf:info
                "No-session timeout for tunnel";
              tailf:cli-full-command;
              type union {
                type uint32 {
                  tailf:info
                    "<0-86400>;;Timeout in seconds";
                  range "0..86400";
                }
                type enumeration {
                  enum "never" {
                    tailf:info
                      "Never timeout";
                  }
                }
              }
            }
            leaf setup {
              tailf:info
                "Time permitted to setup a tunnel";
              tailf:cli-full-command;
              type uint16 {
                tailf:info
                  "<60-6000>;;Timeout in seconds";
                range "60..6000";
              }
            }
          }
          container zlb {
            tailf:info
              "Tunnel ZLB options";
            leaf delay {
              tailf:info
                "<1-5>;;Delay in seconds";
              type uint8 {
                range "1..5";
              }
            }
          }
        }
        container tx-speed {
          tailf:info
            "l2tp transmit speed";
          tailf:cli-compact-syntax;
          tailf:cli-sequence-commands {
            tailf:cli-reset-siblings;
          }
          leaf ANCP {
            tailf:info
              "tx-speed source ANCP";
            tailf:cli-optional-in-sequence;
            type empty;
          }
          leaf RAM-min {
            tailf:info
              "tx-speed source Rate Adaptive Mode - Minimum";
            tailf:cli-optional-in-sequence;
            when "not(../ANCP)" {
              tailf:xpath-root 3;
              tailf:dependency "../ANCP";
            }
            type empty;
          }
          leaf tx-speed {
            tailf:info
              "<0-2147483>;;value of tx-speed in kbps";
            tailf:cli-drop-node-name;
            type uint32 {
              range "0..2147483";
            }
          }
        }
      }
      container lcp {
        tailf:info
          "LCP specific commands";
        leaf renegotiation {
          tailf:info
            "LNS/HGW renegotiates LCP";
          type enumeration {
            enum "always" {
              tailf:info
                "Always renegotiate";
            }
            enum "on-mismatch" {
              tailf:info
                "Renego only when config mismatch between LNS/HGW and LAC/NAS";
            }
          }
        }
      }
      container local {
        tailf:info
          "Local information";
        leaf name {
          type string {
            tailf:info
              "name;;Local name used for group authentication";
          }
        }
      }
      container pptp {
        tailf:info
          "PPTP specific commands";
        tailf:cli-diff-dependency "../accept-dialin/protocol" {
          tailf:xpath-root 3;
        }
        when "not(../accept-dialin/protocol='l2tp')" {
          tailf:xpath-root 3;
          tailf:dependency "../accept-dialin/protocol";
        }
        container flow-control {
          tailf:info
            "PPTP flow control commands";
          leaf receive-window {
            tailf:info
              "Receive window for incoming packets";
            tailf:cli-full-command;
            type uint8 {
              tailf:info
                "<1-64>;;packets";
              range "1..64";
            }
          }
          leaf static-rtt {
            tailf:info
              "Static round trip time";
            tailf:cli-full-command;
            type uint16 {
              tailf:info
                "<100-5000>;;milliseconds";
              range "100..5000";
            }
          }
        }
        container relay {
          tailf:info
            "Relay options configuration";
          container pppoe {
            tailf:info
              "PPPoE relay options";
            leaf bba-group {
              tailf:info
                "WORD;;bba-group name for protocol PPPoE";
              type string;
            }
          }
        }
        container tunnel {
          tailf:info
            "PPTP tunnel commands";
          leaf echo {
            tailf:info
              "Echo packet interval";
            type uint16 {
              tailf:info
                "<0-1000>;;seconds, default is 60";
              range "0..1000";
            }
            default "60";
          }
        }
      }
      container redirect {
        tailf:info
          "Call redirection options";
        leaf identifier {
          tailf:info
            "WORD;;Redirect identifier name (31 chars max)";
          type string {
            length "1..31";
          }
        }
      }
      container source {
        tailf:info
          "Configuration source for this vpdn-group";
        leaf vpdn-template {
          tailf:info
            "Use vpdn-template";
          type string;
        }
      }
      leaf source-ip {
        tailf:info
          "Set source IP address for this vpdn-group";
        type inet:ipv4-address;
      }
      container terminate-from {
        tailf:info
          "";
        leaf hostname {
          tailf:info
            "";
          tailf:cli-full-command;
          type string;
        }
      }
      container vpn {
        tailf:info
          "VPN ID/VRF name";
        leaf id {
          tailf:info
            "VPN ID";
          tailf:cli-full-command;
          type string;
        }
        leaf vrf {
          tailf:info
            "VPN Routing/Forwarding instance name";
          tailf:cli-full-command;
          tailf:cli-diff-dependency "../../../ip/vrf" {
            tailf:xpath-root 3;
          }
          tailf:cli-diff-dependency "../../../vrf/definition" {
            tailf:xpath-root 3;
          }
          type string {
            tailf:info
              "WORD;;VPN Routing/Forwarding instance name";
          }
        }
      }
    }
    container bba-group {
      tailf:ncs-device-type "cli-ned";
      tailf:display-when "not(../../ncs:module) or ../../ncs:module[ncs:name='tailf-ned-cisco-ios']";
      tailf:info
        "Configure BBA Group";
      list pppoe {
        tailf:info
          "PPPoE type";
        key "id";
        leaf id {
          type union {
            type string {
              tailf:info
                "WORD;;BBA Group name";
            }
            type enumeration {
              enum "global" {
                tailf:info
                  "PPPoE global group";
              }
            }
          }
        }
        container vendor-tag {
          tailf:info
            "PPPoE Vendor Specific Tag";
          container circuit-id {
            tailf:info
              "Circuit-Id";
            leaf service {
              tailf:info
                "Enable processing";
              type empty;
            }
          }
          container dsl-sync-rate {
            tailf:info
              "DSL-Sync-Rate";
            leaf service {
              tailf:info
                "Enable processing";
              type empty;
            }
          }
          container remote-id {
            tailf:info
              "Remote-Id";
            leaf service {
              tailf:info
                "Enable processing";
              type empty;
            }
          }
          leaf strip {
            tailf:info
              "Strip all vendor tags";
            type empty;
          }
        }
        leaf virtual-template {
          tailf:info
            "BBA virtual template command";
          type uint16 {
            tailf:info
              "<1-4095>;;Virtual Template interface number";
            range "1..4095";
          }
        }
      }
    }
    container tacacs-server {
      tailf:ncs-device-type "cli-ned";
      tailf:display-when "not(../../ncs:module) or ../../ncs:module[ncs:name='tailf-ned-cisco-ios']";
      tailf:info
        "Modify TACACS query parameters";
      tailf:cli-diff-dependency "../aaa/new-model" {
        tailf:xpath-root 3;
      }
      leaf administration {
        tailf:info
          "Start tacacs+ deamon handling administrative messages";
        type empty;
      }
      list host {
        tailf:info
          "Specify a TACACS server";
        tailf:cli-suppress-mode;
        tailf:cli-delete-when-empty;
        tailf:cli-compact-syntax;
        tailf:cli-reset-container;
        tailf:cli-show-long-obu-diffs;
        ordered-by user;
        key "name";
        leaf name {
          type inet:host {
            tailf:info
              "Hostname or A.B.C.D;;IP address of TACACS server";
          }
        }
        leaf port {
          tailf:info
            "TCP port for TACACS+ server (default is 49)";
          type uint16 {
            tailf:info
              "<1-65535>;;Port number";
            range "1..65535";
          }
        }
        leaf timeout {
          tailf:info
            "Time to wait for this TACACS server to reply (overrides default)";
          type uint16 {
            tailf:info
              "<1-1000>;;Timeout value in seconds to wait for server to reply";
            range "1..1000";
          }
        }
        container key {
          tailf:info
            "per-server encryption key (overrides default)";
          tailf:cli-flatten-container;
          tailf:cli-compact-syntax;
          tailf:cli-sequence-commands;
          uses password-grouping;
        }
      }
      leaf timeout {
        tailf:info
          "Time to wait for a TACACS server to reply";
        type uint16 {
          tailf:info
            "<1-1000>;;Wait time (default 5 seconds)";
          range "1..1000";
        }
        default "5";
      }
      container directed-request {
        tailf:info
          "Allow user to specify tacacs server to use with `@server'";
        tailf:cli-compact-syntax;
        tailf:cli-sequence-commands;
        presence "true";
        leaf restricted {
          tailf:info
            "restrict queries to directed request servers only";
          tailf:cli-optional-in-sequence;
          type empty;
        }
        leaf no-truncate {
          tailf:info
            "Do not truncate the @hostname from username.";
          type empty;
        }
      }
      container key {
        tailf:info
          "Set TACACS+ encryption key.";
        tailf:cli-compact-syntax;
        tailf:cli-sequence-commands;
        uses password-grouping;
      }
      leaf last-resort {
        tailf:info
          "Define TACACS action if no server responds";
        type enumeration {
          enum "password" {
            tailf:info
              "The 'enable' password must be provided";
          }
          enum "succeed" {
            tailf:info
              "Access to privileged level is granted";
          }
        }
      }
    }
    container tacacs {
      tailf:ncs-device-type "cli-ned";
      tailf:display-when "not(../../ncs:module) or ../../ncs:module[ncs:name='tailf-ned-cisco-ios']";
      tailf:info
        "TACACS server configuration command";
      tailf:cli-diff-dependency "../aaa/new-model" {
        tailf:xpath-root 3;
      }
      list server {
        tailf:info
          "Server configuration";
        tailf:cli-mode-name "config-server-tacacs";
        tailf:cli-full-command;
        key "name";
        leaf name {
          type string {
            tailf:info
              "WORD;;Name for the tacacs server configuration";
          }
        }
        container address {
          tailf:info
            "Specify ip address for tacacs server";
          choice address-choice {
            leaf ipv4 {
              tailf:info
                "Configure ipv4 address for tacacs server";
              type inet:host {
                tailf:info
                  "Hostname or A.B.C.D;;IP address of tacacs server";
              }
            }
            leaf ipv6 {
              tailf:info
                "Configure ipv6 address for tacacs server";
              tailf:cli-case-insensitive;
              type inet:host {
                tailf:info
                  "Hostname or X:X:X:X::X;;IP address of tacacs server";
              }
            }
          }
        }
        container key {
          tailf:info
            "per-server encryption key (overrides default)";
          tailf:cli-compact-syntax;
          tailf:cli-sequence-commands;
          uses password-grouping;
        }
        leaf port {
          tailf:info
            "TCP port for TACACS+ server (default is 49)";
          tailf:cli-full-command;
          type uint16 {
            tailf:info
              "<1-65535>;;Port number";
            range "1..65535";
          }
          default "49";
        }
        leaf timeout {
          tailf:info
            "Time to wait for this TACACS server to reply (overrides default)";
          tailf:cli-full-command;
          type uint16 {
            tailf:info
              "<1-1000>;;Timeout value in seconds to wait for server to reply";
            range "1..1000";
          }
        }
        leaf single-connection {
          tailf:info
            "Multiplex all packets over a single tcp connection to server (for CiscoSecure)";
          type empty;
        }
        leaf send-nat-address {
          tailf:info
            "To send client's post NAT address to tacacs+ server";
          type empty;
        }
      }
    }
    container udld {
      tailf:ncs-device-type "cli-ned";
      tailf:display-when "not(../../ncs:module) or ../../ncs:module[ncs:name='tailf-ned-cisco-ios']";
      tailf:info
        "Configure global UDLD setting";
      leaf enable {
        tailf:info
          "Enable UDLD protocol on fiber ports except where locally configured";
        type empty;
      }
      leaf aggressive {
        tailf:info
          "Enable UDLD protocol in aggressive mode on fiber ports except where locally configured";
        type empty;
      }
      container message {
        tailf:info
          "Set UDLD message parameters";
        leaf time {
          tailf:info
            "Set UDLD message time period";
          type uint8 {
            tailf:info
              "<1-90>;;Time in seconds between sending of messages in steady state";
            range "1..90";
          }
        }
      }
    }
    container rep {
      tailf:ncs-device-type "cli-ned";
      tailf:display-when "not(../../ncs:module) or ../../ncs:module[ncs:name='tailf-ned-cisco-ios']";
      tailf:info
        "Resilient Ethernet Protocol characteristics";
      container admin {
        tailf:info
          "administrative configuration";
        list vlan {
          tailf:info
            "VLAN";
          key "name";
          leaf name {
            type uint16 {
              tailf:info
                "<2-4094>;;between 2 and 4094";
              range "2..4094";
            }
          }
        }
      }
    }
    container xconnect {
      tailf:ncs-device-type "cli-ned";
      tailf:display-when "not(../../ncs:module) or ../../ncs:module[ncs:name='tailf-ned-cisco-ios']";
      tailf:info
        "Xconnect config commands";
      container logging {
        tailf:info
          "Configure logging flags";
        container pseudowire {
          tailf:info
            "pseudowire status transition logging";
          leaf status {
            tailf:info
              "pseudowire status up/down logging";
            tailf:cli-full-command;
            type empty;
          }
        }
        leaf redundancy {
          tailf:info
            "xconnect redundancy events";
          tailf:cli-full-command;
          type empty;
        }
      }
    }
    list template {
      tailf:ncs-device-type "cli-ned";
      tailf:display-when "not(../ncs:module) or ../ncs:module[ncs:name='tailf-ned-cisco-ios']";
      tailf:info
        "Select a template to configure";
      tailf:cli-mode-name "config-template";
      key "name";
      leaf name {
        type string {
          tailf:info
            "WORD;;Template name";
        }
      }
      leaf type {
        tailf:info
          "Type of the template";
        tailf:cli-prefix-key;
        type enumeration {
          enum "pseudowire" {
            tailf:info
              "Template customized interface pseudowire";
          }
        }
      }
      leaf encapsulation {
        tailf:info
          "Data encapsulation method";
        type enumeration {
          enum "l2tpv3" {
            tailf:info
              "Use L2TPv3 encapsulation";
          }
          enum "mpls" {
            tailf:info
              "Use MPLS encapsulation";
          }
        }
      }
      leaf mtu {
        tailf:info
          "set Maximum Transmission Unit";
        tailf:cli-full-command;
        type uint16 {
          tailf:info
            "<64-65535>;;Maximum Transmission Unit value";
          range "64..65535";
        }
      }
      leaf control-word {
        tailf:info
          "Control-word options";
        type enumeration {
          enum "exclude" {
            tailf:info
              "Exclude control-word in pseudowire packets";
          }
          enum "include" {
            tailf:info
              "Include control-word in pseudowire packets";
          }
        }
      }
      container preferred-path {
        tailf:info
          "Preferred path";
        tailf:cli-compact-syntax;
        tailf:cli-sequence-commands {
          tailf:cli-reset-siblings;
        }
        choice interface-or-peer {
          leaf interface {
            tailf:info
              "Output Interface";
            type string {
              tailf:info
                "WORD;;Interface Name";
            }
          }
          leaf peer {
            tailf:info
              "Peer Address";
            type inet:host {
              tailf:info
                "Hostname or A.B.C.D;;IP address or host name of Peer PE";
            }
          }
        }
        leaf disable-fallback {
          tailf:info
            "disable fall back to alternative route";
          type empty;
        }
      }
      container signaling {
        tailf:info
          "Signaling options";
        leaf protocol {
          tailf:info
            "Signaling protocol to use";
          type enumeration {
            enum "ldp" {
              tailf:info
                "Use LDP signaling";
            }
            enum "none" {
              tailf:info
                "No signaling, use manually configured pseudowires";
            }
          }
        }
      }
      container dot1x {
        tailf:info
          "Interface Config Commands for IEEE 802.1X";
        leaf pae {
          tailf:info
            "Set 802.1x interface pae type";
          type enumeration {
            enum "authenticator" {
              tailf:info
                "Set pae type as Authenticator";
            }
            enum "supplicant" {
              tailf:info
                "Set pae type as Supplicant";
            }
          }
        }
      }
      container spanning-tree {
        tailf:info
          "Spanning Tree Subsystem";
        container portfast {
          tailf:info
            "Spanning tree portfast options";
          tailf:cli-compact-syntax;
          tailf:cli-delete-when-empty;
          presence "true";
          choice portfast-choice {
            leaf disable {
              tailf:info
                "Disable portfast for this interface";
              type empty;
            }
            leaf network {
              tailf:info
                "Enable portfast network on the interface";
              type empty;
            }
            case trunk-mode {
              leaf edge {
                tailf:info
                  "Enable portfast edge on the interface";
                type empty;
              }
              leaf trunk {
                tailf:info
                  "Enable portfast edge on the interface even in trunk mode";
                type empty;
              }
            }
          }
        }
        leaf guard {
          tailf:info
            "Change an interface's spanning tree guard mode";
          type enumeration {
            enum "loop" {
              tailf:info
                "Set guard mode to loop guard on interface";
            }
            enum "none" {
              tailf:info
                "Set guard mode to none";
            }
            enum "root" {
              tailf:info
                "Set guard mode to root guard on interface";
            }
          }
        }
      }
      container mab {
        tailf:info
          "MAC Authentication Bypass Interface Config Commands";
        tailf:cli-reset-container;
        presence "true";
        leaf eap {
          tailf:info
            "Use EAP authentication for MAC Auth Bypass";
          type empty;
        }
      }
      container access-session {
        tailf:info
          "Access Session specific Interface Configuration Commands";
        leaf port-control {
          tailf:info
            "Set the port-control value";
          type enumeration {
            enum "auto" {
              tailf:info
                "PortState set to automatic";
            }
            enum "force-authorized" {
              tailf:info
                "PortState set to AUTHORIZED";
            }
            enum "force-unauthorized" {
              tailf:info
                "PortState set to UnAuthorized";
            }
          }
        }
      }
      container authentication {
        tailf:info
          "Auth Manager Interface Configuration Commands";
        leaf periodic {
          tailf:info
            "Enable or Disable Reauthentication for this port";
          type empty;
        }
        container timer {
          tailf:info
            "Set authentication timer values";
          leaf reauthenticate {
            tailf:info
              "Time in seconds after which an automatic re-authentication should be initiated (default 1 hour)";
            type union {
              type enumeration {
                enum "server" {
                  tailf:info
                    "Obtain re-authentication timeout value from the server";
                }
              }
              type uint16 {
                tailf:info
                  "<1-65535>;;Enter a value between 1 and 65535";
                range "1..65535";
              }
            }
            default "3600";
          }
        }
      }
      container service-policy {
        tailf:info
          "Configure CPL Service Policy";
        container type {
          tailf:info
            "Configure CPL Service Policy";
          container control {
            tailf:info
              "Apply a control policy to the interface";
            leaf subscriber {
              tailf:info
                "Apply a subscriber control policy to the interfac";
              tailf:non-strict-leafref {
                path "../../../../../policy-map-event-control/policy-map/name";
              }
              type string {
                tailf:info
                  "WORD;;policy-map name";
              }
            }
          }
        }
      }
    }
    container fabric {
      tailf:ncs-device-type "cli-ned";
      tailf:display-when "not(../../ncs:module) or ../../ncs:module[ncs:name='tailf-ned-cisco-ios']";
      tailf:info
        "Catalyst 6000 crossbar fabric configuration commands";
      container switching-mode {
        tailf:info
          "Switching mode settings";
        container allow {
          tailf:info
            "Allow settings";
          choice allow-choice {
            leaf bus-mode {
              tailf:info
                "Allow switching in bus mode for modules";
              type empty;
            }
            container truncated {
              tailf:info
                "Truncated switching mode";
              presence "true";
              leaf threshold {
                tailf:info
                  "Number of SFM-capable modules for truncated switching mode. Switch applies the threshold only when the mode is disallowed. Switch ignores the threshold when the truncated mode is allowed";
                type uint8 {
                  tailf:info
                    "<1-9>;;Threshold for truncated switching mode.";
                  range "1..9";
                }
              }
            }
          }
        }
        container force {
          tailf:info
            "Force modules to different switching modes";
          leaf bus-mode {
            tailf:info
              "Switching mode of service modules will be forced to bus-mode by powercycling it.";
            type empty;
          }
        }
      }
      container buffer-reserve {
        tailf:info
          "Reserve FIFO buffer";
        leaf queue {
          tailf:info
            "Queue setting for buffer reserve";
          type empty;
        }
      }
    }
    container port-channel {
      tailf:ncs-device-type "cli-ned";
      tailf:display-when "not(../../ncs:module) or ../../ncs:module[ncs:name='tailf-ned-cisco-ios']";
      tailf:info
        "EtherChannel configuration";
      container per-module {
        tailf:info
          "per-module configuration";
        leaf load-balance {
          tailf:info
            "Load Balance Enable";
          type empty;
        }
      }
      leaf load-balance {
        tailf:info
          "Load Balancing method";
        type enumeration {
          enum "dst-ip" {
            tailf:info
              "Dst IP Addr";
          }
          enum "dst-mac" {
            tailf:info
              "Dst Mac Addr";
          }
          enum "dst-mixed-ip-port" {
            tailf:info
              "Dst IP Addr and TCP/UDP Port";
          }
          enum "dst-port" {
            tailf:info
              "Dst TCP/UDP Port";
          }
          enum "mpls" {
            tailf:info
              "Load Balancing for MPLS packets";
          }
          enum "src-dst-ip" {
            tailf:info
              "Src XOR Dst IP Addr";
          }
          enum "src-dst-mac" {
            tailf:info
              "Src XOR Dst Mac Addr";
          }
          enum "src-dst-mixed-ip-port" {
            tailf:info
              "Src XOR Dst IP Addr and TCP/UDP Port";
          }
          enum "src-dst-port" {
            tailf:info
              "Src XOR Dst TCP/UDP Port";
          }
          enum "src-ip" {
            tailf:info
              "Src IP Addr";
          }
          enum "src-mac" {
            tailf:info
              "Src Mac Addr";
          }
          enum "src-mixed-ip-port" {
            tailf:info
              "Src IP Addr and TCP/UDP Port";
          }
          enum "src-port" {
            tailf:info
              "Src TCP/UDP Port";
          }
        }
      }
      leaf load-balance-hash-algo {
        tailf:info
          "Algorithm selection for FBLB";
        type string;
      }
    }
    container l2protocol-tunnel {
      tailf:ncs-device-type "cli-ned";
      tailf:display-when "not(../../ncs:module) or ../../ncs:module[ncs:name='tailf-ned-cisco-ios']";
      tailf:info
        "Tunnel Layer2 protocols";
      leaf cos {
        tailf:info
          "Class of Service";
        type uint8 {
          tailf:info
            "<0-7>;;priority value";
          range "0..7";
        }
      }
      container global {
        tailf:info
          "Global settings";
        leaf drop-threshold {
          tailf:info
            "L2PT packets drop threshold";
          type uint16 {
            tailf:info
              "<100-20000>;;Packets per second";
            range "100..20000";
          }
        }
      }
    }
    container l2vpn {
      tailf:ncs-device-type "cli-ned";
      tailf:display-when "not(../../ncs:module) or ../../ncs:module[ncs:name='tailf-ned-cisco-ios']";
      tailf:info
        "Layer2 VPN commands";
      tailf:cli-add-mode;
      tailf:cli-full-command;
      presence "true";
    }
    container l2vpn-vfi {
      tailf:ncs-device-type "cli-ned";
      tailf:display-when "not(../../ncs:module) or ../../ncs:module[ncs:name='tailf-ned-cisco-ios']";
      tailf:cli-drop-node-name;
      container l2vpn {
        container vfi {
          tailf:info
            "Configure a Virtual Forwarding Instance (VFI)";
          list context {
            tailf:info
              "Layer2 VPN Context";
            tailf:cli-mode-name "config-vfi";
            key "name";
            leaf name {
              type string {
                tailf:info
                  "WORD;;Virtual Forwarding Instance (VFI) name";
              }
            }
            container vpn {
              tailf:info
                "VPN configuration";
              leaf id {
                tailf:info
                  "VPN id";
                type uint32 {
                  tailf:info
                    "<1-4294967295>;;VPN id value";
                  range "1..4294967295";
                }
              }
            }
            container autodiscovery {
              tailf:info
                "Auto Discovery mode";
              container bgp {
                tailf:info
                  "Use BGP for neighbor discovery";
                container signaling {
                  tailf:info
                    "Signaling protocol to use";
                  tailf:cli-add-mode;
                  tailf:cli-mode-name "config-vfi-autodiscovery";
                  presence "true";
                  choice protocol-choice {
                    leaf bgp {
                      tailf:info
                        "Use BGP signaling";
                      tailf:cli-hide-in-submode;
                      type empty;
                    }
                    leaf ldp {
                      tailf:info
                        "Use LDP signaling";
                      tailf:cli-hide-in-submode;
                      type empty;
                    }
                  }
                  leaf template {
                    tailf:info
                      "Template to be used for autodiscovered pseudowires";
                    tailf:cli-hide-in-submode;
                    tailf:non-strict-leafref {
                      path "../../../../../../../../template/name";
                    }
                    type string {
                      tailf:info
                        "WORD;;template name (Max size 32)";
                    }
                  }
                  container ve {
                    tailf:info
                      "Specify VPLS Edge device parameters";
                    leaf id {
                      tailf:info
                        "Specify VPLS Edge device ID";
                      type uint16 {
                        tailf:info
                          "<1-16384>;;VPLS Edge device ID value";
                        range "1..16384";
                      }
                    }
                  }
                  leaf vpls-id {
                    tailf:info
                      "Specify VPLS-ID Extendended Community";
                    tailf:cli-full-command;
                    type asn-ip-type {
                      tailf:info
                        "ASN:nn or IP-address:nn;;Specify VPLS-ID Extendended Community";
                    }
                  }
                  container route-target {
                    tailf:info
                      "Specify Route Target VPN Extended Communities";
                    uses route-target-grouping;
                  }
                }
              }
            }
            container member {
              tailf:info
                "Configure the cross connect member";
              list ip-address-list {
                tailf:cli-drop-node-name;
                tailf:cli-suppress-mode;
                tailf:cli-delete-when-empty;
                tailf:cli-compact-syntax;
                key "ip-address";
                leaf ip-address {
                  type inet:ipv4-address {
                    tailf:info
                      "A.B.C.D;;IP address of the peer";
                  }
                }
                choice encapsulation-template-choice {
                  leaf encapsulation {
                    tailf:info
                      "Data encapsulation method";
                    type enumeration {
                      enum "mpls" {
                        tailf:info
                          "Use MPLS encapsulation";
                      }
                    }
                  }
                  leaf template {
                    tailf:info
                      "Template to use for encapsulation and protocol configuration";
                    tailf:cli-full-command;
                    type string {
                      tailf:info
                        "WORD;;template name (Max size 32)";
                    }
                  }
                }
              }
              list ip-address-vc-id-list {
                tailf:cli-drop-node-name;
                tailf:cli-suppress-mode;
                tailf:cli-delete-when-empty;
                tailf:cli-compact-syntax;
                key "ip-address vc-id";
                leaf ip-address {
                  type inet:ipv4-address {
                    tailf:info
                      "A.B.C.D;;IP address of the peer";
                  }
                }
                leaf vc-id {
                  type uint32 {
                    tailf:info
                      "<1-4294967295>;;Enter VC ID value";
                  }
                }
                choice encapsulation-template-choice {
                  leaf encapsulation {
                    tailf:info
                      "Data encapsulation method";
                    type enumeration {
                      enum "mpls" {
                        tailf:info
                          "Use MPLS encapsulation";
                      }
                    }
                  }
                  leaf template {
                    tailf:info
                      "Template to use for encapsulation and protocol configuration";
                    tailf:cli-full-command;
                    type string {
                      tailf:info
                        "WORD;;template name (Max size 32)";
                    }
                  }
                }
              }
              list pseudowire {
                tailf:info
                  "Pseudowire interface";
                tailf:cli-suppress-mode;
                tailf:cli-delete-when-empty;
                tailf:cli-compact-syntax;
                tailf:cli-sequence-commands;
                tailf:cli-allow-join-with-key {
                  tailf:cli-display-joined;
                }
                key "name";
                leaf name {
                  tailf:non-strict-leafref {
                    path "../../../../../../../interface/pseudowire/name";
                  }
                  type uint32 {
                    tailf:info
                      "<1-231072>;;Pseudowire interface number";
                    range "1..231072";
                  }
                }
                leaf ip-address {
                  tailf:cli-drop-node-name;
                  type inet:ipv4-address {
                    tailf:info
                      "A.B.C.D;;IP address of the peer";
                  }
                }
                leaf vc-id {
                  tailf:cli-drop-node-name;
                  tailf:cli-optional-in-sequence;
                  type uint32 {
                    tailf:info
                      "<1-4294967295>;;Enter VC ID value";
                  }
                }
                choice encapsulation-template-choice {
                  leaf encapsulation {
                    tailf:info
                      "Data encapsulation method";
                    type enumeration {
                      enum "mpls" {
                        tailf:info
                          "Use MPLS encapsulation";
                      }
                    }
                  }
                  leaf template {
                    tailf:info
                      "Template to use for encapsulation and protocol configuration";
                    tailf:cli-full-command;
                    type string {
                      tailf:info
                        "WORD;;template name (Max size 32)";
                    }
                  }
                }
              }
            }
            leaf mtu {
              type uint16 {
                tailf:info
                  "<1500-9180>;;Maximum Transmission Unit value";
                range "1500..9180";
              }
            }
          }
        }
      }
    }
    container l2vpn-xconnect {
      tailf:ncs-device-type "cli-ned";
      tailf:display-when "not(../../ncs:module) or ../../ncs:module[ncs:name='tailf-ned-cisco-ios']";
      tailf:cli-drop-node-name;
      container l2vpn {
        tailf:info
          "Layer2 VPN commands";
        container xconnect {
          tailf:info
            "Configure a cross connect";
          list context {
            tailf:info
              "Layer2 VPN Context";
            tailf:cli-mode-name "config-xconnect";
            tailf:cli-compact-syntax;
            key "name";
            leaf name {
              type string {
                tailf:info
                  "WORD;;Configure the cross connect name";
              }
            }
            container remote {
              tailf:info
                "L2VPN remote peer configuration commands";
              container link {
                tailf:info
                  "Link information";
                container failure {
                  tailf:info
                    "Failure information";
                  leaf notification {
                    tailf:info
                      "Notify in case of remote link failure";
                    tailf:cli-boolean-no;
                    type boolean;
                    default "true";
                  }
                }
              }
            }
            leaf interworking {
              tailf:info
                "Interworking options for the cross connect";
              tailf:cli-full-command;
              type enumeration {
                enum "ethernet" {
                  tailf:info
                    "Ethernet interworking";
                }
                enum "ip" {
                  tailf:info
                    "IP interworking";
                }
                enum "vlan" {
                  tailf:info
                    "VLAN interworking";
                }
              }
            }
            container member {
              tailf:info
                "Configure the cross connect member";
              list member-list {
                tailf:cli-drop-node-name;
                tailf:cli-suppress-mode;
                tailf:cli-delete-when-empty;
                tailf:cli-compact-syntax;
                tailf:cli-sequence-commands {
                  tailf:cli-reset-all-siblings;
                }
                key "name";
                leaf name {
                  type string {
                    tailf:info
                      "WORD;;Interface name";
                    pattern '(GigabitEthernet.*)|(Port-channel.*)|(TenGigabitEthernet.*)|(Vlan.*)|(Ethernet.*)|(FastEthernet.*)|(HundredGigE.*)';
                  }
                }
                leaf service-instance {
                  tailf:info
                    "Ethernet Service Instance";
                  tailf:cli-optional-in-sequence;
                  tailf:cli-diff-dependency "../../../../../../../interface/Ethernet/service/instance" {
                    tailf:xpath-root 3;
                  }
                  tailf:cli-diff-dependency "../../../../../../../interface/FastEthernet/service/instance" {
                    tailf:xpath-root 3;
                  }
                  tailf:cli-diff-dependency "../../../../../../../interface/GigabitEthernet/service/instance" {
                    tailf:xpath-root 3;
                  }
                  tailf:cli-diff-dependency "../../../../../../../interface/TenGigabitEthernet/service/instance" {
                    tailf:xpath-root 3;
                  }
                  tailf:cli-diff-dependency "../../../../../../../interface/FortyGigabitEthernet/service/instance" {
                    tailf:xpath-root 3;
                  }
                  tailf:cli-diff-dependency "../../../../../../../interface/HundredGigE/service/instance" {
                    tailf:xpath-root 3;
                  }
                  tailf:cli-diff-dependency "../../../../../../../interface/Port-channel/service/instance" {
                    tailf:xpath-root 3;
                  }
                  tailf:cli-diff-dependency "../../../../../../../interface/Vlan/service/instance" {
                    tailf:xpath-root 3;
                  }
                  type uint32 {
                    tailf:info
                      "<1-4000>;;Service Instance ID";
                  }
                }
                leaf group {
                  tailf:info
                    "Configure the cross connect member redundancy group";
                  type string {
                    tailf:info
                      "WORD;;Enter redundancy group name";
                  }
                }
                leaf priority {
                  tailf:info
                    "Configure the cross connect member priority";
                  type uint8 {
                    tailf:info
                      "<0-16>;;Enter priority number of the member (0: Highest, 16: Lowest)";
                    range "0..16";
                  }
                }
              }
              list pseudowire {
                tailf:info
                  "Pseudowire Interface";
                tailf:cli-suppress-mode;
                tailf:cli-delete-when-empty;
                tailf:cli-allow-join-with-key {
                  tailf:cli-display-joined;
                }
                key "name";
                leaf name {
                  type uint32 {
                    tailf:info
                      "<1-231072>;;Pseudowire interface number";
                    range "1..231072";
                  }
                }
              }
              list address-list {
                tailf:cli-drop-node-name;
                tailf:cli-suppress-mode;
                tailf:cli-delete-when-empty;
                tailf:cli-compact-syntax;
                tailf:cli-sequence-commands {
                  tailf:cli-reset-all-siblings;
                }
                tailf:cli-incomplete-command;
                key "name";
                leaf name {
                  type inet:ipv4-address {
                    tailf:info
                      "A.B.C.D;;IP address of the peer";
                  }
                }
                leaf vcid {
                  tailf:cli-drop-node-name;
                  tailf:cli-incomplete-command;
                  type uint32 {
                    tailf:info
                      "<1-4294967295>;;Enter VC ID value";
                    range "1..4294967295";
                  }
                }
                choice encap-or-termplate {
                  leaf encapsulation {
                    tailf:info
                      "Data encapsulation method";
                    type enumeration {
                      enum "mpls" {
                        tailf:info
                          "Use MPLS encapsulation";
                      }
                    }
                  }
                  leaf template {
                    tailf:info
                      "template to use for encapsulation and protocol configuration";
                    type string {
                      tailf:info
                        "WORD;;template name (Max size 32)";
                    }
                  }
                }
                leaf group {
                  tailf:info
                    "Configure the cross connect member redundancy group";
                  type string {
                    tailf:info
                      "WORD;;Enter redundancy group name";
                  }
                }
                leaf priority {
                  tailf:info
                    "Configure the cross connect member priority";
                  type uint8 {
                    tailf:info
                      "<0-16>;;Enter priority number of the member (0: Highest, 16: Lowest)";
                    range "0..16";
                  }
                }
              }
            }
            container redundancy {
              tailf:info
                "Xconnect redundancy information";
              leaf predictive {
                tailf:info
                  "Switch over to backup member without waiting for UP status";
                type enumeration {
                  enum "disabled" {
                    tailf:info
                      "Disable predictive switchover capability for this xconnect";
                  }
                  enum "enabled" {
                    tailf:info
                      "Enable predictive switchover capability for this xconnect";
                  }
                }
              }
              list delay {
                tailf:info
                  "Xconnect redundancy delay parameters";
                tailf:cli-suppress-mode;
                tailf:cli-delete-when-empty;
                tailf:cli-compact-syntax;
                tailf:cli-sequence-commands;
                key "group";
                leaf group {
                  tailf:info
                    "Redundancy group name";
                  tailf:cli-expose-key-name;
                  type string {
                    tailf:info
                      "Redundancy group name";
                  }
                }
                leaf enable-delay {
                  tailf:cli-drop-node-name;
                  tailf:cli-prefix-key;
                  type uint8 {
                    tailf:info
                      "<0-180>;;Enable delay";
                    range "0..180";
                  }
                }
                leaf disable-delay {
                  tailf:cli-drop-node-name;
                  tailf:cli-prefix-key;
                  type union {
                    type uint8 {
                      tailf:info
                        "<0-180>;;Disable delay";
                      range "0..180";
                    }
                    type enumeration {
                      enum "never" {
                        tailf:info
                          "Disallow disable";
                      }
                    }
                  }
                }
              }
            }
          }
        }
      }
    }
    container l2vpn-evpn {
      tailf:ncs-device-type "cli-ned";
      tailf:display-when "not(../../ncs:module) or ../../ncs:module[ncs:name='tailf-ned-cisco-ios']";
      tailf:cli-drop-node-name;
      container l2vpn {
        tailf:info
          "Layer2 VPN commands";
        container evpn {
          tailf:info
            "Ethernet Virtual Private Network (EVPN) configuration";
          list instance {
            tailf:info
              "EVPN instance (EVI)";
            tailf:cli-incomplete-command;
            tailf:cli-mode-name "config-evpn-evi";
            key "id";
            leaf id {
              type uint16 {
                tailf:info
                  "<1-65535>;;EVPN instance identifier value";
                range "1..65535";
              }
            }
            leaf point-to-point {
              tailf:info
                "EVPN Virtual Private Wire Service (EVPN VPWS)";
              tailf:cli-hide-in-submode;
              type empty;
            }
            container vpws {
              tailf:info
                "EVPN Virtual Private Wire Service configuration";
              list context {
                tailf:info
                  "EVPN VPWS context";
                tailf:cli-mode-name "config-evpn-vpws";
                tailf:cli-full-command;
                key "name";
                leaf name {
                  type string {
                    tailf:info
                      "WORD;;EVPN VPWS context name";
                  }
                }
                container service {
                  tailf:info
                    "VPWS Service Instance";
                  tailf:cli-compact-syntax;
                  tailf:cli-sequence-commands;
                  leaf target {
                    tailf:info
                      "Target (remote) VPWS Service Instance identifier";
                    tailf:cli-incomplete-command;
                    type uint32 {
                      tailf:info
                        "<1-16777215>;;Target VPWS Service Instance identifier value";
                      range "1..16777215";
                    }
                  }
                  leaf source {
                    tailf:info
                      "Source (local) VPWS Service Instance identifier";
                    type uint32 {
                      tailf:info
                        "<1-16777215>;;Source VPWS Service Instance identifier value";
                      range "1..16777215";
                    }
                  }
                }
                container member {
                  tailf:info
                    "EVPN member configuration";
                  tailf:cli-compact-syntax;
                  tailf:cli-sequence-commands;
                  leaf interface {
                    tailf:cli-drop-node-name;
                    tailf:cli-remove-before-change;
                    type string {
                      tailf:info
                        "WORD;;Interface name";
                    }
                  }
                  leaf service-instance {
                    tailf:info
                      "Ethernet Service Instance";
                    tailf:cli-diff-dependency "../../../../../../../../interface/Ethernet/service/instance" {
                      tailf:xpath-root 3;
                    }
                    tailf:cli-diff-dependency "../../../../../../../../interface/FastEthernet/service/instance" {
                      tailf:xpath-root 3;
                    }
                    tailf:cli-diff-dependency "../../../../../../../../interface/GigabitEthernet/service/instance" {
                      tailf:xpath-root 3;
                    }
                    tailf:cli-diff-dependency "../../../../../../../../interface/TenGigabitEthernet/service/instance" {
                      tailf:xpath-root 3;
                    }
                    tailf:cli-diff-dependency "../../../../../../../../interface/FortyGigabitEthernet/service/instance" {
                      tailf:xpath-root 3;
                    }
                    tailf:cli-diff-dependency "../../../../../../../../interface/HundredGigE/service/instance" {
                      tailf:xpath-root 3;
                    }
                    tailf:cli-diff-dependency "../../../../../../../../interface/Port-channel/service/instance" {
                      tailf:xpath-root 3;
                    }
                    tailf:cli-diff-dependency "../../../../../../../../interface/Vlan/service/instance" {
                      tailf:xpath-root 3;
                    }
                    type uint16 {
                      tailf:info
                        "<1-4000>;;Service Instance ID";
                      range "1..4000";
                    }
                  }
                }
              }
            }
          }
        }
      }
    }
    container segment-routing {
      tailf:ncs-device-type "cli-ned";
      tailf:display-when "not(../../ncs:module) or ../../ncs:module[ncs:name='tailf-ned-cisco-ios']";
      tailf:info
        "Enter Segment Routing Mode";
      container mpls {
        tailf:info
          "Segment Routing MPLS Mode";
        tailf:cli-add-mode;
        tailf:cli-mode-name "config-srmpls";
        presence "true";
        leaf shutdown {
          tailf:info
            "SR Shutdown";
          type empty;
        }
        container global-block {
          tailf:info
            "SR Global Block Config";
          tailf:cli-compact-syntax;
          tailf:cli-sequence-commands;
          leaf start {
            tailf:cli-drop-node-name;
            tailf:cli-incomplete-command;
            tailf:cli-remove-before-change;
            type uint16 {
              tailf:info
                "<16-32767>;;SR GB Label Range Start";
              range "16..32767";
            }
          }
          leaf end {
            tailf:cli-drop-node-name;
            type uint16 {
              tailf:info
                "<16-32767>;;SR GB Label Range End";
              range "16..32767";
            }
          }
        }
        container connected-prefix-sid-map {
          tailf:info
            "Enter Connected Prefix Sid Map  Mode";
          tailf:cli-add-mode;
          tailf:cli-mode-name "config-srmpls-conn";
          container address-family {
            tailf:info
              "Enter Address Family command mode";
            container ipv4 {
              tailf:info
                "Address Family";
              tailf:cli-add-mode;
              tailf:cli-mode-name "config-srmpls-conn-af";
              tailf:cli-exit-command "exit-address-family" {
                tailf:info
                  "Exit Address Family command mode";
              }
              list address-list {
                tailf:cli-drop-node-name;
                tailf:cli-suppress-mode;
                tailf:cli-delete-when-empty;
                tailf:cli-compact-syntax;
                tailf:cli-sequence-commands {
                  tailf:cli-reset-siblings;
                }
                tailf:cli-incomplete-command;
                key "prefix";
                leaf prefix {
                  type ios:ipv4-prefix {
                    tailf:info
                      "A.B.C.D/nn;;Starting Prefix";
                  }
                }
                choice absolute-or-index {
                  leaf absolute {
                    tailf:info
                      "SID Absolute";
                    type uint32 {
                      tailf:info
                        "<0-1048575>;;Start of SID";
                      range "0..1048575";
                    }
                  }
                  leaf index {
                    tailf:info
                      "SID Index";
                    type uint32 {
                      tailf:info
                        "<0-1048575>;;Start of SID";
                      range "0..1048575";
                    }
                  }
                }
                leaf range {
                  tailf:info
                    "Set # of SIDs in range";
                  type uint32 {
                    tailf:info
                      "<1-1048575>;;Range value";
                    range "1..1048575";
                  }
                }
              }
            }
          }
        }
      }
    }
    container system {
      tailf:ncs-device-type "cli-ned";
      tailf:display-when "not(../../ncs:module) or ../../ncs:module[ncs:name='tailf-ned-cisco-ios']";
      tailf:info
        "Set the system configuration";
      container env {
        tailf:info
          "Set the system environment settings";
        container temperature {
          tailf:info
            "Set the system temperature settings";
          container threshold {
            tailf:info
              "Set the system temperature thresholds";
            leaf yellow {
              tailf:info
                "Set the yellow threshold";
              type uint8 {
                tailf:info
                  "<0-25>;;Delta value from Red threshold in Degree Celsius";
                range "0..25";
              }
            }
          }
        }
      }
      container mtu {
        tailf:info
          "Set the system Maximum Transmission Unit (MTU)";
        leaf size {
          tailf:cli-drop-node-name;
          type uint16 {
            tailf:info
              "<1500-1998>;;MTU size in bytes";
            range "1500..1998";
          }
        }
        leaf jumbo {
          tailf:info
            "Set Jumbo MTU value for GigabitEthernet or TenGigabitEthernet interfaces";
          type uint16 {
            tailf:info
              "<1500-9000>;;Jumbo MTU size in bytes";
            range "1500..9000";
          }
        }
        leaf routing {
          tailf:info
            "Set the Routing MTU for the system";
          type uint16 {
            tailf:info
              "<NUM>;;MTU size in bytes";
          }
        }
      }
      container flowcontrol {
        container bus {
          leaf auto {
            type empty;
          }
        }
      }
      leaf jumbomtu {
        tailf:info
          "Configure system jumbo mtu size";
        type uint16 {
          tailf:info
            "<1500-9216>;;Jumbo mtu size in Bytes, default is 9216";
          range "1500..9216";
        }
      }
    }
    container stackmaker {
      tailf:ncs-device-type "cli-ned";
      tailf:display-when "not(../../ncs:module) or ../../ncs:module[ncs:name='tailf-ned-cisco-ios']";
      tailf:info
        "Specify stack name and add its member";
      leaf name {
        tailf:info
          "Specify stack name";
        tailf:cli-full-command;
        type string {
          tailf:info
            "WORD;;Name of the stack";
        }
      }
    }
    container diagnostic {
      tailf:ncs-device-type "cli-ned";
      tailf:display-when "not(../../ncs:module) or ../../ncs:module[ncs:name='tailf-ned-cisco-ios']";
      tailf:info
        "Configure diagnostic information";
      container bootup {
        tailf:info
          "Configure diagnostic for bootup";
        leaf level {
          tailf:info
            "Select diagnostic level";
          type enumeration {
            enum "complete" {
              tailf:info
                "Complete level";
            }
            enum "minimal" {
              tailf:info
                "Minimal level";
            }
          }
        }
      }
      container cns {
        tailf:info
          "Configure diagnostic cns information";
        leaf publish {
          tailf:info
            "Configure diagnostic cns publish";
          type string {
            tailf:info
              "WORD;;Diagnostic cns subject";
          }
        }
        leaf subscribe {
          tailf:info
            "Configure diagnostic cns subscribe";
          type string {
            tailf:info
              "WORD;;Diagnostic cns subject";
          }
        }
      }
      container monitor {
        tailf:info
          "Configure diagnostic monitoring tests";
        leaf syslog {
          tailf:info
            "Configure diagnostic monitoring syslog";
          type empty;
        }
      }
    }
    container errdisable {
      tailf:ncs-device-type "cli-ned";
      tailf:display-when "not(../../ncs:module) or ../../ncs:module[ncs:name='tailf-ned-cisco-ios']";
      tailf:info
        "Error disable";
      container detect {
        tailf:info
          "Error disable detection";
        container cause {
          tailf:info
            "Enable error disable detection for application";
          leaf all {
            tailf:info
              "Enable error detection on all cases";
            tailf:cli-full-command;
            type empty;
          }
          leaf arp-inspection {
            tailf:info
              "Enable error detection for arp inspection";
            tailf:cli-full-command;
            type empty;
          }
          leaf bpduguard {
            tailf:info
              "Enable error detection on bpdu-guard";
            tailf:cli-full-command;
            type empty;
          }
          leaf dhcp-rate-limit {
            tailf:info
              "Enable error detection on dhcp-rate-limit";
            tailf:cli-full-command;
            type empty;
          }
          leaf dtp-flap {
            tailf:info
              "Enable error detection on dtp-flapping";
            tailf:cli-full-command;
            type empty;
          }
          leaf gbic-invalid {
            tailf:info
              "Enable error detection on gbic-invalid";
            tailf:cli-full-command;
            type empty;
          }
          leaf inline-power {
            tailf:info
              "Enable error detection for inline-power";
            tailf:cli-full-command;
            type empty;
          }
          leaf l2ptguard {
            tailf:info
              "Enable timer to recover from l2protocol-tunnel error disable state";
            tailf:cli-full-command;
            type empty;
          }
          leaf link-flap {
            tailf:info
              "Enable error detection on linkstate-flapping";
            tailf:cli-full-command;
            type empty;
          }
          leaf loopback {
            tailf:info
              "Enable error detection on loopback";
            tailf:cli-full-command;
            type empty;
          }
          leaf mlacp-minlink {
            tailf:cli-full-command;
            type empty;
          }
          leaf pagp-flap {
            tailf:info
              "Enable error detection on pagp-flapping";
            tailf:cli-full-command;
            type empty;
          }
          leaf pppoe-ia-rate-limit {
            tailf:info
              "Enable error detection on PPPoE IA rate-limit";
            tailf:cli-full-command;
            type empty;
          }
          leaf security-violation {
            tailf:info
              "Enable error detection on 802.1x-guard";
            tailf:cli-full-command;
            type empty;
          }
          leaf sfp-config-mismatch {
            tailf:info
              "Enable error detection on SFP config mismatch";
            tailf:cli-full-command;
            type empty;
          }
          leaf small-frame {
            tailf:info
              "Enable error detection on small_frame";
            tailf:cli-full-command;
            type empty;
          }
        }
      }
      container flap-setting {
        tailf:info
          "Error disable flap detection setting";
        container cause {
          tailf:info
            "Set error disable flap parameters for application";
          container dtp-flap {
            tailf:info
              "Set the variables related to detection of dtp flaps";
            tailf:cli-compact-syntax;
            tailf:cli-sequence-commands;
            leaf max-flaps {
              tailf:info
                "maximum flaps allowed before setting to errdisable";
              type uint8 {
                tailf:info
                  "<1-100>;;flap count";
                range "1..100";
              }
            }
            leaf time {
              tailf:info
                "time period the flaps are counted";
              type uint8 {
                tailf:info
                  "<1-120>;;flap count time";
                range "1..120";
              }
            }
          }
          container link-flap {
            tailf:info
              "Set the variables related to detection of link flaps";
            tailf:cli-compact-syntax;
            tailf:cli-sequence-commands;
            leaf max-flaps {
              tailf:info
                "maximum flaps allowed before setting to errdisable";
              type uint8 {
                tailf:info
                  "<1-100>;;flap count";
                range "1..100";
              }
            }
            leaf time {
              tailf:info
                "time period the flaps are counted";
              type uint8 {
                tailf:info
                  "<1-120>;;flap count time";
                range "1..120";
              }
            }
          }
          container pagp-flap {
            tailf:info
              "Set the variables related to detection of pagp flaps";
            tailf:cli-compact-syntax;
            tailf:cli-sequence-commands;
            leaf max-flaps {
              tailf:info
                "maximum flaps allowed before setting to errdisable";
              type uint8 {
                tailf:info
                  "<1-100>;;flap count";
                range "1..100";
              }
            }
            leaf time {
              tailf:info
                "time period the flaps are counted";
              type uint8 {
                tailf:info
                  "<1-120>;;flap count time";
                range "1..120";
              }
            }
          }
        }
      }
      container recovery {
        tailf:info
          "Error disable recovery";
        container cause {
          tailf:info
            "Enable error disable recovery for application";
          leaf all {
            tailf:info
              "Enable timer to recover from all error causes";
            type empty;
          }
          leaf arp-inspection {
            tailf:info
              "Enable timer to recover from arp inspection error disable state";
            type empty;
          }
          leaf bpduguard {
            tailf:info
              "Enable timer to recover from BPDU Guard error";
            type empty;
          }
          leaf channel-misconfig {
            tailf:info
              "(STP)  Enable timer to recover from channel misconfig error";
            type empty;
          }
          leaf dhcp-rate-limit {
            tailf:info
              "Enable timer to recover from dhcp-rate-limit error";
            type empty;
          }
          leaf dtp-flap {
            tailf:info
              "Enable timer to recover from dtp-flap error";
            type empty;
          }
          leaf gbic-invalid {
            tailf:info
              "Enable timer to recover from invalid GBIC error";
            type empty;
          }
          leaf inline-power {
            tailf:info
              "Enable timer to recover from inline-power error";
            type empty;
          }
          leaf l2ptguard {
            tailf:info
              "Enable timer to recover from l2protocol-tunnel error disable state";
            type empty;
          }
          leaf link-flap {
            tailf:info
              "Enable timer to recover from link-flap error";
            type empty;
          }
          leaf link-monitor-failure {
            type empty;
          }
          leaf loopback {
            tailf:info
              "Enable timer to recover from loopback error";
            type empty;
          }
          leaf mac-limit {
            tailf:info
              "Enable timer to recover from mac limit disable state";
            type empty;
          }
          leaf mlacp-minlink {
            tailf:cli-full-command;
            type empty;
          }
          container oam-remote-failure {
            tailf:cli-display-separated;
            presence "true";
            leaf critical-event {
              tailf:cli-full-command;
              type empty;
            }
            leaf dying-gasp {
              tailf:cli-full-command;
              type empty;
            }
            leaf link-fault {
              tailf:cli-full-command;
              type empty;
            }
          }
          leaf pagp-flap {
            tailf:info
              "Enable timer to recover from pagp-flap error";
            type empty;
          }
          leaf port-mode-failure {
            tailf:info
              "Enable timer to recover from port mode change failure";
            type empty;
          }
          leaf pppoe-ia-rate-limit {
            tailf:info
              "Enable timer to recover from PPPoE IA rate-limit error";
            type empty;
          }
          leaf psp {
            type empty;
          }
          leaf psecure-violation {
            tailf:info
              "Enable timer to recover from psecure violation error";
            type empty;
          }
          leaf security-violation {
            tailf:info
              "Enable timer to recover from 802.1x violation error";
            type empty;
          }
          leaf sfp-config-mismatch {
            tailf:info
              "Enable timer to recover from SFP config mismatch error";
            type empty;
          }
          leaf small-frame {
            tailf:info
              "Enable timer to recover from small frame error";
            type empty;
          }
          leaf storm-control {
            tailf:info
              "Enable timer to recover from storm-control error";
            type empty;
          }
          leaf udld {
            tailf:info
              "Enable timer to recover from udld error";
            type empty;
          }
          leaf unicast-flood {
            type empty;
          }
          leaf vmps {
            tailf:info
              "Enable timer to recover from vmps shutdown error";
            type empty;
          }
        }
        leaf interval {
          tailf:info
            "Error disable recovery timer value";
          type uint32 {
            tailf:info
              "<30-86400>;;timer-interval(sec)";
            range "30..86400";
          }
        }
      }
    }
    container monitor {
      tailf:ncs-device-type "cli-ned";
      tailf:display-when "not(../../ncs:module) or ../../ncs:module[ncs:name='tailf-ned-cisco-ios']";
      tailf:info
        "Monitoring different system events";
      list session {
        tailf:info
          "Configure a SPAN session";
        tailf:cli-suppress-mode;
        tailf:cli-delete-when-empty;
        tailf:cli-incomplete-command;
        key "id";
        leaf id {
          tailf:cli-suppress-range;
          type uint16 {
            tailf:info
              "<1-1024>;;SPAN session number";
            range "1..1024";
          }
        }
        list destination {
          tailf:info
            "SPAN destination interface or VLAN";
          tailf:cli-suppress-mode;
          tailf:cli-delete-when-empty;
          key "id";
          leaf id {
            tailf:cli-multi-word-key;
            type string {
              tailf:info
                "WORD;;monitor session string";
            }
          }
        }
        list source {
          tailf:info
            "SPAN source interface, VLAN ";
          tailf:cli-suppress-mode;
          tailf:cli-delete-when-empty;
          key "id";
          leaf id {
            tailf:cli-multi-word-key;
            type string {
              tailf:info
                "WORD;;monitor session string";
            }
          }
        }
        container filter {
          tailf:info
            "SPAN filter";
          leaf-list vlan {
            tailf:info
              "SPAN filter VLAN";
            tailf:cli-range-list-syntax;
            tailf:cli-full-command;
            type uint16 {
              tailf:info
                "<1-4094>;;SPAN source VLAN";
              range "1..4094";
            }
          }
          container packet-type {
            tailf:info
              "SPAN filter packet-type";
            container good {
              tailf:info
                "Monitor the good packets only";
              tailf:cli-diff-dependency "../bad" {
                tailf:xpath-root 3;
                tailf:cli-trigger-on-set;
              }
              leaf rx {
                tailf:info
                  "Monitor received traffic only";
                type empty;
              }
            }
            container bad {
              tailf:info
                "Monitor the bad packets only";
              tailf:cli-diff-dependency "../good" {
                tailf:xpath-root 3;
                tailf:cli-trigger-on-set;
              }
              leaf rx {
                tailf:info
                  "Monitor received traffic only";
                type empty;
              }
            }
          }
          container ip {
            tailf:info
              "Specify IP Access control rules";
            leaf access-group {
              tailf:info
                "Specify access control group";
              type exp-ip-acl-type;
            }
          }
          container mac {
            tailf:info
              "Specify MAC Access control rules";
            leaf access-group {
              tailf:info
                "Specify access control group";
              type string {
                tailf:info
                  "WORD;;ACL name";
              }
            }
          }
          container ipv6 {
            tailf:info
              "Specify IPv6 Access control rules";
            leaf access-group {
              tailf:info
                "Specify access control group";
              type string {
                tailf:info
                  "WORD;;ACL name";
              }
            }
          }
        }
      }
      container session-local {
        tailf:cli-drop-node-name;
        list session {
          tailf:info
            "Configure a SPAN session";
          tailf:cli-compact-syntax;
          tailf:cli-incomplete-command;
          tailf:cli-mode-name "config-mon-local";
          key "id";
          leaf id {
            tailf:cli-suppress-range;
            type uint16 {
              tailf:info
                "<1-1>;;SPAN session number";
              range "1";
            }
          }
          leaf type {
            tailf:info
              "Type of monitor session";
            tailf:cli-hide-in-submode;
            type enumeration {
              enum "local" {
                tailf:info
                  "Local SPAN Session";
              }
            }
          }
          leaf shutdown {
            tailf:info
              "Shutdown this session";
            type empty;
          }
          container source {
            tailf:info
              "SPAN source";
            container interface {
              tailf:info
                "SPAN destination interface";
              tailf:cli-compact-syntax;
              tailf:cli-sequence-commands {
                tailf:cli-reset-siblings;
              }
              uses interface-name-grouping;
              leaf hyphen {
                tailf:alt-name "-";
                tailf:cli-incomplete-command;
                type empty;
              }
              leaf port {
                tailf:cli-drop-node-name;
                type uint16 {
                  tailf:info
                    "<1-65535>;;Last port number in range";
                  range "1..65535";
                }
              }
            }
          }
          container destination {
            tailf:info
              "SPAN destination";
            container interface {
              tailf:info
                "SPAN destination interface";
              tailf:cli-compact-syntax;
              tailf:cli-sequence-commands {
                tailf:cli-reset-siblings;
              }
              uses interface-name-grouping;
              leaf hyphen {
                tailf:alt-name "-";
                tailf:cli-incomplete-command;
                type empty;
              }
              leaf port {
                tailf:cli-drop-node-name;
                type uint16 {
                  tailf:info
                    "<1-65535>;;Last port number in range";
                  range "1..65535";
                }
              }
            }
          }
        }
      }
      container session-erspan-source {
        tailf:cli-drop-node-name;
        list session {
          tailf:info
            "Configure a SPAN session";
          tailf:cli-compact-syntax;
          tailf:cli-incomplete-command;
          tailf:cli-mode-name "config-mon-erspan-src";
          key "id";
          leaf id {
            tailf:cli-suppress-range;
            type uint16 {
              tailf:info
                "<1-1024>;;SPAN session number";
              range "1..1024";
            }
          }
          leaf type {
            tailf:info
              "Type of monitor session";
            tailf:cli-hide-in-submode;
            type enumeration {
              enum "erspan-source" {
                tailf:info
                  "Encapsulated RSPAN Source Session";
              }
            }
          }
          leaf shutdown {
            tailf:info
              "Shutdown this session";
            type empty;
          }
          container source {
            tailf:info
              "SPAN source";
            container interface {
              tailf:info
                "SPAN destination interface";
              tailf:cli-compact-syntax;
              tailf:cli-sequence-commands {
                tailf:cli-reset-siblings;
              }
              uses interface-name-grouping;
              leaf hyphen {
                tailf:alt-name "-";
                tailf:cli-incomplete-command;
                type empty;
              }
              leaf port {
                tailf:cli-drop-node-name;
                type uint16 {
                  tailf:info
                    "<1-65535>;;Last port number in range";
                  range "1..65535";
                }
              }
            }
          }
          container destination {
            tailf:info
              "Specify Destination and their properties";
            tailf:cli-add-mode;
            tailf:cli-mode-name "config-mon-erspan-src-dst";
            tailf:cli-full-command;
            leaf erspan-id {
              tailf:info
                "Enter ERSPAN Identifier";
              type uint16 {
                tailf:info
                  "<1-1023>;;Erspan ID";
                range "1..1023";
              }
            }
            leaf mtu {
              tailf:info
                "Set the limitation size of ERSPAN encapsulation";
              type uint16 {
                tailf:info
                  "<64-9180>;;MTU size in bytes";
                range "64..9180";
              }
            }
            container ip {
              tailf:info
                "IP Properties";
              leaf address {
                tailf:info
                  "Enter IP Address";
                type inet:ipv4-address {
                  tailf:info
                    "A.B.C.D;;IP address";
                }
              }
            }
            container origin {
              tailf:info
                "Origin IP Properties";
              container ip {
                tailf:info
                  "Origin IP Properties";
                leaf address {
                  tailf:info
                    "Enter IP Address";
                  type inet:ipv4-address {
                    tailf:info
                      "A.B.C.D;;IP address";
                  }
                }
              }
            }
          }
        }
      }
      container session-erspan-destination {
        tailf:cli-drop-node-name;
        list session {
          tailf:info
            "Configure a SPAN session";
          tailf:cli-compact-syntax;
          tailf:cli-incomplete-command;
          tailf:cli-mode-name "config-mon-erspan-src";
          key "id";
          leaf id {
            tailf:cli-suppress-range;
            type uint16 {
              tailf:info
                "<1-1024>;;SPAN session number";
              range "1..1024";
            }
          }
          leaf type {
            tailf:info
              "Type of monitor session";
            tailf:cli-hide-in-submode;
            type enumeration {
              enum "erspan-destination" {
                tailf:info
                  "Encapsulated RSPAN Destination Session";
              }
            }
          }
          leaf shutdown {
            tailf:info
              "Shutdown this session";
            type empty;
          }
          container source {
            tailf:info
              "Specify Source and their properties";
            tailf:cli-add-mode;
            tailf:cli-mode-name "config-mon-erspan-dst-src";
            tailf:cli-full-command;
            leaf erspan-id {
              tailf:info
                "Enter ERSPAN Identifier";
              type uint16 {
                tailf:info
                  "<1-1023>;;Erspan ID";
                range "1..1023";
              }
            }
            container ip {
              tailf:info
                "IP Properties";
              tailf:cli-compact-syntax;
              tailf:cli-sequence-commands {
                tailf:cli-reset-siblings;
              }
              leaf address {
                tailf:info
                  "Enter IP Address";
                type inet:ipv4-address {
                  tailf:info
                    "A.B.C.D;;IP address";
                }
              }
              leaf force {
                tailf:info
                  "Change source IP Address for all ERSPAN Destination Sessions";
                type empty;
              }
            }
          }
        }
      }
      container session-conf {
        tailf:cli-drop-node-name;
        container session {
          tailf:info
            "Configure a SPAN session";
          leaf servicemodule {
            tailf:info
              "Use SPAN to enable service module";
            tailf:cli-boolean-no;
            tailf:cli-full-command;
            type boolean;
            default "true";
          }
        }
      }
      container event-trace {
        tailf:info
          "Tracing of system events";
        list event-trace-list {
          tailf:cli-drop-node-name;
          tailf:cli-suppress-mode;
          tailf:cli-delete-when-empty;
          tailf:cli-compact-syntax;
          key "name";
          leaf name {
            tailf:cli-multi-word-key;
            type string {
              tailf:info
                "WORD;;event trace entry";
            }
          }
        }
      }
    }
    container network-clock {
      tailf:ncs-device-type "cli-ned";
      tailf:display-when "not(../../ncs:module) or ../../ncs:module[ncs:name='tailf-ned-cisco-ios']";
      tailf:info
        "Network clock config commands";
      leaf revertive {
        tailf:info
          "Reference clock reverts to the highest QL/priority after failure";
        tailf:cli-full-command;
        type empty;
      }
      container synchronization {
        tailf:info
          "Network clock synchronization selection process";
        leaf automatic {
          tailf:info
            "ITU-T G.781/Telcordia standard based synchronization selection process";
          type empty;
        }
        container mode {
          tailf:info
            "synchronization networking mode";
          leaf QL-enabled {
            tailf:info
              "QL-enabled mode";
            type empty;
          }
        }
      }
      list input-source {
        tailf:info
          "Synchronization Input Source";
        tailf:cli-suppress-mode;
        tailf:cli-delete-when-empty;
        tailf:cli-compact-syntax;
        tailf:cli-incomplete-command;
        key "priority";
        leaf priority {
          type uint8 {
            tailf:info
              "<1-250>;;Priority";
            range "1..250";
          }
        }
        container interface {
          tailf:info
            "Specify Ethernet, Sonet or ToP Interface";
          uses interface-name-grouping;
        }
        container ptp {
          tailf:info
            "Select a PTP Clock as a Frequency Clock Source";
          leaf domain {
            tailf:info
              "Domain Number for the PTP Clock Source";
            type uint8 {
              tailf:info
                "<0-127>;;PTP Clock Domain Number";
              range "0..127";
            }
          }
        }
      }
      container output-source {
        tailf:info
          "Synchronization output Source";
        list system {
          tailf:cli-suppress-mode;
          tailf:cli-delete-when-empty;
          tailf:cli-compact-syntax;
          tailf:cli-incomplete-command;
          key "priority";
          leaf priority {
            type uint8 {
              tailf:info
                "<1-250>;;Priority";
              range "1..250";
            }
          }
          list External {
            tailf:info
              "External Interface (BITS/SSU/GPS)";
            tailf:cli-suppress-mode;
            tailf:cli-delete-when-empty;
            tailf:cli-compact-syntax;
            key "name";
            leaf name {
              type union {
                type string {
                  tailf:info
                    "<slot>/<card>/<port>;;Enter 0 if card or port parameter is not valid";
                }
                type enumeration {
                  enum "R0" {
                    tailf:info
                      "netsync RP0 bits source slot";
                  }
                  enum "R1" {
                    tailf:info
                      "netsync RP1 bits source slot";
                  }
                }
              }
            }
            leaf e1 {
              tailf:info
                "E1 Signal Mode";
              type enumeration {
                enum "cas" {
                  tailf:info
                    "E1 Channel Associated Signal Mode";
                }
                enum "crc4" {
                  tailf:info
                    "E1 With CRC4 Signal Mode";
                }
                enum "fas" {
                  tailf:info
                    "E1 Frame Alignment Signal Mode";
                }
              }
            }
            leaf ohms {
              tailf:cli-drop-node-name;
              type enumeration {
                enum "120ohms" {
                  tailf:info
                    "120 ohms";
                }
                enum "75ohms" {
                  tailf:info
                    "75 ohms";
                }
              }
            }
            leaf linecode {
              tailf:info
                "linecode option";
              type enumeration {
                enum "ami" {
                  tailf:info
                    "linecode ami";
                }
                enum "hdb3" {
                  tailf:info
                    "linecode hdb3";
                }
              }
            }
          }
        }
      }
      container wait-to-restore {
        tailf:cli-compact-syntax;
        tailf:cli-sequence-commands {
          tailf:cli-reset-siblings;
        }
        leaf seconds {
          tailf:cli-drop-node-name;
          type uint32 {
            tailf:info
              "<0-86400>;;sec (default 300 seconds)";
            range "0..86400";
          }
        }
        leaf global {
          tailf:info
            "Global";
          type empty;
        }
      }
    }
    container esmc {
      tailf:ncs-device-type "cli-ned";
      tailf:display-when "not(../../ncs:module) or ../../ncs:module[ncs:name='tailf-ned-cisco-ios']";
      tailf:info
        "Ethernet Synchronization Messaging Channel";
      leaf process {
        tailf:info
          "process";
        type empty;
      }
    }
    container netconf-yang {
      tailf:ncs-device-type "cli-ned";
      tailf:display-when "not(../../ncs:module) or ../../ncs:module[ncs:name='tailf-ned-cisco-ios']";
      tailf:info
        "Enable netconf-yang";
      container cisco-ia {
        tailf:info
          "Configure cisco-ia parameters";
        container snmp-trap-control {
          tailf:info
            "Configuration parameters for SNMP trap to NetConf notification processing";
          leaf trap-list {
            tailf:info
              "Configure translation of SNMP Traps to NetConf notifications";
            type string {
              tailf:info
                "WORD;;Enter SNMP trap OID string";
            }
          }
        }
      }
      container cisco-odm {
        tailf:info
          "Configure cisco-odm parameters";
        leaf actions {
          tailf:info
            "Configure cisco-odm actions";
          type string {
            tailf:info
              "WORD;;Enter action string";
          }
        }
      }
    }
    list tftp-server {
      tailf:ncs-device-type "cli-ned";
      tailf:display-when "not(../ncs:module) or ../ncs:module[ncs:name='tailf-ned-cisco-ios']";
      tailf:info
        "Provide TFTP service for netload requests";
      tailf:cli-suppress-mode;
      tailf:cli-delete-when-empty;
      tailf:cli-compact-syntax;
      key "name";
      leaf name {
        type string {
          tailf:info
            "Allow URL file TFTP load requests";
        }
      }
      leaf alias {
        tailf:info
          "file alias";
        type string {
          tailf:info
            "WORD;;file alias";
        }
      }
      leaf access-list {
        tailf:cli-drop-node-name;
        tailf:cli-disallow-value "alias";
        type std-ip-acl-type;
      }
    }
    container radius-server {
      tailf:ncs-device-type "cli-ned";
      tailf:display-when "not(../../ncs:module) or ../../ncs:module[ncs:name='tailf-ned-cisco-ios']";
      tailf:info
        "Modify RADIUS query parameters";
      container load-balance {
        tailf:info
          "Radius load-balancing options.";
        container method {
          tailf:info
            "Method by which the next host will be picked.";
          container least-outstanding {
            tailf:info
              "Pick the server with the least transactions outstanding.";
            presence "true";
          }
        }
      }
      container attribute {
        tailf:info
          "Customize selected radius attributes";
        list attribute-list {
          tailf:cli-drop-node-name;
          tailf:cli-suppress-mode;
          tailf:cli-delete-when-empty;
          key "id";
          leaf id {
            type uint8 {
              tailf:info
                "NUM;;attribute id";
            }
          }
          leaf on-for-login-auth {
            tailf:info
              "Send attribute 6 in authentication packet";
            type empty;
          }
          leaf support-multiple {
            tailf:info
              "Support multiple Service-Type values per Radius profile";
            type empty;
          }
          leaf mandatory {
            tailf:info
              "Enforce Service-Type attribute in Access-Accep";
            type empty;
          }
          leaf include-in-access-req {
            tailf:info
              "Send attribute 8 in access-req packet";
            type empty;
          }
          container access-request {
            tailf:info
              "Access-Request packet";
            leaf include {
              tailf:info
                "Include attribute";
              type empty;
            }
          }
        }
      }
      container dead-criteria {
        tailf:info
          "Set the criteria used to decide when a radius server ismarked dead";
        tailf:cli-compact-syntax;
        leaf time {
          tailf:info
            "The time during which no properly formed response must be recieved from the RADIUS server";
          type uint8 {
            tailf:info
              "<1-120>;;Time in seconds during which no response must be recieved from the RADIUS server in order to consider it dead";
            range "1..120";
          }
        }
        leaf tries {
          tailf:info
            "The number of times the router must fail to recieve a response from the radius server to mark it as dead";
          type uint8 {
            tailf:info
              "<1-100>;;Number of transmits to radius server without responses before marking server as dead";
            range "1..100";
          }
        }
      }
      leaf deadtime {
        tailf:info
          "Time to stop using a server that doesn't respond";
        type uint16 {
          tailf:info
            "<1-1440>;;time in minutes";
          range "1..1440";
        }
      }
      list host {
        tailf:info
          "Specify a RADIUS server";
        tailf:cli-suppress-mode;
        tailf:cli-delete-when-empty;
        tailf:cli-compact-syntax;
        tailf:cli-show-long-obu-diffs;
        ordered-by user;
        key "id";
        leaf id {
          type inet:host {
            tailf:info
              "Hostname or A.B.C.D;;IP address of RADIUS server";
          }
        }
        uses radius-server-grouping;
      }
      leaf retransmit {
        tailf:info
          "Specify the number of retries to active server";
        type uint8 {
          tailf:info
            "<0-100>;;Number of retries for a transaction (default is 3)";
          range "0..100";
        }
        default "3";
      }
      leaf timeout {
        tailf:info
          "Time to wait for a RADIUS server to reply";
        type uint16 {
          tailf:info
            "<1-1000>;;Wait time (default 5 seconds)";
          range "1..1000";
        }
        default "5";
      }
      container vsa {
        tailf:info
          "Vendor specific attribute configuration";
        container send {
          tailf:info
            "Send vendor-specific attributes in requests";
          leaf accounting {
            tailf:info
              "Send in accounting requests";
            type empty;
          }
          leaf authentication {
            tailf:info
              "Send in access requests";
            type empty;
          }
        }
      }
      container key {
        tailf:info
          "encryption key shared with the RADIUS servers";
        tailf:cli-compact-syntax;
        tailf:cli-sequence-commands;
        uses password-grouping;
      }
    }
    container radius {
      tailf:ncs-device-type "cli-ned";
      tailf:display-when "not(../../ncs:module) or ../../ncs:module[ncs:name='tailf-ned-cisco-ios']";
      tailf:info
        "RADIUS server configuration command";
      list filter {
        tailf:info
          "Packet filter configuration";
        key "id";
        leaf id {
          type string {
            tailf:info
              "WORD;;Name of the filter (max 31 characters, longer will be rejected";
          }
        }
        leaf match {
          tailf:cli-drop-node-name;
          tailf:cli-prefix-key;
          type enumeration {
            enum "match-all" {
              tailf:info
                "Filter if all of the attributes matches";
            }
            enum "match-any" {
              tailf:info
                "Filter if any of the attributes matches";
            }
          }
        }
      }
      list server {
        tailf:info
          "Server configuration";
        key "id";
        leaf id {
          type string {
            tailf:info
              "WORD;;Name for the radius server configuration";
          }
        }
        container address {
          tailf:info
            "Specify the radius server address";
          container ipv4 {
            tailf:info
              "IPv4 Address";
            tailf:cli-compact-syntax;
            tailf:cli-sequence-commands {
              tailf:cli-reset-siblings;
            }
            leaf host {
              tailf:cli-drop-node-name;
              type inet:host {
                tailf:info
                  "Hostname or A.B.C.D;;IPv4 Address of radius server";
              }
            }
            leaf auth-port {
              tailf:info
                "UDP port for RADIUS authentication server (default is 1645)";
              tailf:cli-optional-in-sequence;
              type uint16 {
                tailf:info
                  "<0-65535>;;Port number";
                range "0..65535";
              }
            }
            leaf acct-port {
              tailf:info
                "UDP port for RADIUS accounting server (default is 1646)";
              type uint16 {
                tailf:info
                  "<0-65535>;;Port number";
                range "0..65535";
              }
            }
          }
        }
        container backoff {
          tailf:info
            "Retry backoff pattern(Default is retransmits with constant delay)";
          container exponential {
            tailf:info
              "Exponential retransmit backoff";
            tailf:cli-compact-syntax;
            tailf:cli-sequence-commands {
              tailf:cli-reset-siblings;
            }
            presence "true";
            leaf max-delay {
              tailf:cli-optional-in-sequence;
              tailf:info
                "Max delay between retransmits(default is 3 min)";
              type uint8 {
                tailf:info
                  "<1-120>;;Max time (in minutes) to delay between retransmits";
                range "1..120";
              }
            }
            leaf backoff-retry {
              tailf:info
                "Exponential backoff retry number(default is 8)";
              type uint8 {
                tailf:info
                  "<1-50>;;Number of retransmits in the exponential backoff mode";
                range "1..50";
              }
            }
          }
        }
        container key {
          tailf:info
            "Per-server encryption key";
          tailf:cli-compact-syntax;
          tailf:cli-sequence-commands;
          leaf type {
            tailf:cli-drop-node-name;
            tailf:cli-optional-in-sequence;
            tailf:cli-incomplete-command;
            type enumeration {
              enum "0" {
                tailf:info
                  "Specifies an UNENCRYPTED key will follow";
              }
              enum "5" {
                tailf:info
                  "Specifies a HIDDEN key will follow";
              }
            }
          }
          leaf secret {
            tailf:cli-drop-node-name;
            tailf:cli-reset-container;
            tailf:cli-full-command;
            tailf:cli-disallow-value "0|5";
            tailf:meta-data "secret-password";
            type string {
              tailf:info
                "LINE;;The UNCRYPTED (cleartext) shared key";
            }
          }
        }
      }
    }
    container zone {
      tailf:ncs-device-type "cli-ned";
      tailf:display-when "not(../../ncs:module) or ../../ncs:module[ncs:name='tailf-ned-cisco-ios']";
      tailf:info
        "FW with zoning";
      list security {
        tailf:info
          "Security zone";
        tailf:cli-mode-name "config-sec-zone";
        tailf:cli-full-command;
        key "id";
        leaf id {
          type string {
            tailf:info
              "WORD;;Name of security zone";
          }
        }
        leaf description {
          tailf:info
            "Zone description";
          tailf:cli-multi-value;
          tailf:cli-preformatted;
          tailf:cli-full-command;
          type string {
            tailf:info
              "LINE;;Description of zone (up to 200 characters)";
          }
        }
        leaf protection {
          tailf:info
            "config syn cookie protection against sync flood";
          tailf:cli-diff-dependency "../../../parameter-map" {
            tailf:xpath-root 3;
          }
          type string {
            tailf:info
              "WORD;;parameter map name";
          }
        }
      }
    }
    container zone-pair {
      tailf:ncs-device-type "cli-ned";
      tailf:display-when "not(../../ncs:module) or ../../ncs:module[ncs:name='tailf-ned-cisco-ios']";
      tailf:info
        "Zone pair command";
      list security {
        tailf:info
          "Zone-pair name";
        tailf:cli-mode-name "config-sec-zone-pair";
        tailf:cli-sequence-commands {
          tailf:cli-reset-siblings;
        }
        key "id";
        leaf id {
          type string {
            tailf:info
              "WORD;;Name of zone-pair";
          }
        }
        leaf source {
          tailf:info
            "Source zone";
          tailf:cli-hide-in-submode;
          tailf:non-strict-leafref {
            path "../../../zone/security/id";
          }
          type string {
            tailf:info
              "WORD;;Name of source zone";
          }
        }
        leaf destination {
          tailf:info
            "Destination zone";
          tailf:cli-hide-in-submode;
          tailf:non-strict-leafref {
            path "../../../zone/security/id";
          }
          type string {
            tailf:info
              "WORD;;Name of destination zone";
          }
        }
        leaf description {
          tailf:info
            "Zone description";
          tailf:cli-break-sequence-commands;
          tailf:cli-multi-value;
          tailf:cli-preformatted;
          tailf:cli-full-command;
          type string {
            tailf:info
              "LINE;;Description of zone (up to 200 characters)";
            length "1..200";
          }
        }
        container service-policy {
          tailf:info
            "Configure CBAC Service Policy";
          container type {
            tailf:info
              "Service Policy type";
            leaf inspect {
              tailf:info
                "Configure CBAC Service Policy type inspect";
              tailf:cli-remove-before-change;
              tailf:non-strict-leafref {
                path "../../../../../policy-map/name";
              }
              type string {
                tailf:info
                  "WORD;;output Policy-map name";
              }
            }
          }
        }
      }
    }
    list alarm-contact {
      tailf:ncs-device-type "cli-ned";
      tailf:display-when "not(../ncs:module) or ../ncs:module[ncs:name='tailf-ned-cisco-ios']";
      tailf:info
        "Configure the system alarm contact settings";
      tailf:cli-suppress-mode;
      tailf:cli-delete-when-empty;
      tailf:cli-incomplete-command;
      key "name";
      leaf name {
        type union {
          type uint8 {
            tailf:info
              "<1-4>;;Alarm contact number";
            range "1..4";
          }
          type enumeration {
            enum "all" {
              tailf:info
                "Configure all alarm contacts";
            }
          }
        }
      }
      leaf description {
        tailf:cli-multi-value;
        tailf:cli-preformatted;
        tailf:cli-full-command;
        type string {
          tailf:info
            "LINE;;Description";
          length "1..80";
        }
      }
      leaf severity {
        tailf:info
          "Set the severity level reported";
        type enumeration {
          enum "critical" {
            tailf:info
              "Critical alarm severity";
          }
          enum "major" {
            tailf:info
              "Major alarm severity";
          }
          enum "minor" {
            tailf:info
              "Minor alarm severity";
          }
        }
      }
      leaf trigger {
        tailf:info
          "Set the alarm trigger";
        type enumeration {
          enum "closed" {
            tailf:info
              "Assert alarm when contact is closed";
          }
          enum "open" {
            tailf:info
              "Assert alarm when contact is open";
          }
        }
      }
    }
    container mpls {
      tailf:ncs-device-type "cli-ned";
      tailf:display-when "not(../../ncs:module) or ../../ncs:module[ncs:name='tailf-ned-cisco-ios']";
      tailf:info
        "Configure MPLS parameters";
      container atm {
        tailf:info
          "Configure ATM options";
        leaf disable-headend-vc {
          tailf:info
            "Dedicated lsc capability: In this mode headend Tag VCs are disabled.";
          type empty;
        }
      }
      leaf cos-map {
        tailf:info
          "Configure MPLS CoS ATM Multi-VC CoS Map";
        tailf:cli-full-command;
        type uint8 {
          range "1..255" {
            tailf:info
              "<1-255>;;cos-map number";
          }
        }
      }
      leaf ip {
        tailf:cli-boolean-no;
        tailf:cli-full-command;
        type boolean;
        default "true";
      }
      container mpls-ip-conf {
        tailf:cli-drop-node-name;
        container ip {
          tailf:info
            "Dynamic MPLS forwarding for IP";
          tailf:cli-incomplete-no;
          tailf:cli-incomplete-command;
          leaf default-route {
            tailf:info
              "Allow MPLS forwarding for ip default route";
            tailf:cli-full-command;
            type empty;
          }
          choice propagate-ttl-choice {
            container propagate-ttl-conf {
              tailf:cli-drop-node-name;
              leaf propagate-ttl {
                tailf:info
                  "Propagate IP TTL into the label stack";
                tailf:cli-boolean-no;
                tailf:cli-full-command;
                type boolean;
                default "true";
              }
            }
            container propagate-ttl {
              tailf:cli-incomplete-command;
              tailf:cli-incomplete-no;
              leaf forwarded {
                tailf:info
                  "Propagate IP TTL for forwarded traffic";
                tailf:cli-boolean-no;
                tailf:cli-full-command;
                type boolean;
                default "true";
              }
            }
          }
          container ttl-expiration {
            tailf:info
              "Control MPLS TTL expiration behavior";
            leaf pop {
              tailf:info
                "Popping labels on TTL expiration";
              type uint8 {
                tailf:info
                  "<1-6>;;Popping all labels if original packet has less than N labels";
                range "1..6";
              }
            }
          }
        }
      }
      container label {
        tailf:info
          "Label properties";
        container atm {
          tailf:info
            "Configure ATM options";
          leaf disable-headend-vc {
            tailf:info
              "Dedicated lsc capability: In this mode headend Tag VCs are disabled.";
            type empty;
          }
        }
        leaf protocol {
          tailf:info
            "Set platform default label distribution protocol";
          tailf:cli-full-command;
          type enumeration {
            enum "ldp" {
              tailf:info
                "Use LDP (default)";
            }
            enum "tdp" {
              tailf:info
                "Use TDP";
            }
          }
        }
        container range {
          tailf:info
            "Label range";
          tailf:cli-compact-syntax;
          tailf:cli-sequence-commands {
            tailf:cli-reset-siblings;
          }
          leaf min {
            tailf:cli-drop-node-name;
            tailf:cli-incomplete-command;
            type uint32 {
              tailf:info
                "<16-1048575>;;Minimum label value";
              range "16..1048575";
            }
          }
          leaf max {
            tailf:cli-drop-node-name;
            type uint32 {
              tailf:info
                "<16-1048575>;;Maximum label value";
              range "16..1048575";
            }
          }
          leaf static {
            tailf:info
              "Specify block of labels for static bindings";
            tailf:cli-incomplete-command;
            type empty;
          }
          leaf static-min {
            tailf:cli-drop-node-name;
            tailf:cli-incomplete-command;
            type uint32 {
              tailf:info
                "NUM;;Upper minimum static label value";
            }
          }
          leaf static-max {
            tailf:cli-drop-node-name;
            type uint32 {
              tailf:info
                "NUM;;Maximum static label value";
            }
          }
        }
      }
      container ldp {
        tailf:info
          "Label Distribution Protocol";
        leaf advertise-labels {
          tailf:cli-boolean-no;
          tailf:cli-full-command;
          type boolean;
          default "true";
        }
        leaf nsr {
          tailf:info
            "Enable Non Stop Routing for LDP";
          tailf:cli-full-command;
          type empty;
        }
        container advertise-labels-conf {
          tailf:cli-drop-node-name;
          container advertise-labels {
            tailf:info
              "Label advertisements";
            tailf:cli-incomplete-command;
            tailf:cli-incomplete-no;
            container for {
              tailf:info
                "Access-list specifying controls on destination prefixes";
              tailf:cli-compact-syntax;
              tailf:cli-sequence-commands;
              leaf from {
                tailf:cli-drop-node-name;
                type string {
                  tailf:info
                    "WORD;;IP access-list for destination prefixes; name or number (1-99)";
                }
              }
              leaf to {
                tailf:info
                  "Access-list specifying controls on LDP peers";
                type string {
                  tailf:info
                    "WORD;;IP access-list for LDP peers; name or number (1-99)";
                }
              }
            }
            container interface {
              tailf:info
                "Advertise /32 interface address";
              uses interface-name-grouping;
            }
            leaf oldstyle {
              tailf:info
                "Use old style (TDP) method for matching prefix acl";
              tailf:cli-full-command;
              type empty;
            }
          }
        }
        container password {
          tailf:info
            "Configure LDP MD5 password";
          container required {
            tailf:info
              "MD5 password is required for the peer";
            presence "true";
          }
          container fallback {
            tailf:info
              "Specifies a fallback password will follow";
            tailf:cli-compact-syntax;
            tailf:cli-sequence-commands;
            choice fallback-choice {
              leaf key-chain {
                tailf:info
                  "Specifies a key-chain name will follow";
                tailf:cli-full-command;
                type string {
                  tailf:info
                    "LINE;;name of key-chain";
                }
                tailf:non-strict-leafref {
                  path "../../../../../key/chain/name";
                }
              }
              case password-case {
                uses password-grouping;
              }
            }
          }
        }
        container atm {
          tailf:info
            "Configure ATM MPLS options";
          leaf control-mode {
            tailf:info
              "Select LSP setup control mode for MPLS VCs";
            tailf:cli-full-command;
            type enumeration {
              enum "independent" {
                tailf:info
                  "Independent Downstream on Demand Label VC setup";
              }
              enum "ordered" {
                tailf:info
                  "Ordered Dowstream on Demand Label VC setup";
              }
            }
          }
          leaf vc-merge {
            tailf:info
              "Select VC merge capability";
            tailf:cli-full-command;
            tailf:cli-boolean-no;
            type boolean;
            default "true";
          }
        }
        container backoff {
          tailf:info
            "Set LDP session backoff parameters";
          tailf:cli-sequence-commands;
          tailf:cli-compact-syntax;
          leaf initial {
            tailf:cli-drop-node-name;
            tailf:cli-incomplete-command;
            type uint32 {
              tailf:info
                "<5-2147483>;;Initial session backoff time (seconds)";
              range "5..2147483";
            }
          }
          leaf max {
            tailf:cli-drop-node-name;
            type uint32 {
              tailf:info
                "<5-2147483>;;Maximum session backoff time (seconds)";
              range "5..2147483";
            }
          }
        }
        container discovery {
          tailf:info
            "LDP discovery";
          container hello {
            tailf:info
              "LDP discovery Hello";
            leaf holdtime {
              tailf:info
                "LDP discovery Hello holdtime";
              type uint16 {
                tailf:info
                  "<1-65535>;;Holdtime in seconds";
                range "1..65535";
              }
            }
            leaf interval {
              tailf:info
                "LDP discovery Hello interval";
              tailf:cli-full-command;
              type uint16 {
                tailf:info
                  "<1-65535>;;Hello interval in seconds";
                range "1..65535";
              }
            }
          }
          container targeted-hello {
            tailf:info
              "LDP discovery Targeted Hello";
            container accept {
              tailf:info
                "Accept targeted hellos";
              tailf:cli-delete-when-empty;
              presence "Accept targeted hellos";
              leaf from {
                tailf:info
                  "Access list to specify acceptable targeted hello sources";
                type string {
                  tailf:info
                    "WORD;;IP access-list for acceptable targeted hello sources";
                }
              }
            }
            leaf holdtime {
              tailf:info
                "LDP discovery Hello holdtime";
              type uint16 {
                tailf:info
                  "<1-65535>;;Holdtime in seconds";
                range "1..65535";
              }
            }
            leaf interval {
              tailf:info
                "LDP discovery Hello interval";
              tailf:cli-full-command;
              type uint16 {
                tailf:info
                  "<1-65535>;;Hello interval in seconds";
                range "1..65535";
              }
            }
          }
        }
        container explicit-null {
          tailf:info
            "Advertise Explicit Null label in place of Implicit Null";
          tailf:cli-delete-when-empty;
          presence "true";
          leaf for {
            tailf:info
              "Access-list specifying controls on destination prefixes";
            type string {
              tailf:info
                "WORD;;IP access-list for destination prefixes; name or number (1-99)";
            }
          }
          leaf to {
            tailf:info
              "Access-list specifying controls on LDP peers";
            type string {
              tailf:info
                "WORD;;IP access-list for LDP peers; name or number (1-99)";
            }
          }
        }
        leaf loop-detection {
          tailf:info
            "Enable LDP Loop Detection";
          tailf:cli-full-command;
          type empty;
        }
        container graceful-restart {
          tailf:info
            "Configure Graceful Restart timers";
          presence "Configure Graceful Restart timers";
          container timers {
            tailf:info
              "Configure Graceful Restart timers";
            leaf forwarding-holding {
              tailf:info
                "Forwarding State Holding time";
              tailf:cli-full-command;
              type uint16 {
                tailf:info
                  "<30-600>;;seconds";
                range "30..600";
              }
            }
            leaf max-recovery {
              tailf:info
                "Max-Recovery time";
              tailf:cli-full-command;
              type uint16 {
                tailf:info
                  "<15-600>;;seconds";
                range "15..600";
              }
            }
            leaf neighbor-liveness {
              tailf:info
                "Neighbor-Liveness time";
              tailf:cli-full-command;
              type uint16 {
                tailf:info
                  "<5-300>;;seconds";
                range "5..600";
              }
            }
          }
        }
        leaf holdtime {
          tailf:info
            "LDP session holdtime";
          tailf:cli-full-command;
          type uint32 {
            tailf:info
              "<15-2147483>;;Holdtime in seconds";
            range "15..2147483";
          }
        }
        container logging {
          tailf:info
            "Enable LDP logging";
          leaf neighbor-changes {
            tailf:info
              "Log LDP neighbor state changes";
            type empty;
          }
        }
        leaf maxhops {
          tailf:info
            "Limit hop count for LDP LSP setup";
          tailf:cli-full-command;
          type uint8 {
            tailf:info
              "<1-255>;;Maximum hop count value";
          }
        }
        list neighbor {
          tailf:info
            "Configure neighbor parameters";
          tailf:cli-suppress-mode;
          tailf:cli-delete-when-empty;
          key "address";
          leaf address {
            type inet:ipv4-address {
              tailf:info
                "A.B.C.D;;IP address for LDP neighbor";
            }
          }
          leaf implicit-withdraw {
            tailf:info
              "Enable LDP Implicit Withdraw Label";
            tailf:cli-full-command;
            type empty;
          }
          container labels {
            tailf:info
              "Configure label binding exchange controls";
            leaf accept {
              tailf:info
                "Specify label bindings to accept";
              type string {
                tailf:info
                  "WORD;;IP access-list for LDP peers; name or number (1-99)";
              }
            }
          }
          container password {
            tailf:info
              "Set a password";
            tailf:cli-flatten-container;
            tailf:cli-compact-syntax;
            tailf:cli-sequence-commands;
            uses password-grouping;
          }
          container targeted {
            tailf:info
              "Establish targeted session";
            tailf:cli-delete-when-empty;
            presence "Establish targeted session";
            leaf protocol {
              tailf:cli-drop-node-name;
              type enumeration {
                enum "ldp" {
                  tailf:info
                    "User LDP";
                }
                enum "tdp" {
                  tailf:info
                    "Use TDP";
                }
              }
            }
          }
        }
        container request-labels {
          tailf:info
            "Access list to specify valid downstream on demand destinations.";
          leaf for {
            tailf:info
              "Access list to specify acceptable downstream on demand destinations";
            type string {
              tailf:info
                "WORD;;IP access-list for destination prefixes; name or number (1-99)";
            }
          }
        }
        container router-id {
          tailf:info
            "Select interface to prefer for LDP identifier address";
          tailf:cli-compact-syntax;
          tailf:cli-sequence-commands {
            tailf:cli-reset-siblings;
          }
          leaf interface {
            tailf:cli-drop-node-name;
            tailf:cli-diff-dependency "../../../../interface" {
              tailf:xpath-root 3;
            }
            type string {
              tailf:info
                "WORD;;intrace name";
            }
          }
          leaf force {
            tailf:info
              "Forcibly change the LDP router id";
            type empty;
          }
        }
        container session {
          tailf:info
            "Configure session parameters";
          container protection {
            tailf:info
              "Configure session protection parameters";
            tailf:cli-compact-syntax;
            presence "true";
            leaf duration {
              tailf:info
                "Period to sustain session protection after loss of link discovery";
              type union {
                type enumeration {
                  enum "infinite" {
                    tailf:info
                      "Protect session forever after loss of link discovery";
                  }
                }
                type uint32 {
                  tailf:info
                    "<30-2147483>;;Holdup time in seconds";
                  range "30..2147483";
                }
              }
            }
          }
        }
        container label {
          tailf:info
            "LDP label mode";
          tailf:cli-add-mode;
          tailf:cli-mode-name "config-ldp-lbl";
          container allocate {
            tailf:info
              "Allocate local labels for specified destination prefixes";
            container global {
              tailf:info
                "Specify global Routing/Forwarding instance";
              tailf:cli-delete-when-empty;
              presence "true";
              choice global-choice {
                leaf host-routes {
                  tailf:info
                    "allocate local label for host routes only";
                  type empty;
                }
                leaf prefix-list {
                  tailf:info
                    "Specify a prefix list for local label filtering";
                  type string {
                    tailf:info
                      "WORD;;IP prefix-list for destination prefixes; name or number (1-99)";
                  }
                }
              }
            }
          }
        }
        container igp {
          tailf:info
            "Configure IGP-related LDP parameters";
          container sync {
            tailf:info
              "Configure LDP-IGP Synchronization parameters";
            leaf holddown {
              tailf:info
                "Configure the LDP-IGP Synchronization holddown time";
              type uint32 {
                tailf:info
                  "<1-2147483647>;;Hold down time in milliseconds";
              }
            }
          }
        }
      }
      container prefix-map {
        tailf:info
          "Configure MPLS CoS Tag-VC Multi-VC Prefix Map";
        tailf:cli-compact-syntax;
        tailf:cli-sequence-commands;
        leaf nr {
          tailf:cli-drop-node-name;
          tailf:cli-incomplete-command;
          type uint8 {
            tailf:info
              "<1-255>;;prefix-map number";
            range "1..255";
          }
        }
        leaf access-list {
          tailf:info
            "Configure access-list for this prefix-map";
          tailf:cli-incomplete-command;
          type uint8 {
            tailf:info
              "<1-255>;;access-list number";
            range "1..255";
          }
        }
        leaf cos-map {
          tailf:info
            "Configure cos-map for this prefix-map";
          type uint8 {
            tailf:info
              "<1-255>;;cos-map number";
            range "1..255";
          }
        }
      }
      container traffic-eng {
        tailf:info
          "Configure Traffic Engineering parameters";
        container auto-bw {
          tailf:info
            "auto-bw parameters";
          container timers {
            tailf:info
              "Enable auto-bw Timers Collection and Application";
            presence "Enable auto-bw Timers Collection and Application";
            leaf frequency {
              tailf:info
                "Interval between auto-bw data collection";
              type uint32 {
                tailf:info
                  "<1-604800>;;seconds between auto-bw";
                range "1..604800";
              }
            }
          }
        }
        container link-management {
          tailf:info
            "Link Management configuration";
          container timers {
            tailf:info
              "Link Management timers configuration";
            leaf bandwidth-hold {
              tailf:info
                "Link Management bandwidth hold timer";
              tailf:cli-full-command;
              type uint16 {
                tailf:info
                  "<1-300>;;seconds";
                range "1..300";
              }
            }
            leaf periodic-flooding {
              tailf:info
                "Link Management periodic flooding interval";
              tailf:cli-full-command;
              type uint16 {
                tailf:info
                  "<0-3600>;;seconds";
                range "0..3600";
              }
            }
          }
        }
        container logging {
          tailf:info
            "Trap logging configuration";
          container lsp {
            tailf:info
              "LSP-specific traps logging configuration";
            container path-errors {
              tailf:info
                "Log LSP Path Error traps";
              presence "Log LSP Path Error traps";
              leaf access-list {
                tailf:cli-drop-node-name;
                type exp-ip-acl-type;
              }
            }
            container preemption {
              tailf:info
                "Log LSP Preemption traps";
              presence "Log LSP Preemption traps";
              leaf access-list {
                tailf:cli-drop-node-name;
                type exp-ip-acl-type;
              }
            }
            container reservation-errors {
              tailf:info
                "Log LSP Reservation Error traps";
              presence "Log LSP Reservation Error traps";
              leaf access-list {
                tailf:cli-drop-node-name;
                type exp-ip-acl-type;
              }
            }
            container setups {
              tailf:info
                "Log LSP Establishment Traps";
              presence "Log LSP Establishment Traps";
              leaf access-list {
                tailf:cli-drop-node-name;
                type exp-ip-acl-type;
              }
            }
            container teardowns {
              tailf:info
                "Log LSP Teardown Traps";
              presence "Log LSP Teardown Traps";
              leaf access-list {
                tailf:cli-drop-node-name;
                type exp-ip-acl-type;
              }
            }
          }
          container tunnel {
            tailf:info
              "Tunnel-specific traps logging configuration";
            container lsp-selection {
              tailf:info
                "Log Tunnel LSP Selection traps";
              presence "Log Tunnel LSP Selection traps";
              leaf access-list {
                tailf:cli-drop-node-name;
                type exp-ip-acl-type;
              }
            }
            container path {
              tailf:info
                "Log Tunnel Path-related traps";
              container change {
                tailf:info
                  "Log Tunnel Path change traps";
                presence "Log Tunnel Path change traps";
                leaf access-list {
                  tailf:cli-drop-node-name;
                  type exp-ip-acl-type;
                }
              }
            }
          }
        }
        container auto-tunnel {
          tailf:info
            "Configure automatic TE tunnels";
          leaf backup {
            tailf:info
              "Configure auto-tunnel backup tunnel";
            tailf:cli-full-command;
            type empty;
          }
          container backup-conf {
            tailf:cli-drop-node-name;
            container backup {
              tailf:info
                "Configure auto-tunnel backup tunnel";
              tailf:cli-incomplete-no;
              tailf:cli-incomplete-command;
              leaf nhop-only {
                tailf:info
                  "Automatically create n-hop backup tunnels only";
                type empty;
              }
              container tunnel-num {
                tailf:info
                  "Configure tunnel I/F numbers for backup auto-tunnels";
                tailf:cli-compact-syntax;
                tailf:cli-sequence-commands;
                leaf min {
                  tailf:info
                    "Configure the starting id-range";
                  tailf:cli-incomplete-command;
                  type uint16 {
                    tailf:info
                      "<0-65535>;;starting tunnel number range";
                  }
                }
                leaf max {
                  tailf:info
                    "Configure the ending id-range";
                  type uint16 {
                    tailf:info
                      "<0-65535>;;ending tunnel number range";
                  }
                }
              }
            }
          }
          container primary {
            tailf:info
              "Automatically create one-hop primary tunnels";
            container config {
              tailf:info
                "Config commands to apply to all primary auto-tunnels";
              container mpls {
                tailf:info
                  "Configure dynamic MPLS forwarding";
                leaf ip {
                  tailf:info
                    "Configure dynamic MPLS forwarding for ip";
                  type empty;
                }
              }
            }
            container tunnel-num {
              tailf:info
                "Configure tunnel I/F numbers for primary auto-tunnels";
              tailf:cli-compact-syntax;
              tailf:cli-sequence-commands;
              leaf min {
                tailf:info
                  "Configure the starting id-range";
                type uint16 {
                  tailf:info
                    "<0-65535>;;starting tunnel number range";
                }
              }
              leaf max {
                tailf:info
                  "Configure the ending id-range";
                type uint16 {
                  tailf:info
                    "<0-65535>;;ending tunnel number range";
                }
              }
            }
          }
        }
        container path-selection {
          tailf:info
            "Path Selection Configuration";
          leaf metric {
            tailf:info
              "Metric Type Configuration";
            tailf:cli-full-command;
            type enumeration {
              enum "igp" {
                tailf:info
                  "Use IGP metric";
              }
              enum "te" {
                tailf:info
                  "User TE metric";
              }
            }
            default "te";
          }
          container overload {
            tailf:info
              "Overload Node Configuration";
            leaf allow {
              tailf:info
                "Allow overloaded nodes in CSPFs";
              type enumeration {
                enum "head" {
                  tailf:info
                    "Allow overloaded head node in TE CSPF";
                }
                enum "middle" {
                  tailf:info
                    "Allow overloaded middle node in TE CSPF";
                }
                enum "tail" {
                  tailf:info
                    "Allow overloaded middle node in TE CSPF";
                }
              }
            }
          }
        }
        container reoptimize {
          tailf:info
            "Reoptimization parameters";
          container events {
            tailf:info
              "Reoptimization triggers";
            leaf link-up {
              tailf:info
                "Reoptimize tunnels on link up events";
              type empty;
            }
          }
          container timers {
            tailf:info
              "Reoptimization timers";
            container delay {
              tailf:info
                "Delay reoptimization action";
              leaf cleanup {
                tailf:info
                  "Delay cleanup of reoptimized LSP";
                tailf:cli-full-command;
                type uint8 {
                  tailf:info
                    "<0-60>;;seconds to delay cleanup of replaced tunnel LSP";
                  range "0..60";
                }
              }
              leaf installation {
                tailf:info
                  "Delay replacement of current LSP by reoptimized LSP";
                tailf:cli-full-command;
                type uint16 {
                  tailf:info
                    "<0-3600>;;seconds to delay replacement of tunnel LSP";
                  range "0..3600";
                }
              }
            }
            leaf frequency {
              tailf:info
                "Interval between reoptimization scans";
              tailf:cli-full-command;
              type uint32 {
                tailf:info
                  "<0-604800>;;seconds between reoptimizations (0 disables reoptimization)";
                range "0..604800";
              }
            }
          }
        }
        container signalling {
          tailf:info
            "Traffic Engineering Signalling Parameters";
          container advertise {
            tailf:info
              "Signalling advertisement parameters";
            container implicit-null {
              tailf:info
                "Use MPLS encoding for Implicit-Null Label in signalling messages";
              presence "Use MPLS encoding for Implicit-Null Label in signalling messages";
              leaf nr {
                tailf:cli-drop-node-name;
                type uint8 {
                  tailf:info
                    "<1-99>;;Number of IP access-list to determine applicable signalling peers";
                  range "1..99";
                }
              }
            }
          }
          container forwarding {
            tailf:info
              "Control interaction of LSP signalling and LFIB maintenance";
            leaf sync {
              tailf:info
                "Program linecard LFIBs before signalling LSP label upstream";
              type empty;
            }
          }
          container restart {
            tailf:info
              "Signalling restart parameters";
            container neighbors {
              tailf:info
                "Identify signalling restart capable neighbors";
              presence "Identify signalling restart capable neighbors";
              leaf nr {
                tailf:cli-drop-node-name;
                type uint8 {
                  tailf:info
                    "<1-99>;;Number of IP access-list to determine applicable signalling peers";
                  range "1..99";
                }
              }
            }
          }
        }
        container topology {
          tailf:info
            "Topology Database Configuration";
          container holddown {
            tailf:info
              "Topology Database hold down timers";
            leaf sigerr {
              tailf:info
                "Link hold down time for signalling errors";
              type uint16 {
                tailf:info
                  "<0-300>;;Hold down time in seconds";
                range "0..300";
              }
            }
          }
        }
        leaf tunnels {
          tailf:info
            "Traffic Engineering tunnels";
          tailf:cli-full-command;
          type empty;
        }
      }
      leaf propagate-cos {
        type empty;
      }
      container discovery {
        tailf:info
          "Configure LSP discovery";
        container vpn {
          tailf:info
            "Configure Layer 3 VPN LSP discovery";
          leaf interval {
            tailf:info
              "Configure discovery refresh interval";
            type uint32 {
              tailf:info
                "<1-86400>;;Refresh interval in seconds";
              range "1..86400";
            }
          }
          leaf next-hop {
            tailf:info
              "Configure Layer 3 VPN LSP discovery";
            type empty;
          }
        }
      }
    }
    container clns {
      tailf:ncs-device-type "cli-ned";
      tailf:display-when "not(../../ncs:module) or ../../ncs:module[ncs:name='tailf-ned-cisco-ios']";
      tailf:info
        "Global CLNS configuration subcommands";
      leaf routing {
        tailf:info
          "Enable clns routing";
        type empty;
      }
      list filter-set {
        tailf:info
          "Define CLNS filter set";
        tailf:cli-suppress-mode;
        tailf:cli-delete-when-empty;
        tailf:cli-compact-syntax;
        tailf:cli-sequence-commands;
        tailf:cli-incomplete-command;
        key "name";
        leaf name {
          type string {
            tailf:info
              "WORD;;Name of filter set";
          }
        }
        leaf operation {
          tailf:cli-drop-node-name;
          tailf:cli-incomplete-command;
          type enumeration {
            enum "deny" {
              tailf:info
                "Deny matching addresses";
            }
            enum "permit" {
              tailf:info
                "Permit matching addresses";
            }
          }
        }
        leaf template {
          tailf:cli-drop-node-name;
          type string {
            tailf:info
              "WORD;;Address template to filter";
          }
        }
      }
    }
    container l3-over-l2 {
      tailf:ncs-device-type "cli-ned";
      tailf:display-when "not(../../ncs:module) or ../../ncs:module[ncs:name='tailf-ned-cisco-ios']";
      tailf:info
        "L3 over L2 specific configuration";
      container flush {
        tailf:info
          "configure whether L3 buffers should be flushed";
        leaf buffers {
          tailf:info
            "Enable flushing of L3 buffers for L3-over-L2 support";
          type empty;
        }
      }
    }
    container l3vpn {
      tailf:ncs-device-type "cli-ned";
      tailf:display-when "not(../../ncs:module) or ../../ncs:module[ncs:name='tailf-ned-cisco-ios']";
      tailf:info
        "l3vpn encapsulation ip commands";
      container encapsulation {
        tailf:info
          "l3vpn encapsulation ip";
        list ip {
          tailf:info
            "l3vpn encapsulation ip";
          tailf:cli-mode-name "config-l3vpn-encap-ip";
          tailf:cli-full-command;
          key "name";
          leaf name {
            type string {
              tailf:info
                "WORD;;profile name";
            }
          }
          container transport {
            tailf:info
              "transport mode";
            container ipv4 {
              tailf:info
                "transport ipv4 mode";
              presence "true";
              container source {
                tailf:info
                  "transport source";
                uses interface-name-grouping;
              }
            }
          }
        }
      }
    }
    container router {
      tailf:ncs-device-type "cli-ned";
      tailf:display-when "not(../../ncs:module) or ../../ncs:module[ncs:name='tailf-ned-cisco-ios']";
      tailf:info
        "Enable a routing process";
      container mobile {
        tailf:info
          "Mobile routes";
        tailf:cli-add-mode;
        tailf:cli-mode-name "config-router";
        tailf:cli-diff-dependency "../../ip/routing" {
          tailf:xpath-root 3;
          tailf:cli-trigger-on-set;
        }
        presence "true";
      }
      list bgp {
        tailf:info
          "Border Gateway Protocol (BGP)";
        tailf:cli-mode-name "config-router";
        tailf:cli-diff-dependency "../../ip/routing" {
          tailf:xpath-root 3;
          tailf:cli-trigger-on-set;
        }
        tailf:cli-diff-dependency "../../route-map" {
          tailf:xpath-root 3;
        }
        tailf:cli-diff-dependency "../../ip/prefix-list" {
          tailf:xpath-root 3;
        }
        max-elements 1;
        key "as-no";
        leaf as-no {
          tailf:cli-suppress-range;
          tailf:cli-diff-dependency "/ios:router/bgp" {
            tailf:xpath-root 3;
            tailf:cli-trigger-on-set;
          }
          type bgp-as-no-type;
        }
        container template {
          tailf:info
            "Enter template command mode";
          list peer-policy {
            tailf:info
              "Template configuration for policy parameters";
            tailf:cli-mode-name "config-router-ptmp";
            tailf:cli-exit-command "exit-peer-policy" {
              tailf:info
                "Exit from template configuration mode";
            }
            key "name";
            leaf name {
              type string {
                tailf:info
                  "WORD;;Name of peer-policy template";
              }
            }
            leaf peer-group {
              tailf:hidden "all";
              type empty;
            }
            leaf remote-as {
              tailf:hidden "all";
              type empty;
            }
            leaf activate {
              tailf:hidden "all";
              type empty;
            }
            container inherit {
              tailf:info
                "Inherit a template";
              tailf:cli-compact-syntax;
              tailf:cli-sequence-commands {
                tailf:cli-reset-siblings;
              }
              tailf:cli-diff-dependency "../peer-group" {
                tailf:xpath-root 3;
              }
              tailf:cli-diff-dependency "../remote-as" {
                tailf:xpath-root 3;
              }
              tailf:cli-diff-dependency "../activate" {
                tailf:xpath-root 3;
              }
              leaf peer-policy {
                tailf:info
                  "Inherit a peer-policy template";
                tailf:cli-incomplete-command;
                tailf:non-strict-leafref {
                  path "../../../peer-policy/name";
                }
                type string {
                  tailf:info
                    "WORD;;Template name";
                }
              }
              leaf sequence {
                tailf:cli-drop-node-name;
                tailf:cli-full-command;
                type uint16 {
                  tailf:info
                    "<1-65535>;;Sequence number";
                  range "1..65535";
                }
              }
              leaf peer-session {
                tailf:hidden "all";
                type empty;
              }
            }
            uses router-bgp-peer-policy-grouping;
          }
          list peer-session {
            tailf:info
              "Template configuration for session parameters";
            tailf:cli-mode-name "config-router-stmp";
            tailf:cli-exit-command "exit-peer-session" {
              tailf:info
                "Exit from template configuration mode";
            }
            key "name";
            leaf name {
              type string {
                tailf:info
                  "WORD;;Name of peer-session template";
              }
            }
            leaf remote-as {
              tailf:info
                "Specify a BGP neighbor";
              tailf:cli-full-command;
              type string {
                tailf:info
                  "AS of remote neighbor";
              }
            }
            leaf peer-group {
              tailf:hidden "all";
              type empty;
            }
            leaf activate {
              tailf:hidden "all";
              type empty;
            }
            uses description-grouping;
            container inherit {
              tailf:info
                "Inherit a template";
              tailf:cli-compact-syntax;
              tailf:cli-sequence-commands {
                tailf:cli-reset-siblings;
              }
              tailf:cli-diff-dependency "../peer-group" {
                tailf:xpath-root 3;
              }
              tailf:cli-diff-dependency "../remote-as" {
                tailf:xpath-root 3;
              }
              tailf:cli-diff-dependency "../activate" {
                tailf:xpath-root 3;
              }
              leaf peer-session {
                tailf:info
                  "Inherit a peer-session template";
                tailf:non-strict-leafref {
                  path "../../../peer-session/name";
                }
                type string {
                  tailf:info
                    "WORD;;Template name";
                }
              }
            }
            uses router-bgp-peer-session-grouping;
          }
        }
        uses router-bgp-bgp-grouping;
        uses router-bgp-af-grouping {
          refine "neighbor/password/text" {
            tailf:meta-data "secret-password" {
              tailf:meta-value "router bgp <bgp><NL><*> ::  neighbor <neighbor> password <PASSWORD>";
            }
          }
          refine "neighbor-tag/neighbor/password/text" {
            tailf:meta-data "secret-password" {
              tailf:meta-value "router bgp <bgp><NL><*> ::  neighbor <neighbor> password <PASSWORD>";
            }
          }
        }
        container address-family {
          tailf:info
            "Enter Address Family command mode";
          list ipv4 {
            tailf:info
              "Address family";
            tailf:cli-mode-name "config-router-af";
            tailf:cli-delete-when-empty;
            tailf:cli-full-command;
            tailf:cli-exit-command "exit-address-family" {
              tailf:info
                "Exit from Address Family configuration mode";
            }
            key "af";
            leaf af {
              tailf:key-default "unicast";
              type enumeration {
                enum "unicast" {
                  tailf:info
                    "Address Family modifier";
                }
                enum "multicast" {
                  tailf:info
                    "Address Family modifier";
                }
                enum "mdt" {
                  tailf:info
                    "IPv4 multicast distribution tree (MDT)";
                }
                enum "tunnel" {
                  tailf:info
                    "IPv4 tunnel address prefixes.";
                }
                enum "labeled-unicast" {
                  tailf:info
                    "IPv4 labeled-unicast address prefixes";
                }
                enum "flowspec" {
                  tailf:info
                    "Address Family modifier";
                }
                enum "mvpn" {
                  tailf:info
                    "Address Family modifier";
                }
              }
            }
            uses router-bgp-af-grouping {
              refine "neighbor" {
                tailf:cli-diff-dependency "../../../neighbor" {
                  tailf:xpath-root 3;
                }
              }
            }
          }
          list ipv6 {
            tailf:info
              "Address family";
            tailf:cli-mode-name "config-router-af";
            tailf:cli-delete-when-empty;
            tailf:cli-full-command;
            tailf:cli-exit-command "exit-address-family" {
              tailf:info
                "Exit from Address Family configuration mode";
            }
            tailf:cli-diff-dependency "../../../../ipv6/unicast-routing" {
              tailf:xpath-root 3;
            }
            key "af";
            leaf af {
              tailf:key-default "unicast";
              type enumeration {
                enum "unicast" {
                  tailf:info
                    "Address Family modifier";
                }
                enum "multicast" {
                  tailf:info
                    "Address Family modifier";
                }
                enum "flowspec" {
                  tailf:info
                    "Address Family modifier";
                }
                enum "mvpn" {
                  tailf:info
                    "Address Family modifier";
                }
              }
            }
            uses router-bgp-af-grouping {
              refine "neighbor" {
                tailf:cli-diff-dependency "../../../neighbor" {
                  tailf:xpath-root 3;
                }
              }
            }
          }
          container with-vrf {
            tailf:cli-drop-node-name;
            list ipv4 {
              tailf:info
                "Address family";
              tailf:cli-suppress-mode;
              tailf:cli-delete-when-empty;
              tailf:cli-incomplete-command;
              tailf:cli-incomplete-no;
              key "af";
              leaf af {
                tailf:key-default "unicast";
                type enumeration {
                  enum "unicast" {
                    tailf:info
                      "Address Family modifier";
                  }
                  enum "multicast" {
                    tailf:info
                      "Address Family modifier";
                  }
                  enum "mdt" {
                    tailf:info
                      "IPv4 multicast distribution tree (MDT)";
                  }
                  enum "tunnel" {
                    tailf:info
                      "IPv4 tunnel address prefixes.";
                  }
                  enum "labeled-unicast" {
                    tailf:info
                      "IPv4 labeled-unicast address prefixes";
                  }
                  enum "flowspec" {
                    tailf:info
                      "Address Family modifier";
                  }
                }
              }
              list vrf {
                tailf:cli-mode-name "config-router-af";
                tailf:cli-delete-when-empty;
                tailf:cli-full-command;
                tailf:cli-exit-command "exit-address-family" {
                  tailf:info
                    "Exit from Address Family configuration mode";
                }
                key "name";
                leaf name {
                  tailf:cli-diff-dependency "../../../../../../../ip/vrf" {
                    tailf:xpath-root 3;
                  }
                  tailf:cli-diff-dependency "../../../../../../../vrf/definition" {
                    tailf:xpath-root 3;
                  }
                  type string {
                    tailf:info
                      "WORD;;VPN Routing/Forwarding instance name";
                  }
                }
                uses router-bgp-bgp-grouping;
                uses router-bgp-af-grouping {
                  refine "neighbor" {
                    tailf:cli-diff-dependency "../../../../../neighbor" {
                      tailf:xpath-root 3;
                    }
                    tailf:cli-diff-dependency "../../../../../../../ip/vrf/rd" {
                      tailf:xpath-root 3;
                    }
                  }
                  refine "neighbor/password/text" {
                    tailf:meta-data "secret-password" {
                      tailf:meta-value "router bgp <bgp><NL><*> address-family ipv4(?: <ipv4>)? vrf <vrf><NL><*> ::   neighbor <neighbor> password <PASSWORD>";
                    }
                  }
                }
              }
            }
          }
          container ipv6-with-vrf {
            tailf:cli-drop-node-name;
            list ipv6 {
              tailf:info
                "Address family";
              tailf:cli-suppress-mode;
              tailf:cli-delete-when-empty;
              tailf:cli-incomplete-command;
              tailf:cli-incomplete-no;
              tailf:cli-diff-dependency "../../../../../ipv6/unicast-routing" {
                tailf:xpath-root 3;
              }
              key "af";
              leaf af {
                type enumeration {
                  enum "unicast" {
                    tailf:info
                      "Address Family modifier";
                  }
                  enum "multicast" {
                    tailf:info
                      "Address Family modifier";
                  }
                  enum "flowspec" {
                    tailf:info
                      "Address Family modifier";
                  }
                }
                tailf:key-default "unicast";
              }
              list vrf {
                tailf:cli-mode-name "config-router-af";
                tailf:cli-delete-when-empty;
                tailf:cli-full-command;
                tailf:cli-exit-command "exit-address-family" {
                  tailf:info
                    "Exit from Address Family configuration mode";
                }
                key "name";
                leaf name {
                  tailf:cli-diff-dependency "../../../../../../../vrf/definition" {
                    tailf:xpath-root 3;
                  }
                  tailf:cli-diff-dependency "../../../../../../../ip/vrf" {
                    tailf:xpath-root 3;
                  }
                  type string {
                    tailf:info
                      "WORD;;VPN Routing/Forwarding instance name";
                  }
                }
                uses router-bgp-bgp-grouping;
                uses router-bgp-af-grouping {
                  refine "neighbor" {
                    tailf:cli-diff-dependency "../../../../../neighbor" {
                      tailf:xpath-root 3;
                    }
                  }
                  refine "neighbor/password/text" {
                    tailf:meta-data "secret-password" {
                      tailf:meta-value "router bgp <bgp><NL><*> address-family ipv6(?: <ipv6>)? vrf <vrf><NL><*> ::   neighbor <neighbor> password <PASSWORD>";
                    }
                  }
                }
              }
            }
          }
          list vpnv4 {
            tailf:info
              "Address family";
            tailf:cli-mode-name "config-router-af";
            tailf:cli-delete-when-empty;
            tailf:cli-exit-command "exit-address-family" {
              tailf:info
                "Exit from Address Family configuration mode";
            }
            key "af";
            leaf af {
              tailf:key-default "unicast";
              type enumeration {
                enum "unicast" {
                  tailf:info
                    "Address Family modifier";
                }
                enum "multicast" {
                  tailf:info
                    "Address Family modifier";
                }
                enum "flowspec" {
                  tailf:info
                    "Address Family modifier";
                }
              }
            }
            uses router-bgp-af-grouping {
              refine "neighbor" {
                tailf:cli-diff-dependency "../../../neighbor" {
                  tailf:xpath-root 3;
                }
              }
            }
          }
          list vpnv6 {
            tailf:info
              "Address family";
            tailf:cli-mode-name "config-router-af";
            tailf:cli-delete-when-empty;
            tailf:cli-exit-command "exit-address-family" {
              tailf:info
                "Exit from Address Family configuration mode";
            }
            key "af";
            leaf af {
              tailf:key-default "unicast";
              tailf:cli-diff-dependency "../../../../../ipv6/unicast-routing" {
                tailf:xpath-root 3;
              }
              type enumeration {
                enum "unicast" {
                  tailf:info
                    "Address Family modifier";
                }
                enum "multicast" {
                  tailf:info
                    "Address Family modifier";
                }
                enum "flowspec" {
                  tailf:info
                    "Address Family modifier";
                }
              }
            }
            uses router-bgp-af-grouping {
              refine "neighbor" {
                tailf:cli-diff-dependency "../../../neighbor" {
                  tailf:xpath-root 3;
                }
              }
            }
          }
          list l2vpn {
            tailf:info
              "Address family";
            tailf:cli-mode-name "config-router-af";
            tailf:cli-delete-when-empty;
            tailf:cli-exit-command "exit-address-family" {
              tailf:info
                "Exit from Address Family configuration mode";
            }
            key "af";
            leaf af {
              tailf:key-default "vpls";
              type enumeration {
                enum "evpn" {
                  tailf:info
                    "Address Family modifier";
                }
                enum "vpls" {
                  tailf:info
                    "Address Family modifier";
                }
              }
            }
            uses router-bgp-af-grouping {
              refine "neighbor" {
                tailf:cli-diff-dependency "../../../neighbor" {
                  tailf:xpath-root 3;
                }
              }
            }
          }
          list nsap {
            tailf:info
              "Address family";
            tailf:cli-mode-name "config-router-af";
            tailf:cli-delete-when-empty;
            tailf:cli-exit-command "exit-address-family" {
              tailf:info
                "Exit from Address Family configuration mode";
            }
            key "af";
            leaf af {
              tailf:key-default "unicast";
              type enumeration {
                enum "unicast" {
                  tailf:info
                    "Address Family modifier";
                }
              }
            }
            uses router-bgp-af-grouping {
              refine "neighbor" {
                tailf:cli-diff-dependency "../../../neighbor" {
                  tailf:xpath-root 3;
                }
              }
            }
          }
          list rtfilter {
            tailf:info
              "Address family";
            tailf:cli-mode-name "config-router-af";
            tailf:cli-delete-when-empty;
            tailf:cli-exit-command "exit-address-family" {
              tailf:info
                "Exit from Address Family configuration mode";
            }
            key "af";
            leaf af {
              tailf:key-default "unicast";
              type enumeration {
                enum "unicast" {
                  tailf:info
                    "Address Family modifier";
                }
              }
            }
            uses router-bgp-af-grouping {
              refine "neighbor" {
                tailf:cli-diff-dependency "../../../neighbor" {
                  tailf:xpath-root 3;
                }
              }
            }
          }
        }
      }
      container eigrp-virtual-instance {
        tailf:cli-drop-node-name;
        list eigrp {
          tailf:info
            "Enhanced Interior Gateway Routing Protocol (EIGRP)";
          tailf:cli-mode-name "config-router";
          tailf:cli-diff-dependency "../../../ip/routing" {
            tailf:xpath-root 3;
            tailf:cli-trigger-on-set;
          }
          key "name";
          leaf name {
            type string {
              tailf:info
                "WORD;;EIGRP Virtual-Instance Name";
              pattern '[A-Za-z]+.*';
            }
          }
          container address-family {
            tailf:info
              "Enter Address Family command mode";
            container ipv4-vrf {
              tailf:cli-drop-node-name;
              container ipv4 {
                tailf:info
                  "Address family IPv4";
                container unicast {
                  tailf:info
                    "Address Family Unicast";
                  list vrf {
                    tailf:info
                      "Specify a specific virtual routing/forwarding instance";
                    tailf:cli-mode-name "config-router-af";
                    tailf:cli-sequence-commands;
                    tailf:cli-incomplete-command;
                    tailf:cli-exit-command "exit-address-family" {
                      tailf:info
                        "Exit Address Family configuration mode";
                    }
                    key "name";
                    leaf name {
                      tailf:cli-diff-dependency "../../../../../../../../../ip/vrf" {
                        tailf:xpath-root 3;
                      }
                      tailf:cli-diff-dependency "../../../../../../../../../vrf/definition" {
                        tailf:xpath-root 3;
                      }
                      type string {
                        tailf:info
                          "WORD;;Virtual Routing/Forwarding instance name";
                      }
                    }
                    leaf autonomous-system {
                      tailf:info
                        "Specify Address-Family Autonomous System Number";
                      tailf:cli-hide-in-submode;
                      tailf:cli-full-command;
                      type uint16 {
                        tailf:info
                          "<1-65535>;;Autonomous System";
                        range "1..65535";
                      }
                    }
                    uses router-eigrp-af-virtual-instance-grouping;
                  }
                }
              }
            }
            container ipv4 {
              tailf:info
                "Address family IPv4";
              tailf:cli-add-mode;
              tailf:cli-mode-name "config-router-af";
              tailf:cli-sequence-commands;
              tailf:cli-incomplete-command;
              tailf:cli-exit-command "exit-address-family" {
                tailf:info
                  "Exit Address Family configuration mode";
              }
              presence "true";
              leaf af {
                tailf:cli-drop-node-name;
                tailf:cli-hide-in-submode;
                tailf:cli-incomplete-command;
                type enumeration {
                  enum "unicast" {
                    tailf:info
                      "Address Family Unicast";
                  }
                  enum "multicast" {
                    tailf:info
                      "Address Family Multicast";
                  }
                }
              }
              leaf autonomous-system {
                tailf:info
                  "Specify Address-Family Autonomous System Number";
                tailf:cli-hide-in-submode;
                tailf:cli-remove-before-change;
                tailf:cli-full-command;
                type uint16 {
                  tailf:info
                    "<1-65535>;;Autonomous System";
                  range "1..65535";
                }
              }
              uses router-eigrp-af-virtual-instance-grouping;
            }
            container ipv6-vrf {
              tailf:cli-drop-node-name;
              container ipv6 {
                tailf:info
                  "Address family IPv6";
                container unicast {
                  tailf:info
                    "Address Family Unicast";
                  list vrf {
                    tailf:info
                      "Specify a specific virtual routing/forwarding instance";
                    tailf:cli-mode-name "config-router-af";
                    tailf:cli-sequence-commands;
                    tailf:cli-incomplete-command;
                    tailf:cli-exit-command "exit-address-family" {
                      tailf:info
                        "Exit Address Family configuration mode";
                    }
                    key "name";
                    leaf name {
                      tailf:cli-diff-dependency "../../../../../../../../../ip/vrf" {
                        tailf:xpath-root 3;
                      }
                      tailf:cli-diff-dependency "../../../../../../../../../vrf/definition" {
                        tailf:xpath-root 3;
                      }
                      type string {
                        tailf:info
                          "WORD;;Virtual Routing/Forwarding instance name";
                      }
                    }
                    leaf autonomous-system {
                      tailf:info
                        "Specify Address-Family Autonomous System Number";
                      tailf:cli-hide-in-submode;
                      tailf:cli-full-command;
                      type uint16 {
                        tailf:info
                          "<1-65535>;;Autonomous System";
                        range "1..65535";
                      }
                    }
                    uses router-eigrp-af-virtual-instance-grouping;
                  }
                }
              }
            }
            container ipv6 {
              tailf:info
                "Address family IPv6";
              tailf:cli-add-mode;
              tailf:cli-mode-name "config-router-af";
              tailf:cli-sequence-commands;
              tailf:cli-incomplete-command;
              tailf:cli-exit-command "exit-address-family" {
                tailf:info
                  "Exit Address Family configuration mode";
              }
              presence "true";
              leaf af {
                tailf:cli-drop-node-name;
                tailf:cli-hide-in-submode;
                tailf:cli-incomplete-command;
                type enumeration {
                  enum "unicast" {
                    tailf:info
                      "Address Family Unicast";
                  }
                  enum "multicast" {
                    tailf:info
                      "Address Family Multicast";
                  }
                }
              }
              leaf autonomous-system {
                tailf:info
                  "Specify Address-Family Autonomous System Number";
                tailf:cli-hide-in-submode;
                tailf:cli-full-command;
                type uint16 {
                  tailf:info
                    "<1-65535>;;Autonomous System";
                  range "1..65535";
                }
              }
              uses router-eigrp-af-virtual-instance-grouping;
            }
          }
        }
      }
      list eigrp {
        tailf:info
          "Enhanced Interior Gateway Routing Protocol (EIGRP)";
        tailf:cli-mode-name "config-router";
        tailf:cli-diff-dependency "../../ip/routing" {
          tailf:xpath-root 3;
          tailf:cli-trigger-on-set;
        }
        key "as-no";
        leaf as-no {
          type uint16 {
            tailf:info
              "<1-65535>;;Autonomous system number";
            range "1..65535";
          }
        }
        container address-family {
          tailf:info
            "Enter Address Family command mode";
          container ipv4 {
            tailf:info
              "Address Family IPv4";
            list vrf {
              tailf:info
                "Specify a specific virtual routing/forwarding instance";
              tailf:cli-mode-name "config-router-af";
              tailf:cli-exit-command "exit-address-family" {
                tailf:info
                  "Exit Address Family configuration mode";
              }
              key "name";
              leaf name {
                tailf:cli-diff-dependency "../../../../../../vrf/definition" {
                  tailf:xpath-root 3;
                }
                tailf:cli-diff-dependency "../../../../../../ip/vrf" {
                  tailf:xpath-root 3;
                }
                type string {
                  tailf:info
                    "WORD;;Virtual Routing/Forwarding instance name";
                }
              }
              leaf autonomous-system {
                tailf:info
                  "Specify Address-Family Autonomous System Number";
                tailf:cli-hide-in-submode;
                tailf:cli-full-command;
                type uint16 {
                  tailf:info
                    "<1-65535>;;Autonomous System";
                  range "1..65535";
                }
              }
              uses router-eigrp-grouping;
              uses router-eigrp-base-grouping;
            }
          }
        }
        uses router-eigrp-grouping;
        uses router-eigrp-base-grouping;
      }
      list ospfv3 {
        tailf:info
          "OSPFv3";
        tailf:cli-mode-name "config-router";
        tailf:cli-diff-dependency "../../ip/routing" {
          tailf:xpath-root 3;
          tailf:cli-trigger-on-set;
        }
        key "id";
        leaf id {
          tailf:cli-suppress-range;
          type uint16 {
            tailf:info
              "<1-65535>;;Process ID";
            range "1..65535";
          }
        }
        uses router-ospfv3-grouping;
        uses router-ospf-common-grouping;
        leaf shutdown {
          tailf:info
            "Shutdown the router process";
          type empty;
        }
        container address-family {
          tailf:info
            "Enter Address Family command mode";
          container ipv4 {
            tailf:info
              "Address family";
            container unicast {
              tailf:info
                "Address Family Modifier";
              tailf:cli-add-mode;
              tailf:cli-mode-name "config-router-af";
              tailf:cli-full-command;
              tailf:cli-exit-command "exit-address-family" {
                tailf:info
                  "Exit from Address Family configuration mode";
              }
              uses router-ospfv3-grouping;
              uses router-ospf-common-grouping;
              uses router-ospf-common-af-grouping;
              uses router-ospfv3-af-grouping;
            }
          }
          container ipv6 {
            tailf:info
              "Address family";
            container unicast {
              tailf:info
                "Address Family Modifier";
              tailf:cli-add-mode;
              tailf:cli-mode-name "config-router-af";
              tailf:cli-full-command;
              tailf:cli-exit-command "exit-address-family" {
                tailf:info
                  "Exit from Address Family configuration mode";
              }
              uses router-ospfv3-grouping;
              uses router-ospf-common-grouping;
              uses router-ospf-common-af-grouping;
              uses router-ospfv3-af-grouping;
            }
          }
          container ipv4-vrf {
            tailf:cli-drop-node-name;
            container ipv4 {
              tailf:info
                "Address family";
              container unicast {
                tailf:info
                  "Address Family Modifier";
                list vrf {
                  tailf:info
                    "Specify parameters for a VPN Routing/Forwarding instance";
                  tailf:cli-mode-name "config-router-af";
                  tailf:cli-full-command;
                  tailf:cli-exit-command "exit-address-family" {
                    tailf:info
                      "Exit from Address Family configuration mode";
                  }
                  key "name";
                  leaf name {
                    tailf:cli-diff-dependency "../../../../../../../../ip/vrf" {
                      tailf:xpath-root 3;
                    }
                    tailf:cli-diff-dependency "../../../../../../../../vrf/definition" {
                      tailf:xpath-root 3;
                    }
                    type string {
                      tailf:info
                        "WORD;;VPN Routing/Forwarding instance name";
                    }
                  }
                  uses router-ospfv3-grouping;
                  uses router-ospf-common-grouping;
                  uses router-ospf-common-af-grouping;
                  uses router-ospfv3-af-grouping;
                }
              }
            }
          }
          container ipv6-vrf {
            tailf:cli-drop-node-name;
            container ipv6 {
              tailf:info
                "Address family";
              container unicast {
                tailf:info
                  "Address Family Modifier";
                list vrf {
                  tailf:info
                    "Specify parameters for a VPN Routing/Forwarding instance";
                  tailf:cli-mode-name "config-router-af";
                  tailf:cli-full-command;
                  tailf:cli-exit-command "exit-address-family" {
                    tailf:info
                      "Exit from Address Family configuration mode";
                  }
                  key "name";
                  leaf name {
                    tailf:cli-diff-dependency "../../../../../../../../ip/vrf" {
                      tailf:xpath-root 3;
                    }
                    tailf:cli-diff-dependency "../../../../../../../../vrf/definition" {
                      tailf:xpath-root 3;
                    }
                    type string {
                      tailf:info
                        "WORD;;VPN Routing/Forwarding instance name";
                    }
                  }
                  uses router-ospfv3-grouping;
                  uses router-ospf-common-grouping;
                  uses router-ospf-common-af-grouping;
                  uses router-ospfv3-af-grouping;
                }
              }
            }
          }
        }
      }
      list ospf {
        tailf:info
          "Open Shortest Path First (OSPF)";
        tailf:cli-mode-name "config-router";
        tailf:cli-sequence-commands;
        tailf:cli-diff-dependency "../../ip/routing" {
          tailf:xpath-root 3;
          tailf:cli-trigger-on-set;
        }
        key "id";
        leaf id {
          tailf:cli-suppress-range;
          type uint16 {
            tailf:info
              "<1-65535>;;Process ID";
            range "1..65535";
          }
        }
        leaf vrf {
          tailf:info
            "VPN Routing/Forwarding Instance";
          tailf:cli-hide-in-submode;
          tailf:cli-full-command;
          tailf:cli-diff-dependency "../../../ip/vrf" {
            tailf:xpath-root 3;
          }
          tailf:cli-diff-dependency "../../../vrf/definition" {
            tailf:xpath-root 3;
          }
          type string {
            tailf:info
              "WORD;;VPN Routing/Forwarding Instance (VRF) name";
          }
        }
        uses router-ospf-common-grouping {
          refine "area" {
            tailf:cli-break-sequence-commands;
          }
        }
        uses router-ospf-common-af-grouping;
        uses router-ospf-grouping;
      }
      container isis {
        tailf:info
          "ISO IS-IS";
        tailf:cli-add-mode;
        tailf:cli-mode-name "config-router";
        tailf:cli-full-command;
        tailf:cli-diff-dependency "../../ip/routing" {
          tailf:xpath-root 3;
        }
        presence "true";
        uses router-isis-grouping;
      }
      container isis-container {
        tailf:cli-drop-node-name;
        list isis {
          tailf:info
            "ISO IS-IS";
          tailf:cli-mode-name "config-router";
          tailf:cli-diff-dependency "../../../ip/routing" {
            tailf:xpath-root 3;
          }
          key "area-tag";
          leaf area-tag {
            type string {
              tailf:info
                "WORD;;ISO routing area tag";
            }
          }
          uses router-isis-grouping;
        }
      }
      container rip {
        tailf:info
          "Routing Information Protocol (RIP)";
        tailf:cli-add-mode;
        tailf:cli-mode-name "config-router";
        tailf:cli-full-command;
        uses router-rip-grouping {
          refine "version" {
            tailf:cli-diff-dependency "../../../ip/routing" {
              tailf:xpath-root 3;
              tailf:cli-trigger-on-set;
            }
          }
        }
        container address-family {
          tailf:info
            "Enter Address Family command mode";
          container ipv4 {
            tailf:info
              "Address family";
            container unicast {
              tailf:cli-add-mode;
              tailf:cli-mode-name "config-router-af";
              tailf:info
                "Address Family Modifier";
              tailf:cli-full-command;
              tailf:cli-exit-command "exit-address-family" {
                tailf:info
                  "Exit from Address Family configuration mode";
              }
              tailf:cli-diff-dependency "../../../../../ip/routing" {
                tailf:xpath-root 3;
                tailf:cli-trigger-on-set;
              }
              uses router-rip-grouping;
            }
            list vrf {
              tailf:info
                "Specify parameters for a VPN Routing/Forwarding instance";
              tailf:cli-mode-name "config-router-af";
              tailf:cli-full-command;
              tailf:cli-exit-command "exit-address-family" {
                tailf:info
                  "Exit from Address Family configuration mode";
              }
              tailf:cli-diff-dependency "../../../../../ip/routing" {
                tailf:xpath-root 3;
                tailf:cli-trigger-on-set;
              }
              key "name";
              leaf name {
                tailf:cli-diff-dependency "../../../../../../ip/vrf" {
                  tailf:xpath-root 3;
                }
                tailf:cli-diff-dependency "../../../../../../vrf/definition" {
                  tailf:xpath-root 3;
                }
                type string {
                  tailf:info
                    "WORD;;VPN Routing/Forwarding instance name";
                }
              }
              uses router-rip-af-grouping;
            }
          }
        }
      }
      container lisp {
        tailf:info
          "Locator/ID Separation Protocol";
        tailf:cli-add-mode;
        tailf:cli-mode-name "config-router-lisp";
        tailf:cli-diff-dependency "../../interface" {
          tailf:xpath-root 3;
        }
        presence "true";
        uses router-lisp-grouping {
          refine "eid-table/vrf/name" {
            tailf:cli-diff-dependency "../../../../../ip/vrf" {
              tailf:xpath-root 3;
            }
            tailf:cli-diff-dependency "../../../../../vrf/definition" {
              tailf:xpath-root 3;
            }
          }
          refine "site/authentication-key/secret" {
            tailf:meta-data "secret-password" {
              tailf:meta-value "router lisp<NL><*> site <site><NL><*> ::   authentication-key <PASSWORD>";
            }
          }
          refine "ipv4/etr/map-server/key/secret" {
            tailf:meta-data "secret-password" {
              tailf:meta-value "router lisp<NL><*> ::  ipv4 etr map-server <map-server> key <PASSWORD>";
            }
          }
        }
      }
      container router-lisp {
        tailf:cli-drop-node-name;
        list lisp {
          tailf:cli-mode-name "config-router-lisp";
          key "id";
          leaf id {
            type uint8 {
              tailf:info
                "<0-15>;;router lisp ID";
              range "0..15";
            }
          }
          uses router-lisp-grouping {
            refine "eid-table/vrf/name" {
              tailf:cli-diff-dependency "../../../../../../ip/vrf" {
                tailf:xpath-root 3;
              }
              tailf:cli-diff-dependency "../../../../../../vrf/definition" {
                tailf:xpath-root 3;
              }
            }
          }
        }
      }
      container odr {
        tailf:info
          "On Demand stub Routes";
        tailf:cli-add-mode;
        tailf:cli-mode-name "config-router";
        tailf:cli-full-command;
        presence "true";
      }
    }
    container vstack-conf {
      tailf:ncs-device-type "cli-ned";
      tailf:display-when "not(../../ncs:module) or ../../ncs:module[ncs:name='tailf-ned-cisco-ios']";
      tailf:cli-drop-node-name;
      container vstack {
        tailf:info
          "Configure vstack parameters";
        tailf:cli-incomplete-command;
        tailf:cli-incomplete-no;
        leaf director {
          tailf:info
            "Configure director's IP address";
          tailf:cli-full-command;
          type inet:ipv4-address {
            tailf:info
              "A.B.C.D;;Director's IP Address";
          }
        }
        leaf basic {
          tailf:info
            "Enable vstack director";
          tailf:cli-full-command;
          type empty;
        }
      }
    }
    container vstack-no {
      tailf:ncs-device-type "cli-ned";
      tailf:display-when "not(../../ncs:module) or ../../ncs:module[ncs:name='tailf-ned-cisco-ios']";
      tailf:cli-drop-node-name;
      leaf vstack {
        tailf:info
          "Configure vstack parameters and enable or disable SmartInstall";
        tailf:cli-boolean-no;
        type boolean;
        default "true";
      }
    }
    container snmp {
      tailf:ncs-device-type "cli-ned";
      tailf:display-when "not(../../ncs:module) or ../../ncs:module[ncs:name='tailf-ned-cisco-ios']";
      tailf:info
        "Modify non engine SNMP parameters";
      container ifmib {
        tailf:info
          "IF-MIB commands";
        container ifindex {
          tailf:info
            "ifindex persistence";
          leaf persist {
            tailf:info
              "Persist interface indices";
            type empty;
          }
        }
        container ifalias {
          tailf:info
            "ifAlias description option, by default it is limited to 64 character";
          leaf long {
            tailf:info
              "ifAlias description can be up to 256 characters";
            type empty;
          }
        }
        container trap {
          tailf:info
            "IF-MIB trap options";
          leaf throttle {
            tailf:info
              "disable subinterface link down traps if main interface is down";
            type empty;
          }
        }
      }
      container mib {
        tailf:info
          "MIB commands";
        container bulkstat {
          tailf:info
            "Bulkstat Configuration commands";
          list object-list {
            tailf:info
              "Configure an Object List.";
            tailf:cli-suppress-mode;
            tailf:cli-delete-when-empty;
            key "name";
            leaf name {
              type string {
                tailf:info
                  "WORD;;Name of object list";
              }
            }
          }
        }
        container persist {
          tailf:info
            "Persistence for MIBS";
          leaf v3mibs {
            tailf:info
              "Persistence for v3 MIBS";
            type empty;
          }
          leaf dsmib {
            tailf:info
              "DiffServ MIB persistence";
            type empty;
          }
          leaf cbqos {
            tailf:info
              "CBQOS MIB index persistence";
            type empty;
          }
          leaf circuit {
            tailf:info
              "Circuit MIB persistence";
            type empty;
          }
        }
      }
    }
    list menu {
      tailf:ncs-device-type "cli-ned";
      tailf:display-when "not(../ncs:module) or ../ncs:module[ncs:name='tailf-ned-cisco-ios']";
      tailf:info
        "Define a user-interface menu";
      tailf:cli-suppress-mode;
      tailf:cli-delete-when-empty;
      key "name";
      leaf name {
        type string {
          tailf:info
            "WORD;;Name of this menu";
        }
      }
      leaf title {
        tailf:info
          "Set menu title";
        tailf:cli-no-value-on-delete;
        type string {
          tailf:info
            "LINE;;Quoted text of title. Use \\r\\n for newline. delimeter ^ is added automatically.";
        }
      }
      list command {
        tailf:cli-suppress-mode;
        tailf:cli-delete-when-empty;
        tailf:cli-incomplete-command;
        key "item";
        leaf item {
          type string {
            tailf:info
              "WORD;;Menu item number or character";
          }
        }
        leaf command {
          tailf:cli-drop-node-name;
          tailf:cli-multi-value;
          type string {
            tailf:info
              "WORD;;Menu item number or character";
          }
        }
      }
      leaf clear-screen {
        tailf:info
          "Use termcap database to clear screen";
        tailf:cli-full-command;
        type empty;
      }
      leaf status-line {
        tailf:info
          "Display user status at top of screen";
        tailf:cli-full-command;
        type empty;
      }
      leaf line-mode {
        tailf:info
          "require <enter> after typing selection";
        tailf:cli-full-command;
        type empty;
      }
      leaf single-space {
        tailf:info
          "single-space menu entries on display";
        tailf:cli-full-command;
        type empty;
      }
    }
    container snmp-server {
      tailf:ncs-device-type "cli-ned";
      tailf:display-when "not(../../ncs:module) or ../../ncs:module[ncs:name='tailf-ned-cisco-ios']";
      tailf:info
        "Modify SNMP engine parameters";
      list user {
        tailf:info
          "Define a user who can access the SNMP engine";
        tailf:cli-suppress-mode;
        tailf:cli-delete-when-empty;
        tailf:cli-compact-syntax;
        tailf:cli-sequence-commands {
          tailf:cli-reset-siblings;
        }
        tailf:cli-incomplete-command;
        key "name";
        leaf name {
          tailf:cli-diff-dependency "../../engineID" {
            tailf:xpath-root 3;
          }
          type string {
            tailf:info
              "WORD;;Name of the user";
          }
        }
        leaf group {
          tailf:cli-drop-node-name;
          tailf:cli-incomplete-command;
          type string {
            tailf:info
              "WORD;;Group to which the user belongs";
          }
        }
        choice security-model {
          leaf v1 {
            tailf:info
              "user using the v1 security model";
            type empty;
          }
          leaf v2c {
            tailf:info
              "user using the v2c security model";
            type empty;
          }
          case v3 {
            leaf v3 {
              tailf:info
                "user using the v3 security model";
              type empty;
            }
            leaf encrypted {
              tailf:cli-drop-node-name;
              tailf:cli-optional-in-sequence;
              tailf:cli-incomplete-command;
              type enumeration {
                enum "encrypted" {
                  tailf:info
                    "specifying passwords as MD5 or SHA digests";
                }
              }
              default "encrypted";
            }
            leaf auth {
              tailf:info
                "authentication parameters for the user";
              tailf:cli-optional-in-sequence;
              tailf:cli-incomplete-command;
              type enumeration {
                enum "md5" {
                  tailf:info
                    "Use HMAC MD5 algorithm for authentication";
                }
                enum "sha" {
                  tailf:info
                    "Use HMAC SHA algorithm for authentication";
                }
              }
            }
            leaf auth-password {
              when "../auth" {
                tailf:xpath-root 3;
                tailf:dependency "../auth";
              }
              tailf:cli-drop-node-name;
              tailf:meta-data "support-encrypted-password";
              type string {
                tailf:info
                  "WORD;;authentication pasword for user";
              }
            }
            leaf priv {
              tailf:info
                "encryption parameters for the user";
              tailf:cli-optional-in-sequence;
              tailf:cli-incomplete-command;
              type enumeration {
                enum "3des" {
                  tailf:info
                    "Use 168 bit 3DES algorithm for encryption";
                }
                enum "aes" {
                  tailf:info
                    "Use AES algorithm for encryption";
                }
                enum "des" {
                  tailf:info
                    "Use 56 bit DES algorithm for encryption";
                }
              }
            }
            leaf bits {
              when "../priv = 'aes'" {
                tailf:xpath-root 3;
                tailf:dependency "../priv";
              }
              tailf:cli-drop-node-name;
              tailf:cli-incomplete-command;
              type enumeration {
                enum "128" {
                  tailf:info
                    "128 bit keys.";
                }
                enum "192" {
                  tailf:info
                    "192 bit keys.";
                }
                enum "256" {
                  tailf:info
                    "256 bit keys.";
                }
              }
            }
            leaf priv-password {
              when "../priv" {
                tailf:xpath-root 3;
                tailf:dependency "../priv";
              }
              tailf:cli-drop-node-name;
              type string {
                tailf:info
                  "WORD;;privacy pasword for user";
              }
            }
          }
        }
        container access {
          tailf:info
            "specify an access-list associated with this group";
          tailf:cli-flatten-container;
          choice access-choice {
            leaf access-list-std {
              tailf:cli-drop-node-name;
              type uint16 {
                tailf:info
                  "<1-99>;;Standard access list";
                range "1..99";
              }
            }
            leaf access-list-named {
              tailf:cli-drop-node-name;
              type string {
                tailf:info
                  "WORD;;Named access list";
              }
            }
            leaf ipv6 {
              tailf:info
                "Specify IPv6 Named Access-List";
              type string {
                tailf:info
                  "WORD;;IPv6 Access-list name";
              }
            }
          }
        }
      }
      leaf chassis-id {
        tailf:info
          "String to uniquely identify this chassis";
        tailf:cli-multi-value;
        type string {
          tailf:info
            "LINE;;Unique ID string";
        }
      }
      list community {
        tailf:info
          "Enable SNMP; set community string and access privs";
        tailf:cli-suppress-mode;
        tailf:cli-delete-when-empty;
        tailf:cli-compact-syntax;
        tailf:cli-sequence-commands {
          tailf:cli-reset-siblings;
        }
        key "name";
        leaf name {
          type string {
            tailf:info
              "WORD;;SNMP community string";
          }
        }
        leaf view {
          tailf:info
            "Restrict this community to a named MIB view";
          tailf:cli-optional-in-sequence;
          type string {
            tailf:info
              "WORD;;MIB view to which this community has access";
          }
        }
        choice access-choice {
          leaf RO {
            tailf:info
              "Read-only access with this community string";
            tailf:cli-optional-in-sequence;
            type empty;
          }
          leaf RW {
            tailf:info
              "Read-write access with this community string";
            tailf:cli-optional-in-sequence;
            type empty;
          }
        }
        leaf ipv6 {
          tailf:info
            "Specify IPv6 Named Access-List";
          tailf:cli-optional-in-sequence;
          type string {
            tailf:info
              "WORD;;IPv6 Access-list name";
          }
        }
        leaf access-list-name {
          tailf:cli-drop-node-name;
          type std-ip-acl-type;
        }
      }
      leaf contact {
        tailf:info
          "Text for mib object sysContact";
        tailf:cli-full-command;
        type string {
          tailf:info
            "LINE;;identification of the contact person for this managed node";
        }
      }
      list context {
        tailf:info
          "Create/Delete a context apart from default";
        tailf:cli-suppress-mode;
        tailf:cli-delete-when-empty;
        key "name";
        leaf name {
          type string {
            tailf:info
              "WORD;;Context Name";
          }
        }
      }
      container drop {
        tailf:info
          "Silently drop SNMP packets";
        leaf vrf-traffic {
          tailf:info
            "Silently drop SNMP packets that come on VRF interface";
          type empty;
        }
      }
      container enable {
        tailf:info
          "Enable SNMP Traps or Informs";
        choice enable-choice {
          leaf informs {
            tailf:info
              "Enable SNMP Informs";
            type empty;
          }
          list traps {
            tailf:info
              "Enable SNMP Traps";
            tailf:cli-suppress-mode;
            tailf:cli-delete-when-empty;
            tailf:cli-full-command;
            key "name";
            leaf name {
              tailf:cli-multi-word-key;
              type string {
                tailf:info
                  "WORD;;Trap name";
              }
            }
          }
        }
      }
      container engineID {
        tailf:info
          "Configure a local or remote SNMPv3 engineID";
        leaf local {
          tailf:info
            "engineID of the local agent";
          type string {
            tailf:info
              "WORD;;engine ID octet string";
            length "1..24";
          }
        }
        list remote {
          tailf:info
            "engineID of the remote agent";
          tailf:cli-suppress-mode;
          tailf:cli-delete-when-empty;
          tailf:cli-compact-syntax;
          tailf:cli-sequence-commands;
          tailf:cli-incomplete-command;
          key "address";
          leaf address {
            type inet:host {
              tailf:info
                "Hostname, A.B.C.D or X:X:X:X::X;;Remote address";
            }
          }
          leaf udp-port {
            tailf:info
              "The remote notification host's UDP port number";
            tailf:cli-optional-in-sequence;
            type uint16 {
              tailf:info
                "<0-65535>;;The remote notification host's UDP port number";
            }
          }
          leaf vrf {
            tailf:info
              "The remote notification host's VPN routing instance";
            tailf:cli-diff-dependency "../../../../ip/vrf" {
              tailf:xpath-root 3;
            }
            tailf:cli-diff-dependency "../../../../vrf/definition" {
              tailf:xpath-root 3;
            }
            type string {
              tailf:info
                "WORD;;VPN Routing/Forwarding instance name";
            }
          }
          leaf engineid-string {
            tailf:cli-drop-node-name;
            type string {
              tailf:info
                "WORD;;engine ID octet string";
            }
          }
        }
      }
      list group {
        tailf:info
          "Define a User Security Model group";
        tailf:cli-suppress-mode;
        tailf:cli-delete-when-empty;
        tailf:cli-compact-syntax;
        tailf:cli-sequence-commands;
        key "id";
        leaf id {
          type string {
            tailf:info
              "WORD;;Name of the group";
          }
        }
        choice security-model {
          leaf v1 {
            tailf:info
              "group using the v1 security model";
            type empty;
          }
          leaf v2c {
            tailf:info
              "group using the v2c security model";
            type empty;
          }
          container v3 {
            tailf:info
              "group using the User Security Model (SNMPv3)";
            tailf:cli-compact-syntax;
            tailf:cli-sequence-commands {
              tailf:cli-reset-siblings;
            }
            leaf security-level {
              tailf:cli-drop-node-name;
              type enumeration {
                enum "auth" {
                  tailf:info
                    "group using the authNoPriv Security Level";
                }
                enum "noauth" {
                  tailf:info
                    "group using the noAuthNoPriv Security Level";
                }
                enum "priv" {
                  tailf:info
                    "group using SNMPv3 authPriv security level";
                }
              }
            }
            leaf context {
              tailf:cli-optional-in-sequence;
              tailf:info
                "specify a context to associate these views for the group";
              type string {
                tailf:info
                  "WORD;;context name";
              }
            }
            leaf match {
              tailf:cli-optional-in-sequence;
              tailf:info
                "context name match criteria";
              type enumeration {
                enum "exact" {
                  tailf:info
                    "match the exact context";
                }
                enum "prefix" {
                  tailf:info
                    "only match the context prefix";
                }
              }
            }
            leaf read {
              tailf:cli-optional-in-sequence;
              tailf:info
                "specify a read view for the group";
              type string {
                tailf:info
                  "WORD;;read view name";
              }
            }
            leaf write {
              tailf:cli-optional-in-sequence;
              tailf:info
                "specify a write view for the group";
              type string {
                tailf:info
                  "WORD;;write view name";
              }
            }
            leaf notify {
              tailf:cli-optional-in-sequence;
              tailf:info
                "specify a notify view for the group";
              type string {
                tailf:info
                  "WORD;;notify view name";
              }
            }
            leaf access {
              tailf:info
                "specify an access-list associated with this group";
              type empty;
            }
            leaf ipv6 {
              when "../access" {
                tailf:xpath-root 3;
                tailf:dependency "../access";
              }
              tailf:info
                "Specify IPv6 Named Access-List";
              tailf:cli-optional-in-sequence;
              type string {
                tailf:info
                  "WORD;;IPv6 Access-list name";
              }
            }
            leaf acl {
              when "../access" {
                tailf:xpath-root 3;
                tailf:dependency "../access";
              }
              tailf:cli-drop-node-name;
              type union {
                type uint8 {
                  tailf:info
                    "<1-99>;;Std IP accesslist allowing access with this group";
                  range "1..99";
                }
                type string {
                  tailf:info
                    "WORD;;Access-list name";
                }
              }
            }
          }
        }
      }
      list host {
        tailf:info
          "Specify hosts to receive SNMP notifications";
        tailf:cli-suppress-mode;
        tailf:cli-delete-when-empty;
        tailf:cli-compact-syntax;
        tailf:cli-sequence-commands {
          tailf:cli-reset-all-siblings;
        }
        tailf:cli-incomplete-command;
        key "ip-address";
        leaf ip-address {
          tailf:cli-disallow-value "vrf";
          tailf:cli-case-sensitive;
          type inet:host {
            tailf:info
              "WORD;;Hostname or IP/IPv6 address of SNMP notification host";
          }
        }
        uses snmp-server-host-grouping;
      }
      container host-vrf {
        tailf:cli-drop-node-name;
        list host {
          tailf:info
            "Specify hosts to receive SNMP notifications";
          tailf:cli-suppress-mode;
          tailf:cli-delete-when-empty;
          tailf:cli-compact-syntax;
          tailf:cli-sequence-commands {
            tailf:cli-reset-all-siblings;
          }
          tailf:cli-incomplete-command;
          key "ip-address vrf";
          leaf ip-address {
            tailf:cli-case-sensitive;
            type inet:host {
              tailf:info
                "WORD;;Hostname or IP/IPv6 address of SNMP notification host";
            }
          }
          leaf vrf {
            tailf:info
              "VPN Routing instance for this host";
            tailf:cli-expose-key-name;
            tailf:cli-diff-dependency "../../../../ip/vrf" {
              tailf:xpath-root 3;
            }
            tailf:cli-diff-dependency "../../../../vrf/definition" {
              tailf:xpath-root 3;
            }
            type string {
              tailf:info
                "WORD;;VPN Routing/Forwarding instance name";
            }
          }
          uses snmp-server-host-grouping;
        }
      }
      container ip {
        tailf:info
          "IP ToS configuration for SNMP traffic";
        leaf dscp {
          tailf:info
            "IP DSCP value for SNMP traffic";
          type uint8 {
            tailf:info
              "<0-63>;;ip dscp value (default value 0 )";
            range "0..63";
          }
        }
        leaf precedence {
          tailf:info
            "IP Precedence value for SNMP traffic";
          tailf:cli-full-command;
          type uint8 {
            tailf:info
              "<0-7>;;ip precedence value (default value 0)";
            range "0..7";
          }
        }
      }
      container ifindex {
        tailf:info
          "Enable ifindex persistence";
        leaf persist {
          tailf:info
            "Persist interface indices";
          type empty;
        }
      }
      leaf location {
        tailf:info
          "Text for mib object sysLocation";
        tailf:cli-full-command;
        type string {
          tailf:info
            "LINE;;The physical location of this node";
        }
      }
      container manager {
        tailf:info
          "Modify SNMP manager parameters";
        tailf:cli-display-separated;
        presence "true";
        leaf session-timeout {
          tailf:info
            "Timeout value for destroying sessions";
          type uint32 {
            tailf:info
              "<10-2147483>;;seconds";
            range "10..2147483";
          }
        }
      }
      leaf packetsize {
        tailf:info
          "Largest SNMP packet size";
        type uint16 {
          tailf:info
            "<484-17940>;;Packet size";
          range "484..17940";
        }
      }
      leaf queue-length {
        tailf:info
          "Message queue length for each TRAP host";
        type uint16 {
          tailf:info
            "<1-5000>;;Queue length (default 10)";
          range "1..5000";
        }
      }
      container queue-limit {
        tailf:info
          "Message queue size for different queues";
        leaf notification-host {
          tailf:info
            "Message queue length for each notification host";
          type uint16 {
            tailf:info
              "<1-5000>;;notification host queue length";
            range "1..5000";
          }
        }
      }
      leaf tftp-server-list {
        tailf:info
          "Limit TFTP servers used via SNMP";
        tailf:cli-full-command;
        type std-acl-type;
      }
      leaf system-shutdown {
        tailf:info
          "Enable use of the SNMP reload command";
        type empty;
      }
      container file-transfer {
        tailf:info
          "File transfer related commands";
        list access-group {
          tailf:info
            "Access control for file transfers";
          tailf:cli-suppress-mode;
          tailf:cli-delete-when-empty;
          key "name";
          leaf name {
            type std-ip-acl-type;
          }
          leaf-list protocol {
            tailf:info
              "protocol options";
            tailf:cli-list-syntax;
            type enumeration {
              enum "ftp" {
                tailf:info
                  "Configure acl for ftp transfer protocol";
              }
              enum "rcp" {
                tailf:info
                  "Configure acl for rcp transfer protocol";
              }
              enum "scp" {
                tailf:info
                  "Configure acl for scp transfer protocol";
              }
              enum "sftp" {
                tailf:info
                  "Configure acl for sftp transfer protocol";
              }
              enum "tftp" {
                tailf:info
                  "Configure acl for tftp transfer protocol";
              }
            }
          }
        }
      }
      container source-interface {
        tailf:info
          "Assign an source interface";
        container informs {
          tailf:info
            "source interface for informs";
          uses interface-name-grouping;
        }
        container traps {
          tailf:info
            "source interface for traps";
          uses interface-name-grouping;
        }
      }
      container trap {
        tailf:info
          "SNMP trap options";
        leaf timeout {
          tailf:info
            "Set timeout for TRAP message retransmissions";
          tailf:cli-full-command;
          type uint16 {
            tailf:info
              "<1-1000>;;Timeout (default 30 seconds)";
            range "1..1000";
          }
          default "30";
        }
        container authentication {
          tailf:info
            "fine-tune enable/disable of authentication traps";
          leaf unknown-context {
            tailf:info
              "enable authentication traps for unknown context error";
            tailf:cli-boolean-no;
            type boolean;
            default "true";
          }
        }
      }
      leaf sparse-tables {
        tailf:cli-boolean-no;
        tailf:cli-full-command;
        type boolean;
        default "true";
      }
      container trap-source {
        tailf:info
          "Assign an interface for the source address of all traps";
        uses interface-name-grouping;
      }
      leaf trap-timeout {
        tailf:info
          "Set timeout for TRAP message retransmissions";
        tailf:cli-full-command;
        type uint16 {
          tailf:info
            "<1-1000>;;Timeout (default 30 seconds)";
        }
      }
      list view {
        tailf:info
          "Define an SNMPv2 MIB view";
        tailf:cli-suppress-mode;
        tailf:cli-delete-when-empty;
        tailf:cli-compact-syntax;
        key "name mib";
        leaf name {
          type string {
            tailf:info
              "WORD;;Name of the view";
          }
        }
        leaf mib {
          type string {
            tailf:info
              "WORD;;MIB view family name";
          }
        }
        leaf inc-exl {
          tailf:cli-drop-node-name;
          type enumeration {
            enum "excluded" {
              tailf:info
                "MIB family is excluded from the view";
            }
            enum "included" {
              tailf:info
                "MIB family is included in the view";
            }
          }
        }
      }
    }
    container rtr {
      tailf:ncs-device-type "cli-ned";
      tailf:display-when "not(../../ncs:module) or ../../ncs:module[ncs:name='tailf-ned-cisco-ios']";
      tailf:info
        "RTR Base Configuration";
      container responder {
        tailf:info
          "Enable RTR Responder";
        presence "true";
      }
    }
    container ipc {
      tailf:ncs-device-type "cli-ned";
      tailf:display-when "not(../../ncs:module) or ../../ncs:module[ncs:name='tailf-ned-cisco-ios']";
      tailf:info
        "Configure IPC system";
      container zone {
        tailf:info
          "Configure an IPC Zone";
        container default {
          tailf:info
            "Configure the default zone";
          tailf:cli-add-mode;
          tailf:cli-mode-name "config-ipczone";
          presence "true";
        }
      }
    }
    container cts {
      tailf:ncs-device-type "cli-ned";
      tailf:display-when "not(../../ncs:module) or ../../ncs:module[ncs:name='tailf-ned-cisco-ios']";
      tailf:info
        "Cisco Trusted Security commands";
      container logging {
        tailf:info
          "Set logging parameters";
        leaf verbose {
          tailf:info
            "Show verbose messages in system logs";
          type empty;
        }
      }
    }
    container license {
      tailf:ncs-device-type "cli-ned";
      tailf:display-when "not(../../ncs:module) or ../../ncs:module[ncs:name='tailf-ned-cisco-ios']";
      tailf:info
        "Configure license features";
      container accept {
        tailf:info
          "Accept all further License Agreements";
        container end {
          tailf:info
            "Accept all further License Agreements";
          container user {
            tailf:info
              "Accept all further License Agreements";
            leaf agreement {
              tailf:info
                "Accept all further License Agreements";
              type empty;
            }
          }
        }
      }
      list feature {
        tailf:info
          "License features";
        tailf:cli-suppress-mode;
        tailf:cli-delete-when-empty;
        ordered-by user;
        key "line";
        leaf line {
          tailf:cli-multi-word-key;
          type string {
            tailf:info
              "WORD;;License line";
          }
        }
      }
      list boot {
        tailf:info
          "license boot config commands";
        tailf:cli-suppress-mode;
        tailf:cli-delete-when-empty;
        ordered-by user;
        key "line";
        leaf line {
          tailf:cli-multi-word-key;
          type string {
            tailf:info
              "WORD;;License line";
          }
        }
      }
      container smart {
        tailf:info
          "Smart licensing";
        leaf enable {
          tailf:info
            "Enable Smart Licensing";
          type empty;
        }
      }
    }
    container setup {
      tailf:ncs-device-type "cli-ned";
      tailf:display-when "not(../../ncs:module) or ../../ncs:module[ncs:name='tailf-ned-cisco-ios']";
      tailf:info
        "Configure setup options";
      leaf express {
        tailf:info
          "Configure whether express setup mode is enabled";
        tailf:cli-boolean-no;
        tailf:cli-full-command;
        type boolean;
        default "true";
      }
    }
    container trunk {
      tailf:ncs-device-type "cli-ned";
      tailf:display-when "not(../../ncs:module) or ../../ncs:module[ncs:name='tailf-ned-cisco-ios']";
      tailf:info
        "Global trunk configuration";
      list group {
        tailf:info
          "Specify a trunk group";
        tailf:cli-mode-name "config-trunk-group";
        key "name";
        leaf name {
          type string {
            tailf:info
              "WORD;;Trunk group label";
          }
        }
        container hunt-scheme {
          tailf:info
            "The hunt scheme in trunk group";
          choice hunt-scheme-choice {
            container round-robin {
              tailf:info
                "The next interface with free timeslots is selected";
              tailf:cli-compact-syntax;
              tailf:cli-delete-when-empty;
              presence "true";
            }
            leaf random {
              tailf:info
                "The timeslot is selected randomly";
              type empty;
            }
            leaf sequential {
              type empty;
            }
          }
        }
      }
    }
    container gw-accounting {
      tailf:ncs-device-type "cli-ned";
      tailf:display-when "not(../../ncs:module) or ../../ncs:module[ncs:name='tailf-ned-cisco-ios']";
      choice gw-accounting-choice {
        container syslog {
          tailf:info
            "Enable voip syslog accounting.";
          tailf:cli-delete-when-empty;
          presence "true";
          leaf stats {
            tailf:info
              "Enable stats as part of accounting.";
            type empty;
          }
        }
        leaf aaa {
          tailf:info
            "Enable aaa accounting";
          type empty;
        }
        leaf file {
          tailf:info
            "Enable voip file accounting.";
          type empty;
        }
        container h323 {
          tailf:cli-delete-when-empty;
          presence "true";
          leaf vsa {
            type empty;
          }
        }
        leaf voip {
          type empty;
        }
      }
    }
    list voice-card {
      tailf:ncs-device-type "cli-ned";
      tailf:display-when "not(../ncs:module) or ../ncs:module[ncs:name='tailf-ned-cisco-ios']";
      tailf:info
        "Configure a specific voice-card";
      tailf:cli-mode-name "config-voicecard";
      key "slot";
      leaf slot {
        type string {
          tailf:info
            "WORD;;Voice interface slot/abay";
          pattern '[0-9]+.*';
        }
      }
      leaf dspfarm {
        tailf:info
          "Enable dspFarm feature for this voice card";
        type empty;
      }
      leaf watchdog {
        tailf:cli-boolean-no;
        tailf:cli-full-command;
        type boolean;
        default "true";
      }
    }
    container voice {
      tailf:ncs-device-type "cli-ned";
      tailf:display-when "not(../../ncs:module) or ../../ncs:module[ncs:name='tailf-ned-cisco-ios']";
      tailf:info
        "Global voice configuration";
      container service {
        tailf:info
          "Global packet telephony service commands";
        container voip {
          tailf:info
            "Voice over IP";
          tailf:cli-add-mode;
          tailf:cli-mode-name "conf-voi-serv";
          container sip {
            tailf:info
              "SIP configuration commands";
            tailf:cli-add-mode;
            tailf:cli-mode-name "conf-serv-sip";
            tailf:cli-delete-when-empty;
            presence "true";
            container bind {
              tailf:info
                "SIP bind command";
              container control {
                tailf:info
                  "bind only SIP control packets";
                container source-interface {
                  tailf:info
                    "Specify interface for source address of SIP packets";
                  tailf:cli-compact-syntax;
                  uses interface-name-grouping;
                }
              }
              container media {
                tailf:info
                  "bind only SIP media packets";
                container source-interface {
                  tailf:info
                    "Specify interface for source address of SIP packets";
                  tailf:cli-compact-syntax;
                  uses interface-name-grouping;
                }
              }
            }
          }
        }
      }
      container iec {
        tailf:info
          "Configure Internal Error Code behavior";
        leaf syslog {
          tailf:info
            "Enable syslog reporting whenever an IEC is triggered";
          type empty;
        }
      }
      list translation-rule {
        tailf:info
          "Translation Rule configuration commands";
        tailf:cli-mode-name "cfg-translation-rule";
        key "tag";
        leaf tag {
          type uint32 {
            tailf:info
              "<1-2147483647>;;Translation rule tag";
            range "1..2147483647";
          }
        }
        list rule {
          tailf:info
            "Translation rule";
          tailf:cli-suppress-mode;
          tailf:cli-delete-when-empty;
          tailf:cli-incomplete-command;
          tailf:cli-compact-syntax;
          tailf:cli-sequence-commands {
            tailf:cli-reset-all-siblings;
          }
          ordered-by user;
          key "tag";
          leaf tag {
            type uint8 {
              tailf:info
                "<1-15>;;Translation rule tag";
              range "1..15";
            }
          }
          leaf reject {
            tailf:info
              "Call block rule";
            tailf:cli-optional-in-sequence;
            type empty;
          }
          leaf pattern {
            tailf:cli-drop-node-name;
            tailf:cli-full-command;
            tailf:cli-multi-value;
            type string {
              tailf:info
                "WORD;;Matching pattern";
            }
          }
        }
      }
      list translation-profile {
        tailf:info
          "Translation profile configuration commands";
        tailf:cli-mode-name "cfg-translation-profile";
        key "name";
        leaf name {
          type string {
            tailf:info
              "WORD;;Translation profile name";
          }
        }
        container translate {
          tailf:info
            "Specify numbers that should be translated";
          list called {
            tailf:info
              "Translation rule for the called-number";
            tailf:cli-suppress-mode;
            tailf:cli-delete-when-empty;
            key "tag";
            leaf tag {
              type uint32 {
                tailf:info
                  "<1-2147483647>;;Translation rule tag";
                range "1..2147483647";
              }
            }
          }
        }
      }
    }
    container event {
      tailf:ncs-device-type "cli-ned";
      tailf:display-when "not(../../ncs:module) or ../../ncs:module[ncs:name='tailf-ned-cisco-ios']";
      tailf:info
        "Event related configuration commands";
      container manager {
        tailf:info
          "Event Manager configuration commands";
        list environment {
          tailf:info
            "Set an Embedded Event Manager global environment variable";
          tailf:cli-suppress-mode;
          tailf:cli-delete-when-empty;
          key "name";
          leaf name {
            type string {
              tailf:info
                "WORD;;Name of the global environment variable";
            }
          }
          leaf value {
            tailf:cli-multi-value;
            tailf:cli-drop-node-name;
            type string {
              tailf:info
                "LINE;;Value of the global environment variable";
            }
          }
        }
        container session {
          tailf:info
            "Set Embedded Event Manager session attributes";
          container cli {
            tailf:info
              "Set Embedded Event Manager session cli attributes";
            leaf username {
              tailf:info
                "Set username used in Embedded Event Manager cli sessions";
              type string {
                tailf:info
                  "WORD;;username";
              }
            }
          }
        }
        container directory {
          tailf:info
            "Set Embedded Event Manager directory information";
          container user {
            tailf:info
              "Set Embedded Event Manager user directory information";
            leaf policy {
              tailf:info
                "Set Embedded Event Manager user policy directory";
              type string {
                tailf:info
                  "WORD;;Path of the Embedded Event Manager user policy directory";
              }
            }
          }
        }
        list applet {
          tailf:info
            "Register an Event Manager applet";
          tailf:cli-mode-name "config-applet";
          tailf:cli-exit-command "exit" {
            tailf:info
              "Exit from Event Manager applet configuration submode";
          }
          key "name";
          leaf name {
            type string {
              tailf:info
                "WORD;;Name of the Event Manager applet";
            }
          }
          leaf description {
            tailf:info
              "Add or modify an applet description";
            tailf:cli-multi-value;
            tailf:cli-preformatted;
            tailf:cli-full-command;
            type string {
              tailf:info
                "LINE;;description";
            }
          }
          leaf authorization {
            tailf:info
              "Specify an authorization type for the applet";
            tailf:cli-hide-in-submode;
            type enumeration {
              enum "bypass" {
                tailf:info
                  "EEM aaa authorization type bypass";
              }
            }
          }
          leaf class {
            tailf:info
              "Specify a class for the applet";
            tailf:cli-hide-in-submode;
            type string {
              tailf:info
                "Class A-Z | default - default class";
              pattern '[A-Z]|default';
            }
          }
          leaf trap {
            tailf:info
              "Generate an SNMP trap when applet is triggered.";
            tailf:cli-hide-in-submode;
            type empty;
          }
          container event {
            tailf:info
              "Add or modify event information";
            uses event-manager-applet-event-grouping;
            list tag {
              tailf:info
                "event tag identifier";
              tailf:cli-suppress-mode;
              tailf:cli-delete-when-empty;
              key "name";
              leaf name {
                type string {
                  tailf:info
                    "WORD;;tag name";
                }
              }
              uses event-manager-applet-event-grouping;
            }
          }
          list action {
            tailf:info
              "Add or modify an action statement";
            tailf:cli-suppress-mode;
            tailf:cli-delete-when-empty;
            tailf:cli-compact-syntax;
            tailf:cli-reset-container;
            tailf:cli-incomplete-command;
            ordered-by user;
            key "name";
            leaf name {
              type string {
                tailf:info
                  "WORD;;Label";
              }
            }
            choice action-choice {
              container cli {
                tailf:info
                  "Execute a CLI command";
                tailf:cli-compact-syntax;
                leaf command {
                  tailf:info
                    "CLI command";
                  type string {
                    tailf:info
                      "WORD;;CLI string";
                  }
                }
                leaf pattern {
                  tailf:info
                    "response pattern";
                  type string {
                    tailf:info
                      "WORD;;pattern";
                  }
                }
              }
              leaf regexp {
                tailf:info
                  "regular expression match";
                tailf:cli-full-command;
                type string {
                  tailf:info
                    "WORD;;regular expression pattern";
                }
              }
              leaf wait {
                tailf:info
                  "Wait for a specified amount of time";
                type uint32 {
                  tailf:info
                    "<1-31536000>;;Seconds value";
                  range "1..31536000";
                }
              }
              container syslog {
                tailf:info
                  "Log a syslog message";
                tailf:cli-compact-syntax;
                leaf priority {
                  tailf:info
                    "Priority of syslog message";
                  type logging-level-type;
                }
                leaf msg {
                  tailf:info
                    "Syslog message";
                  type string {
                    tailf:info
                      "WORD;;message string";
                  }
                }
                leaf facility {
                  tailf:info
                    "Facility string";
                  type string {
                    tailf:info
                      "WORD;;facility string";
                  }
                }
                leaf filter {
                  tailf:info
                    "Filter destination of syslog message";
                  type enumeration {
                    enum "esm" {
                      tailf:info
                        "Filter destination is ESM";
                    }
                  }
                }
              }
              container snmp-trap {
                tailf:info
                  "Send an SNMP trap";
                tailf:cli-compact-syntax;
                leaf intdata1 {
                  tailf:info
                    "SNMP integer data1";
                  type int32 {
                    tailf:info
                      "<-2147483648 - 2147483647>;;SNMP trap integer value1";
                  }
                }
                leaf intdata2 {
                  tailf:info
                    "SNMP integer data2";
                  type int32 {
                    tailf:info
                      "<-2147483648 - 2147483647>;;SNMP trap integer value2";
                  }
                }
                leaf strdata {
                  tailf:info
                    "SNMP trap string";
                  type string {
                    tailf:info
                      "WORD;;SNMP trap string value";
                  }
                }
              }
              leaf cmd {
                tailf:cli-drop-node-name;
                tailf:cli-multi-value;
                type string {
                  tailf:info
                    "Action string within quotes";
                }
              }
            }
          }
          container trigger {
            tailf:info
              "Enter applet trigger configuration submode";
            tailf:cli-add-mode;
            tailf:cli-mode-name "config-applet-trigger";
            presence "true";
            container correlate {
              tailf:info
                "event correlation statement";
              tailf:cli-compact-syntax;
              tailf:cli-sequence-commands {
                tailf:cli-reset-siblings;
              }
              leaf event {
                tailf:info
                  "event for correlation";
                type string {
                  tailf:info
                    "WORD;;event tag value";
                }
              }
              leaf operand2 {
                tailf:cli-drop-node-name;
                tailf:cli-incomplete-command;
                type enumeration {
                  enum "and" {
                    tailf:info
                      "Use boolean and logic";
                  }
                  enum "andnot" {
                    tailf:info
                      "Use boolean andnot logic";
                  }
                  enum "or" {
                    tailf:info
                      "Use boolean or logic";
                  }
                }
              }
              container event2 {
                tailf:cli-drop-node-name;
                tailf:cli-flatten-container;
                tailf:cli-compact-syntax;
                leaf event {
                  tailf:info
                    "event2 for correlation";
                  type string {
                    tailf:info
                      "WORD;;event tag value";
                  }
                }
              }
            }
          }
        }
        list policy {
          tailf:info
            "Run a pre-registered policy";
          tailf:cli-suppress-mode;
          tailf:cli-delete-when-empty;
          tailf:cli-compact-syntax;
          key "name";
          leaf name {
            type string {
              tailf:info
                "WORD;;Name of the Embedded Event Manager policy file";
            }
          }
          leaf type {
            tailf:info
              "Type of Embedded Event Manager policy";
            type enumeration {
              enum "system" {
                tailf:info
                  "Search for a Embedded Event Manager system policy";
              }
              enum "user" {
                tailf:info
                  "Search for a Embedded Event Manager user policy";
              }
            }
          }
        }
      }
    }
    leaf disable-eadi {
      tailf:ncs-device-type "cli-ned";
      tailf:display-when "not(../../ncs:module) or ../../ncs:module[ncs:name='tailf-ned-cisco-ios']";
      tailf:cli-full-command;
      type empty;
    }
    container memory-size {
      tailf:ncs-device-type "cli-ned";
      tailf:display-when "not(../../ncs:module) or ../../ncs:module[ncs:name='tailf-ned-cisco-ios']";
      tailf:info
        "Adjust memory size by percentage";
      leaf iomem {
        tailf:info
          "I/O memory";
        type uint8 {
          tailf:info
            "<5-25>;;percentage of DRAM to use for I/O memory: 5, 10, 15, 20, 25";
          range "5..25" {
            tailf:step "5";
          }
        }
      }
    }
    container memory {
      tailf:ncs-device-type "cli-ned";
      tailf:display-when "not(../../ncs:module) or ../../ncs:module[ncs:name='tailf-ned-cisco-ios']";
      tailf:info
        "Configure memory management";
      container free {
        tailf:info
          "free memory low water mark";
        container low-watermark {
          tailf:info
            "low water mark for notifications";
          leaf processor {
            tailf:info
              "Processor memory";
            type uint32 {
              tailf:info
                "<1-3994575>;;low water mark of memory in KB";
            }
          }
        }
      }
    }
    container transceiver {
      tailf:ncs-device-type "cli-ned";
      tailf:display-when "not(../../ncs:module) or ../../ncs:module[ncs:name='tailf-ned-cisco-ios']";
      tailf:info
        "Select from transceiver configuration commands";
      container type {
        tailf:info
          "type keyword";
        container all {
          tailf:cli-add-mode;
          tailf:cli-mode-name "config-xcvr-type";
          tailf:cli-full-command;
          container monitoring {
            tailf:info
              "Enable/disable monitoring";
            presence "true";
            leaf interval {
              tailf:info
                "Set interval for monitoring";
              type uint16 {
                tailf:info
                  "<300-3600>;;Time interval for monitoring transceiver in seconds";
                range "300..3600";
              }
            }
          }
        }
      }
    }
    list alias {
      tailf:ncs-device-type "cli-ned";
      tailf:display-when "not(../ncs:module) or ../ncs:module[ncs:name='tailf-ned-cisco-ios']";
      tailf:info
        "Create command alias";
      tailf:cli-suppress-mode;
      tailf:cli-delete-when-empty;
      key "mode name";
      leaf mode {
        type string {
          tailf:info
            "WORD;;;Alias mode";
        }
      }
      leaf name {
        type string {
          tailf:info
            "WORD;;Alias name";
        }
      }
      leaf line {
        tailf:cli-drop-node-name;
        tailf:cli-multi-value;
        tailf:cli-no-value-on-delete;
        tailf:cli-full-command;
        type string {
          tailf:info
            "WORD;;alias line";
        }
      }
    }
    container spd {
      tailf:ncs-device-type "cli-ned";
      tailf:display-when "not(../../ncs:module) or ../../ncs:module[ncs:name='tailf-ned-cisco-ios']";
      leaf enable {
        tailf:cli-boolean-no;
        tailf:cli-full-command;
        type boolean;
        default "true";
      }
      leaf headroom {
        type uint16;
      }
    }
    container cached-show {
      tailf:ncs-device-type "cli-ned";
      tailf:display-when "not(../../ncs:module) or ../../ncs:module[ncs:name='tailf-ned-cisco-ios']";
      container version {
        tailf:info
          "Cached output of 'show version' on device";
        leaf version {
          type string;
        }
        leaf model {
          type string;
        }
        container license {
          leaf level {
            type string;
          }
          leaf type {
            type string;
          }
        }
      }
      container license {
        tailf:info
          "Cached output of 'show license udi' on device";
        container udi {
          leaf pid {
            type string;
          }
          leaf sn {
            type string;
          }
        }
      }
      list inventory {
        tailf:info
          "Cached output of 'show inventory' on device";
        tailf:cli-suppress-mode;
        key "name";
        leaf name {
          tailf:cli-expose-key-name;
          type string;
        }
        leaf sn {
          type string;
        }
      }
    }
    leaf xxyyzztop {
      tailf:ncs-device-type "cli-ned";
      tailf:display-when "not(../../ncs:module) or ../../ncs:module[ncs:name='tailf-ned-cisco-ios']";
      tailf:info
        "Internal state variable, do not modify.";
      tailf:cli-run-template "";
      tailf:cli-show-with-default;
      type uint16;
      default "0";
    }
    leaf xxyyzzfail {
      tailf:ncs-device-type "cli-ned";
      tailf:display-when "not(../../ncs:module) or ../../ncs:module[ncs:name='tailf-ned-cisco-ios']";
      type empty;
    }
  }
  augment "/ncs:devices/ncs:template/ncs:config" {
    container upgrade {
      container fpd {
        leaf auto {
          type empty;
        }
        leaf path {
          type string;
        }
      }
    }
    container tailfned {
      leaf police {
        type string;
      }
      container api {
        leaf new-ip-access-list {
          type empty;
        }
      }
    }
    leaf version {
      type string;
    }
    container service {
      leaf config {
        type empty;
      }
      leaf exec-callback {
        type empty;
      }
      leaf nagle {
        type empty;
      }
      leaf slave-log {
        type string;
        // NCS drop default statement
      }
      container pad {
        leaf to-xot {
          type empty;
        }
        leaf from-xot {
          type empty;
        }
        leaf cmns {
          type empty;
        }
      }
      container conf {
        leaf pad {
          type string;
          // NCS drop default statement
        }
      }
      leaf tcp-keepalives-in {
        type empty;
      }
      leaf tcp-keepalives-out {
        type empty;
      }
      container timestamps {
        presence "true";
        container debug {
          choice timestamp-choice {
            leaf uptime {
              type empty;
            }
            container datetime {
              presence "true";
              leaf msec {
                type empty;
              }
              leaf localtime {
                type empty;
              }
              leaf show-timezone {
                type empty;
              }
              leaf year {
                type empty;
              }
            }
          }
        }
        container log {
          choice timestamp-choice {
            leaf uptime {
              type empty;
            }
            container datetime {
              presence "true";
              leaf msec {
                type empty;
              }
              leaf localtime {
                type empty;
              }
              leaf show-timezone {
                type empty;
              }
              leaf year {
                type empty;
              }
            }
          }
        }
      }
      container password-encryption {
        presence "true";
      }
      leaf password-recovery {
        type string;
      }
      leaf exec-wait {
        type empty;
      }
      leaf linenumber {
        type empty;
      }
      leaf compress-config {
        type empty;
      }
      leaf udp-small-servers {
        type empty;
      }
      container prompt {
        leaf config {
          type string;
          // NCS drop default statement
        }
      }
      leaf tcp-small-servers {
        type empty;
      }
      leaf old-slip-prompts {
        type empty;
      }
      leaf pt-vty-logging {
        type empty;
      }
      leaf disable-ip-fast-frag {
        type empty;
      }
      leaf sequence-numbers {
        type empty;
      }
      container divert-rate-limit {
        list ip {
          // NCS patched for predictable order
          ordered-by user;
          key "divert-code";
          leaf divert-code {
            type string;
          }
          leaf rate {
            type string;
          }
          leaf limit {
            type string;
          }
        }
        list ipv6 {
          // NCS patched for predictable order
          ordered-by user;
          key "divert-code";
          leaf divert-code {
            type string;
          }
          leaf rate {
            type string;
          }
          leaf limit {
            type string;
          }
        }
        list trusted-site {
          // NCS patched for predictable order
          ordered-by user;
          key "ip-address mask-ip-address tos mask";
          // NCS drop max-elements statement
          leaf ip-address {
            type string;
          }
          leaf mask-ip-address {
            type string;
          }
          leaf tos {
            type string;
          }
          leaf mask {
            type string;
          }
        }
        list trusted-site-ipv6 {
          // NCS patched for predictable order
          ordered-by user;
          key "ip-address traffic-class mask";
          // NCS drop max-elements statement
          leaf ip-address {
            type string;
          }
          leaf traffic-class {
            type string;
          }
          leaf mask {
            type string;
          }
        }
      }
      container counters {
        container max {
          leaf age {
            type string;
          }
        }
      }
      container alignment {
        leaf detection {
          type string;
          // NCS drop default statement
        }
        leaf logging {
          type string;
          // NCS drop default statement
        }
      }
      leaf call-home {
        type empty;
      }
      leaf dhcp {
        type string;
        // NCS drop default statement
      }
      leaf finger {
        type empty;
      }
      container heartbeat {
        leaf fatal-count {
          type string;
        }
        leaf interrupt-interval {
          type string;
        }
        leaf interrupt-max {
          type string;
        }
        leaf transmit-interval {
          type string;
        }
        leaf warning-timeout {
          type string;
        }
        leaf fatal-timeout {
          type string;
        }
        leaf cslipc-timeout {
          type string;
        }
        leaf alive-timeout {
          type string;
        }
      }
      leaf hide-telnet-addresses {
        type empty;
      }
      leaf unsupported-transceiver {
        type empty;
      }
      leaf internal {
        type empty;
      }
    }
    container boot {
      leaf config {
        type string;
      }
      container network {
        leaf remote-url {
          type string;
        }
      }
    }
    container password {
      container encryption {
        leaf aes {
          type empty;
        }
      }
    }
    container login {
      container block-for {
        leaf seconds {
          type string;
        }
        leaf attempts {
          type string;
        }
        leaf within {
          type string;
        }
      }
      container on-failure {
        leaf log {
          type empty;
        }
        leaf every {
          type string;
          // NCS drop default statement
        }
      }
      container on-success {
        leaf log {
          type empty;
        }
        leaf every {
          type string;
          // NCS drop default statement
        }
      }
    }
    container cdp {
      leaf run {
        type string;
        // NCS drop default statement
      }
      leaf advertise-v2 {
        type string;
        // NCS drop default statement
      }
      container tlv {
        leaf location {
          type string;
          // NCS drop default statement
        }
        leaf app {
          type string;
          // NCS drop default statement
        }
      }
    }
    container platform {
      leaf shell {
        type empty;
      }
      leaf console {
        type string;
      }
      container bfd {
        leaf allow-svi {
          type empty;
        }
      }
      leaf bfd-debug-trace {
        type string;
      }
      container enable {
        list controller {
          // NCS patched for predictable order
          ordered-by user;
          key "name";
          leaf name {
            type string;
          }
        }
      }
      container hardware {
        container throughput {
          container level {
            choice throughput-choice {
              leaf MB {
                type string;
              }
              leaf kbps {
                type string;
              }
            }
          }
        }
      }
      container ipccl {
        leaf log-history {
          type string;
        }
      }
      container ipv4 {
        container pbr {
          container optimize {
            leaf tcam {
              type empty;
            }
          }
        }
      }
      container ring {
        leaf rx {
          type string;
        }
      }
      container tcam-parity-error {
        leaf enable {
          type empty;
        }
      }
      container tcam-threshold {
        leaf alarm-frequency {
          type string;
        }
      }
      container multicast {
        container lre {
          leaf off {
            type empty;
          }
        }
      }
      container punt-keepalive {
        leaf disable-kernel-core {
          type string;
        }
      }
      list punt-policer {
        // NCS patched for predictable order
        ordered-by user;
        key "cause";
        leaf cause {
          type string;
        }
        leaf rate {
          type string;
        }
      }
      container punt-policer-high {
        list punt-policer {
          // NCS patched for predictable order
          ordered-by user;
          key "cause";
          leaf cause {
            type string;
          }
          leaf rate {
            type string;
          }
          leaf high {
            type empty;
          }
        }
      }
      container punt-sbrl {
        container wan {
          list punt-cause {
            // NCS patched for predictable order
            ordered-by user;
            key "cause";
            leaf cause {
              type string;
            }
            leaf rate {
              type string;
            }
            leaf quarantine-time {
              type string;
            }
            leaf burst-factor {
              type string;
            }
          }
        }
        container subscriber {
          leaf rate {
            type string;
          }
        }
      }
      container qos {
        leaf marker-statistics {
          type empty;
        }
        container match-statistics {
          leaf per-filter {
            type empty;
          }
          leaf per-ace {
            // NCS drop tailf-common:cli-diff-dependency statement
            type empty;
          }
        }
        leaf performance-monitor {
          type empty;
        }
        leaf punt-path-matching {
          type empty;
        }
      }
      container power {
        container redundancy-mode {
          leaf nplus1 {
            type empty;
          }
        }
      }
    }
    leaf hostname {
      type string;
    }
    container boot-marker {
      container boot {
        list system {
          // NCS patched for predictable order
          ordered-by user;
          key "entry";
          leaf entry {
            type string;
          }
        }
      }
    }
    container shell {
      leaf processing {
        type string;
        // NCS drop default statement
      }
    }
    container aqm-register-fnf {
      presence "true";
    }
    container service-module {
      list wlan-ap {
        // NCS patched for predictable order
        ordered-by user;
        key "interface-number";
        leaf interface-number {
          type string;
        }
        leaf bootimage {
          type string;
        }
      }
    }
    container vrf {
      list definition {
        // NCS patched for predictable order
        ordered-by user;
        unique "rd";
        key "name";
        leaf name {
          type string;
        }
        leaf description {
          type string;
        }
        leaf rd {
          type string;
        }
        container route-target {
          // NCS drop tailf-common:cli-diff-dependency statement
          uses ncs_template_route-target-grouping;
        }
        container address-family {
          container ipv4 {
            presence "true";
            uses ncs_template_vrf-definition-af-grouping;
            container mdt {
              container default {
                leaf address {
                  type string;
                }
                container mpls {
                  leaf mldp {
                    type string;
                  }
                }
              }
              container data {
                list multicast {
                  // NCS patched for predictable order
                  ordered-by user;
                  key "address wildcard";
                  leaf address {
                    type string;
                  }
                  leaf wildcard {
                    type string;
                  }
                }
                leaf list {
                  type string;
                }
                leaf threshold {
                  type string;
                }
              }
              leaf log-reuse {
                type empty;
              }
              leaf-list preference {
                // NCS patched for predictable order
                ordered-by user;
                type string;
              }
            }
          }
          container ipv6 {
            presence "true";
            uses ncs_template_vrf-definition-af-grouping;
          }
        }
      }
    }
    container security {
      container passwords {
        leaf min-length {
          type string;
        }
      }
      container authentication {
        container failure {
          leaf rate {
            type string;
          }
          leaf log {
            type empty;
          }
        }
      }
    }
    container enable {
      container password {
        uses ncs_template_password-grouping;
      }
      container password-conf {
        container password {
          list level {
            // NCS patched for predictable order
            ordered-by user;
            key "level";
            leaf level {
              type string;
            }
            uses ncs_template_password-grouping;
          }
        }
      }
      leaf last-resort {
        type string;
      }
      container secret {
        leaf type {
          type string;
        }
        leaf secret {
          type string;
        }
      }
      container secret-conf {
        container secret {
          list level {
            // NCS patched for predictable order
            ordered-by user;
            key "level";
            leaf level {
              type string;
            }
            leaf type {
              type string;
            }
            leaf secret {
              type string;
            }
          }
        }
      }
      leaf use-tacacs {
        type empty;
      }
    }
    container aaa {
      leaf new-model {
        type empty;
      }
      container group {
        // NCS drop tailf-common:cli-diff-dependency statement
        container server {
          list radius {
            // NCS patched for predictable order
            ordered-by user;
            key "name";
            leaf name {
              type string;
            }
            container server {
              list name {
                // NCS patched for predictable order
                ordered-by user;
                key "name";
                leaf name {
                  type string;
                }
              }
              list direct {
                // NCS patched for predictable order
                ordered-by user;
                key "name";
                leaf name {
                  type string;
                }
                leaf auth-port {
                  type string;
                }
                leaf acct-port {
                  type string;
                }
              }
            }
            list server-private {
              // NCS patched for predictable order
              ordered-by user;
              key "name";
              leaf name {
                type string;
              }
              uses ncs_template_radius-server-grouping;
            }
            container backoff {
              container exponential {
                presence "true";
                leaf max-delay {
                  type string;
                  // NCS drop default statement
                }
                leaf backoff-retry {
                  type string;
                  // NCS drop default statement
                }
              }
            }
            container ip {
              container vrf {
                leaf forwarding {
                  // NCS drop tailf-common:cli-diff-dependency statement
                  type string;
                }
              }
              container radius {
                container source-interface {
                  uses ncs_template_interface-name-grouping;
                }
              }
            }
            leaf deadtime {
              type string;
            }
          }
          list tacacs-plus {
            // NCS patched for predictable order
            ordered-by user;
            tailf:alt-name "tacacs+";
            key "name";
            leaf name {
              type string;
            }
            container server {
              list name {
                // NCS patched for predictable order
                ordered-by user;
                key "name";
                leaf name {
                  type string;
                }
              }
              list server-list {
                // NCS patched for predictable order
                ordered-by user;
                key "name";
                leaf name {
                  type string;
                }
              }
            }
            list server-private {
              // NCS patched for predictable order
              ordered-by user;
              key "name";
              leaf name {
                type string;
              }
              leaf timeout {
                type string;
              }
              container key {
                uses ncs_template_password-grouping;
              }
            }
            container ip {
              container vrf {
                leaf forwarding {
                  // NCS drop tailf-common:cli-diff-dependency statement
                  type string;
                }
              }
              container tacacs {
                container source-interface {
                  uses ncs_template_interface-name-grouping;
                }
              }
            }
          }
        }
      }
      container authentication {
        // NCS drop tailf-common:cli-diff-dependency statement
        container attempts {
          leaf login {
            type string;
            // NCS drop default statement
          }
        }
        leaf username-prompt {
          type string;
        }
        list dot1x {
          // NCS patched for predictable order
          ordered-by user;
          key "name";
          leaf name {
            type string;
          }
          leaf cache {
            type string;
          }
          leaf group {
            type string;
          }
        }
        list login {
          // NCS patched for predictable order
          ordered-by user;
          key "name";
          leaf name {
            type string;
          }
          uses ncs_template_aaa-authentication-method-grouping;
        }
        container enable {
          container default {
            uses ncs_template_aaa-authentication-method-grouping;
          }
        }
        list ppp {
          // NCS patched for predictable order
          ordered-by user;
          key "name";
          leaf name {
            type string;
          }
          uses ncs_template_aaa-authentication-method-grouping;
        }
      }
      container authorization {
        // NCS drop tailf-common:cli-diff-dependency statement
        leaf console {
          type empty;
        }
        leaf config-commands {
          type empty;
        }
        list exec {
          // NCS patched for predictable order
          ordered-by user;
          key "name";
          leaf name {
            type string;
          }
          uses ncs_template_aaa-authorization-method-grouping;
        }
        list commands {
          // NCS patched for predictable order
          ordered-by user;
          key "level name";
          leaf level {
            type string;
          }
          leaf name {
            type string;
          }
          uses ncs_template_aaa-authorization-method-grouping;
        }
        list eventmanager {
          // NCS patched for predictable order
          ordered-by user;
          key "name";
          leaf name {
            type string;
          }
          uses ncs_template_aaa-authorization-method-grouping;
        }
        list network {
          // NCS patched for predictable order
          ordered-by user;
          key "name";
          leaf name {
            type string;
          }
          uses ncs_template_aaa-authorization-method-grouping;
        }
        list auth-proxy {
          // NCS patched for predictable order
          ordered-by user;
          key "name";
          leaf name {
            type string;
          }
          uses ncs_template_aaa-authorization-method-grouping;
        }
      }
      container accounting {
        // NCS drop tailf-common:cli-diff-dependency statement
        container send {
          container stop-record {
            container authentication {
              leaf failure {
                type empty;
              }
              container failure-vrf {
                container failure {
                  list vrf {
                    // NCS patched for predictable order
                    ordered-by user;
                    key "name";
                    leaf name {
                      // NCS drop tailf-common:cli-diff-dependency statement
                      // NCS drop tailf-common:cli-diff-dependency statement
                      type string;
                    }
                  }
                }
              }
            }
          }
        }
        container nested {
          presence "true";
          container suppress {
            leaf stop {
              type empty;
            }
          }
        }
        list commands {
          // NCS patched for predictable order
          ordered-by user;
          key "level name";
          leaf level {
            type string;
          }
          leaf name {
            type string;
          }
          uses ncs_template_aaa-accounting-method-grouping;
        }
        list exec {
          // NCS patched for predictable order
          ordered-by user;
          key "name";
          leaf name {
            type string;
          }
          uses ncs_template_aaa-accounting-method-grouping;
        }
        list network {
          // NCS patched for predictable order
          ordered-by user;
          key "name";
          leaf name {
            type string;
          }
          uses ncs_template_aaa-accounting-method-grouping;
        }
        list auth-proxy {
          // NCS patched for predictable order
          ordered-by user;
          key "name";
          leaf name {
            type string;
          }
          uses ncs_template_aaa-accounting-method-grouping;
        }
        list connection {
          // NCS patched for predictable order
          ordered-by user;
          key "name";
          leaf name {
            type string;
          }
          uses ncs_template_aaa-accounting-method-grouping;
        }
        list dot1x {
          // NCS patched for predictable order
          ordered-by user;
          key "name";
          leaf name {
            type string;
          }
          uses ncs_template_aaa-accounting-method-grouping;
        }
        container system {
          container default {
            presence "true";
            uses ncs_template_aaa-accounting-method-grouping;
          }
        }
        container suppress {
          leaf null-username {
            type empty;
          }
        }
        container update {
          leaf newinfo {
            type empty;
          }
          leaf periodic {
            type string;
          }
        }
        container delay-start {
          presence "true";
          leaf all {
            type empty;
          }
        }
      }
      leaf session-id {
        // NCS drop tailf-common:cli-diff-dependency statement
        type string;
      }
      container attribute {
        // NCS drop tailf-common:cli-diff-dependency statement
        list list {
          // NCS patched for predictable order
          ordered-by user;
          key "name";
          leaf name {
            type string;
          }
          container attribute {
            container type {
              leaf interface-config {
                type string;
              }
            }
          }
        }
      }
      container server {
        // NCS drop tailf-common:cli-diff-dependency statement
        container radius {
          container dynamic-author {
            list client {
              // NCS patched for predictable order
              ordered-by user;
              key "address";
              leaf address {
                type string;
              }
              container server-key {
                uses ncs_template_password-grouping {
                  refine "secret";
                }
              }
            }
          }
        }
      }
    }
    list switch {
      // NCS patched for predictable order
      ordered-by user;
      key "id";
      leaf id {
        type string;
      }
      leaf provision {
        type string;
      }
    }
    container resource {
      container policy {
        presence "true";
        list policy {
          // NCS patched for predictable order
          ordered-by user;
          key "name";
          leaf name {
            type string;
          }
          leaf global {
            type empty;
          }
          leaf system {
            type empty;
          }
        }
      }
    }
    container cns {
      list trusted-server {
        // NCS patched for predictable order
        ordered-by user;
        key "agent name";
        leaf agent {
          type string;
        }
        leaf name {
          type string;
        }
      }
      container id {
        leaf string {
          type string;
        }
        container id-services-list {
          list string {
            // NCS patched for predictable order
            ordered-by user;
            key "service";
            leaf string {
              type string;
            }
            leaf service {
              type string;
            }
          }
        }
      }
      list event {
        // NCS patched for predictable order
        ordered-by user;
        key "name";
        leaf name {
          type string;
        }
        leaf port-number {
          type string;
        }
        container source {
          uses ncs_template_interface-name-grouping;
        }
        container keepalive {
          leaf seconds {
            type string;
          }
          leaf retry-count {
            type string;
          }
        }
      }
      container image {
        container server {
          leaf server-url {
            type string;
          }
          leaf status {
            type string;
          }
        }
      }
      container config {
        container notify {
          leaf capture {
            type string;
          }
          leaf interval {
            type string;
          }
        }
        container partial {
          leaf host {
            type string;
          }
          leaf port-number {
            type string;
          }
        }
      }
      list exec {
        // NCS patched for predictable order
        ordered-by user;
        // NCS drop max-elements statement
        key "port-number";
        leaf encrypt {
          type empty;
        }
        leaf port-number {
          type string;
        }
        container source {
          uses ncs_template_interface-name-grouping;
        }
      }
      leaf dhcp {
        type empty;
      }
    }
    container epm {
      leaf logging {
        type empty;
      }
    }
    container clock {
      container timezone {
        leaf zone {
          type string;
        }
        leaf offset {
          type string;
        }
        leaf hours {
          type string;
        }
        leaf minutes {
          type string;
        }
      }
      container summer-time {
        leaf zone {
          type string;
        }
        choice summer-choice {
          case date-case {
            leaf date {
              type empty;
            }
            leaf date-start-month {
              type string;
            }
            leaf date-start-date {
              type string;
            }
            leaf date-start-year {
              type string;
            }
            leaf date-start-time {
              type string;
            }
            leaf date-end-month {
              type string;
            }
            leaf date-end-date {
              type string;
            }
            leaf date-end-year {
              type string;
            }
            leaf date-end-time {
              type string;
            }
            leaf date-offset {
              type string;
            }
          }
          case recurring-case {
            leaf recurring {
              type empty;
            }
            leaf start {
              type string;
            }
            leaf start-day {
              type string;
            }
            leaf start-month {
              type string;
            }
            leaf start-time {
              type string;
            }
            leaf end {
              type string;
            }
            leaf end-day {
              type string;
            }
            leaf end-month {
              type string;
            }
            leaf end-time {
              type string;
            }
            leaf offset {
              type string;
            }
          }
        }
      }
      container calendar-valid {
        presence "true";
      }
    }
    container device-sensor {
      leaf accounting {
        type empty;
      }
      leaf notify {
        type string;
        // NCS drop default statement
      }
    }
    container call-home {
      leaf contact-email-addr {
        type string;
      }
      container source-interface {
        uses ncs_template_interface-name-grouping;
      }
      leaf vrf {
        // NCS drop tailf-common:cli-diff-dependency statement
        // NCS drop tailf-common:cli-diff-dependency statement
        type string;
      }
      container http-proxy {
        leaf server {
          type string;
        }
        leaf port {
          type string;
        }
      }
      list profile {
        // NCS patched for predictable order
        ordered-by user;
        key "name";
        leaf name {
          type string;
        }
        leaf anonymous-reporting-only {
          type empty;
        }
        leaf active {
          type string;
          // NCS drop default statement
        }
        container destination {
          container transport-method {
            leaf http {
              type empty;
            }
            leaf email {
              type string;
              // NCS drop default statement
            }
          }
          container address {
            leaf http {
              type string;
            }
            leaf email {
              type string;
            }
          }
        }
      }
    }
    container facility-alarm {
      container core-temperature {
        uses ncs_template_facility-alarm-grouping;
      }
      container outlet-temperature {
        uses ncs_template_facility-alarm-grouping;
      }
      container intake-temperature {
        uses ncs_template_facility-alarm-grouping;
      }
      container critical {
        leaf exceed-action {
          type string;
        }
      }
    }
    container cef {
      container table {
        container output-chain {
          container build {
            leaf favor {
              type string;
            }
          }
        }
      }
    }
    container ipdr {
      list session {
        // NCS patched for predictable order
        ordered-by user;
        key "session-id";
        leaf session-id {
          type string;
        }
        leaf session-name {
          type string;
        }
        leaf session-descr {
          type string;
        }
      }
      list type {
        // NCS patched for predictable order
        ordered-by user;
        key "session-id";
        leaf session-id {
          type string;
        }
        choice type-choice {
          leaf ad-hoc {
            type empty;
          }
          leaf event {
            type empty;
          }
          leaf time-interval {
            type string;
          }
        }
      }
      list collector {
        // NCS patched for predictable order
        ordered-by user;
        key "name";
        leaf name {
          type string;
        }
        leaf ip-addr {
          type string;
        }
        leaf port {
          type string;
        }
      }
      list associate {
        // NCS patched for predictable order
        ordered-by user;
        key "session-id";
        leaf session-id {
          type string;
        }
        leaf collector-name {
          type string;
        }
        leaf priority {
          type string;
        }
      }
      list template {
        // NCS patched for predictable order
        ordered-by user;
        key "session-id";
        leaf session-id {
          type string;
        }
        leaf template-name {
          type string;
        }
      }
      container exporter {
        leaf start {
          type empty;
        }
      }
    }
    container qos-conf {
      leaf qos {
        type empty;
      }
    }
    container qos {
      container dbl {
        presence "true";
        container exceed-action {
          leaf ecn {
            type empty;
          }
          leaf probability {
            type string;
          }
        }
      }
      container map {
        container dscp {
          list dscp-to-tq-queue {
            // NCS patched for predictable order
            ordered-by user;
            key "to tx-queue";
            leaf to {
              type string;
            }
            leaf tx-queue {
              type string;
            }
            uses ncs_template_dscp-value-0-7-grouping;
          }
          list dscp-to-cos {
            // NCS patched for predictable order
            ordered-by user;
            key "to cos";
            leaf to {
              type string;
            }
            leaf cos {
              type string;
            }
            uses ncs_template_dscp-value-0-7-grouping;
          }
        }
        container cos {
          list cos-to-dscp {
            // NCS patched for predictable order
            ordered-by user;
            key "to dscp";
            leaf to {
              type string;
            }
            leaf dscp {
              type string;
            }
            uses ncs_template_cos-value-0-7-grouping;
          }
        }
      }
      container account {
        container layer2 {
          container encapsulation {
            leaf length {
              type string;
            }
          }
        }
      }
      container rewrite {
        container ip {
          leaf dscp {
            type string;
            // NCS drop default statement
          }
        }
      }
      list aggregate-policer {
        // NCS patched for predictable order
        ordered-by user;
        key "name";
        leaf name {
          type string;
        }
        leaf rate {
          type string;
        }
        leaf xps {
          type string;
        }
        leaf burst {
          type string;
        }
        leaf burst-type {
          type string;
        }
        container conform-action {
          choice action-choice {
            leaf drop {
              type empty;
            }
            leaf transmit {
              type empty;
            }
          }
        }
        leaf exceed-action {
          type string;
        }
      }
    }
    container card {
      list card-slot {
        // NCS patched for predictable order
        ordered-by user;
        key "slot card-type";
        leaf slot {
          type string;
        }
        leaf card-type {
          type string;
        }
      }
      list card-slot-subslot {
        // NCS patched for predictable order
        ordered-by user;
        key "slot-subslot card-type";
        leaf slot-subslot {
          type string;
        }
        leaf card-type {
          type string;
        }
        leaf SPA-DOCSIS-HD-V1-port {
          // NCS drop when statement
          type string;
        }
        leaf license {
          type string;
        }
      }
      container type {
        list t1 {
          // NCS patched for predictable order
          ordered-by user;
          key "slot";
          leaf slot {
            type string;
          }
        }
        container t1-bay {
          list t1 {
            // NCS patched for predictable order
            ordered-by user;
            key "slot bay";
            leaf slot {
              type string;
            }
            leaf bay {
              type string;
            }
          }
        }
        list t3 {
          // NCS patched for predictable order
          ordered-by user;
          key "slot subslot";
          leaf slot {
            type string;
          }
          leaf subslot {
            type string;
          }
        }
        list e1 {
          // NCS patched for predictable order
          ordered-by user;
          key "slot bay";
          leaf slot {
            type string;
          }
          leaf bay {
            type string;
          }
        }
        list e3 {
          // NCS patched for predictable order
          ordered-by user;
          key "slot subslot";
          leaf slot {
            type string;
          }
          leaf subslot {
            type string;
          }
        }
      }
    }
    container hw-module {
      list bay {
        // NCS patched for predictable order
        ordered-by user;
        key "name";
        leaf name {
          type string;
        }
        leaf shutdown {
          type empty;
        }
        choice power-choice {
          leaf powered {
            type empty;
          }
          leaf unpowered {
            type empty;
          }
        }
      }
      list ism {
        // NCS patched for predictable order
        ordered-by user;
        key "name";
        leaf name {
          type string;
        }
      }
      list slot {
        // NCS patched for predictable order
        ordered-by user;
        key "name";
        leaf name {
          type string;
        }
        leaf process-max-time {
          type string;
        }
      }
      container module {
        list module-list {
          // NCS patched for predictable order
          ordered-by user;
          key "name port-group";
          leaf name {
            type string;
          }
          leaf port-group {
            type string;
          }
          leaf select {
            type string;
          }
        }
      }
    }
    container cable {
      container profile {
        list mac-domain {
          // NCS patched for predictable order
          ordered-by user;
          key "name";
          leaf name {
            type string;
          }
          container cable {
            container dynamic-secret {
              container reject {
                presence "true";
                leaf nocrypt {
                  type empty;
                }
              }
            }
            container privacy {
              leaf bpi-plus-policy {
                type string;
              }
            }
          }
        }
        list wideband-interface {
          // NCS patched for predictable order
          ordered-by user;
          key "name";
          leaf name {
            type string;
          }
          container cable {
            container downstream {
              leaf attribute-mask {
                type string;
              }
            }
          }
        }
        list downstream {
          // NCS patched for predictable order
          ordered-by user;
          key "name";
          leaf name {
            type string;
          }
          container cable {
            container rf-bandwidth-percent {
              leaf percent-value {
                type string;
              }
            }
            leaf attribute-mask {
              type string;
            }
          }
        }
        list service-group {
          // NCS patched for predictable order
          ordered-by user;
          key "name";
          leaf name {
            type string;
          }
          container cable {
            leaf bundle {
              type string;
            }
          }
          list mac-domain {
            // NCS patched for predictable order
            ordered-by user;
            key "id";
            leaf id {
              type string;
            }
            leaf profile {
              type string;
            }
            container downstream {
              list sg-channel {
                // NCS patched for predictable order
                ordered-by user;
                key "profile";
                leaf profile {
                  type string;
                }
                leaf-list id {
                  // NCS patched for predictable order
                  ordered-by user;
                  type string;
                }
                leaf upstream {
                  type string;
                }
              }
            }
            list upstream {
              // NCS patched for predictable order
              ordered-by user;
              key "id";
              leaf id {
                type string;
              }
              leaf sg-channel {
                type string;
              }
            }
            list us-bonding-group {
              // NCS patched for predictable order
              ordered-by user;
              key "id";
              leaf id {
                type string;
              }
              container admission-control {
                leaf max-reserved-bandwidth {
                  type string;
                }
              }
              list upstream {
                // NCS patched for predictable order
                ordered-by user;
                key "id";
                leaf id {
                  type string;
                }
              }
            }
          }
          list wideband-interface {
            // NCS patched for predictable order
            ordered-by user;
            key "id";
            leaf id {
              type string;
            }
            leaf profile {
              type string;
            }
            container downstream {
              list sg-channel {
                // NCS patched for predictable order
                ordered-by user;
                key "id";
                leaf id {
                  type string;
                }
                leaf rf-bandwidth-percent {
                  type string;
                }
              }
            }
          }
        }
      }
      container downstream {
        list freq-profile {
          // NCS patched for predictable order
          ordered-by user;
          key "name";
          leaf name {
            type string;
          }
          list lane {
            // NCS patched for predictable order
            ordered-by user;
            key "id";
            leaf id {
              type string;
            }
            leaf start-freq {
              type string;
            }
            list block {
              // NCS patched for predictable order
              ordered-by user;
              key "id";
              leaf id {
                type string;
              }
              leaf start-freq {
                type string;
              }
            }
          }
        }
        list rf-profile {
          // NCS patched for predictable order
          ordered-by user;
          key "name";
          leaf name {
            type string;
          }
          container cable {
            container downstream {
              leaf annex {
                type string;
              }
              leaf modulation {
                type string;
              }
              container interleaver-depth {
                leaf option1 {
                  type string;
                }
                leaf option2 {
                  type string;
                }
              }
              leaf symbol-rate {
                type string;
              }
            }
          }
        }
        list qam-profile {
          // NCS patched for predictable order
          ordered-by user;
          key "name";
          leaf name {
            type string;
          }
          leaf annex {
            type string;
          }
          leaf modulation {
            type string;
          }
          leaf interleaver-depth {
            type string;
          }
          leaf symbol-rate {
            type string;
          }
          leaf spectrum-inversion {
            type string;
          }
          uses ncs_template_description-grouping;
        }
        list controller-profile {
          // NCS patched for predictable order
          ordered-by user;
          key "id";
          leaf id {
            type string;
          }
          leaf shutdown {
            type empty;
          }
          uses ncs_template_description-grouping;
          leaf max-carrier {
            type string;
          }
          leaf base-channel-power {
            type string;
          }
          container rf-chan {
            list rf-chan {
              // NCS patched for predictable order
              ordered-by user;
              key "start";
              leaf start {
                type string;
              }
              leaf end {
                type string;
              }
              uses ncs_template_controller-integrated-cable-rf-chan-grouping;
            }
          }
        }
      }
      container upstream {
        container rate-adapt {
          leaf priority {
            type string;
          }
          leaf rate {
            type string;
          }
          leaf local {
            type empty;
          }
        }
        list controller-profile {
          // NCS patched for predictable order
          ordered-by user;
          key "name";
          leaf name {
            type string;
          }
          uses ncs_template_description-grouping;
          uses ncs_template_us-channel-grouping;
        }
      }
      list linecard {
        // NCS patched for predictable order
        ordered-by user;
        key "id";
        leaf id {
          type string;
        }
        leaf encryption {
          type string;
        }
        leaf scrambler {
          type string;
        }
      }
      container admission-control {
        container preempt {
          leaf priority-voice {
            type empty;
          }
        }
      }
      container flap-list {
        leaf aging {
          type string;
        }
      }
      container source-verify {
        container leasequery-filter {
          container downstream {
            leaf threshold {
              type string;
            }
            leaf interval {
              type string;
            }
          }
        }
      }
      container modem {
        container remote-query {
          container gather {
            leaf polling-interval {
              type string;
            }
            leaf community-string {
              type string;
            }
          }
          leaf src-ip {
            type string;
          }
        }
        leaf max-cpe {
          type string;
        }
        leaf v6-max-cpe-prefix {
          type string;
        }
        list vendor {
          // NCS patched for predictable order
          ordered-by user;
          key "oui";
          leaf oui {
            type string;
          }
          leaf vendor-name {
            type string;
          }
        }
      }
      container modulation-profile {
        list modulation-profile-list {
          // NCS patched for predictable order
          ordered-by user;
          key "profile";
          leaf profile {
            type string;
          }
          container atdma {
            uses ncs_template_cable-modulation-profile-list-grouping;
          }
          container tdma {
            uses ncs_template_cable-modulation-profile-list-grouping;
          }
          container mixed {
            uses ncs_template_cable-modulation-profile-list-grouping;
          }
          uses ncs_template_cable-modulation-profile-list-grouping;
        }
      }
      list tag {
        // NCS patched for predictable order
        ordered-by user;
        key "id";
        leaf id {
          type string;
        }
        leaf name {
          type string;
        }
        leaf service-type-id {
          type string;
        }
        leaf docsis-version {
          type string;
        }
        leaf service-class {
          type string;
        }
      }
      container service {
        list class {
          // NCS patched for predictable order
          ordered-by user;
          key "class-index";
          leaf class-index {
            type string;
          }
          leaf name {
            type string;
          }
          choice direction-choice {
            leaf downstream {
              // NCS drop tailf-common:cli-diff-dependency statement
              type empty;
            }
            leaf upstream {
              // NCS drop tailf-common:cli-diff-dependency statement
              type empty;
            }
          }
          leaf peak-rate {
            // NCS drop tailf-common:cli-diff-dependency statement
            type string;
          }
          leaf max-concat-burst {
            // NCS drop tailf-common:cli-diff-dependency statement
            type string;
          }
          container tos-overwrite {
            // NCS drop tailf-common:cli-diff-dependency statement
            leaf and-mask {
              type string;
            }
            leaf or-mask {
              type string;
            }
          }
          leaf req-trans-policy {
            // NCS drop tailf-common:cli-diff-dependency statement
            type string;
          }
          leaf max-rate {
            // NCS drop tailf-common:cli-diff-dependency statement
            type string;
          }
          leaf max-burst {
            // NCS drop tailf-common:cli-diff-dependency statement
            type string;
          }
          leaf min-rate {
            // NCS drop tailf-common:cli-diff-dependency statement
            type string;
          }
          leaf min-packet-size {
            // NCS drop tailf-common:cli-diff-dependency statement
            type string;
          }
          leaf max-latency {
            // NCS drop tailf-common:cli-diff-dependency statement
            type string;
          }
          leaf req-attr-mask {
            // NCS drop tailf-common:cli-diff-dependency statement
            type string;
          }
          leaf admission-timeout {
            // NCS drop tailf-common:cli-diff-dependency statement
            type string;
          }
          leaf activity-timeout {
            // NCS drop tailf-common:cli-diff-dependency statement
            type string;
          }
          leaf priority {
            // NCS drop tailf-common:cli-diff-dependency statement
            type string;
          }
          leaf sched-type {
            // NCS drop tailf-common:cli-diff-dependency statement
            type string;
          }
        }
        list type {
          // NCS patched for predictable order
          ordered-by user;
          key "id";
          leaf id {
            type string;
          }
          leaf ds-frequency {
            type string;
          }
        }
        container attribute {
          container ds-bonded {
            container downstream-type {
              container bonding-enabled {
                presence "true";
                leaf enforce {
                  type empty;
                }
              }
            }
          }
          container withhold-tlvs {
            leaf peak-rate {
              type empty;
            }
          }
        }
        container flow {
          leaf activity-timeout {
            type string;
          }
        }
      }
      container qos {
        container permission {
          leaf create {
            type empty;
          }
          leaf update {
            type empty;
          }
          leaf modems {
            type empty;
          }
        }
      }
      container multicast {
        container mdf-disable {
          leaf WB-Incapable-CM {
            type empty;
          }
        }
      }
      container filter {
        list group {
          // NCS patched for predictable order
          ordered-by user;
          key "group-id";
          leaf group-id {
            type string;
          }
          list index {
            // NCS patched for predictable order
            ordered-by user;
            key "index-num";
            leaf index-num {
              type string;
            }
            leaf src-ip {
              type string;
            }
            leaf src-mask {
              type string;
            }
            leaf dest-ip {
              type string;
            }
            leaf dest-mask {
              type string;
            }
            leaf v6-src-address {
              type string;
            }
            leaf v6-src-pfxlen {
              type string;
            }
            leaf v6-dest-address {
              type string;
            }
            leaf v6-dest-pfxlen {
              type string;
            }
            leaf v6-flow-label {
              type string;
            }
            leaf ip-proto {
              type string;
            }
            container ip-tos {
              leaf tos-mask {
                type string;
              }
              leaf tos-value {
                type string;
              }
            }
            leaf src-port {
              type string;
            }
            leaf dest-port {
              type string;
            }
            leaf ip-version {
              type string;
              // NCS drop default statement
            }
            container tcp-flags {
              leaf flags-mask {
                type string;
              }
              leaf flags-value {
                type string;
              }
            }
            leaf match-action {
              type string;
            }
            leaf status {
              type string;
              // NCS drop default statement
            }
          }
        }
      }
      container submgmt {
        container default {
          container filter-group {
            container cm {
              uses ncs_template_cable-submgmt-default-filter-group-grouping;
            }
            container cpe {
              uses ncs_template_cable-submgmt-default-filter-group-grouping;
            }
            container mta {
              uses ncs_template_cable-submgmt-default-filter-group-grouping;
            }
            container stb {
              uses ncs_template_cable-submgmt-default-filter-group-grouping;
            }
            container ps {
              uses ncs_template_cable-submgmt-default-filter-group-grouping;
            }
          }
          leaf active {
            type empty;
          }
        }
      }
      container logging {
        container badipsource {
          presence "true";
          leaf buffer-size {
            type string;
          }
        }
        container layer2events {
          presence "true";
          leaf buffer-size {
            type string;
          }
        }
        container overlapip {
          presence "true";
          leaf buffer-size {
            type string;
          }
        }
        container ironbus {
          presence "true";
          leaf buffer-size {
            type string;
          }
        }
        container downstream-index {
          presence "true";
          leaf buffer-size {
            type string;
          }
        }
      }
      container default-tos-qos10 {
        container tos-overwrite {
          leaf tos-and {
            type string;
          }
          leaf tos-or {
            type string;
          }
        }
      }
      container primary-sflow-qos11 {
        leaf keep {
          type string;
        }
      }
      container sflog {
        leaf max-entry {
          type string;
        }
        leaf entry-duration {
          type string;
        }
      }
      list trust {
        // NCS patched for predictable order
        ordered-by user;
        key "address";
        leaf address {
          type string;
        }
      }
      container dynamic-secret {
        container exclude {
          leaf modem {
            type string;
          }
          leaf oui {
            type string;
          }
        }
        container tftp {
          leaf insert-upgrade-server {
            type empty;
          }
        }
      }
      container docsis30-voice {
        container downstream {
          leaf req-attr-mask {
            type string;
          }
          leaf forb-attr-mask {
            type string;
          }
        }
      }
      leaf util-interval {
        type string;
      }
      container clock {
        leaf dti {
          type empty;
        }
        leaf dti-server-type {
          type string;
        }
      }
      container bgsync {
        leaf active {
          type string;
          // NCS drop default statement
        }
        leaf ptime {
          type string;
          // NCS drop default statement
        }
        leaf itime {
          type string;
          // NCS drop default statement
        }
      }
      container privacy {
        leaf encrypt-alg-priority {
          type string;
        }
      }
      container dsg {
        list client-list {
          // NCS patched for predictable order
          ordered-by user;
          key "client-list-id";
          leaf client-list-id {
            type string;
          }
          list id-index {
            // NCS patched for predictable order
            ordered-by user;
            key "id";
            leaf id {
              type string;
            }
            choice parameter-choice {
              leaf application-id {
                type string;
              }
              leaf broadcast {
                type string;
              }
              leaf ca-system-id {
                type string;
              }
              leaf mac-addr {
                type string;
              }
            }
          }
        }
        list tg {
          // NCS patched for predictable order
          ordered-by user;
          key "group-id";
          leaf group-id {
            type string;
          }
          list channel {
            // NCS patched for predictable order
            ordered-by user;
            key "channel-id";
            leaf channel-id {
              type string;
            }
            leaf priority {
              type string;
            }
            leaf status {
              type string;
              // NCS drop default statement
            }
          }
        }
        list tunnel {
          // NCS patched for predictable order
          ordered-by user;
          key "tunnel-id";
          leaf tunnel-id {
            type string;
          }
          leaf mac-addr {
            type string;
          }
          leaf tg {
            type string;
          }
          leaf clients {
            type string;
          }
          leaf status {
            type string;
            // NCS drop default statement
          }
        }
        list cfr {
          // NCS patched for predictable order
          ordered-by user;
          key "index";
          leaf index {
            type string;
          }
          leaf dest-ip {
            type string;
          }
          leaf tunnel {
            type string;
          }
          leaf priority {
            type string;
          }
          leaf src-ip {
            type string;
          }
          leaf in-dcd {
            type string;
          }
        }
        list timer {
          // NCS patched for predictable order
          ordered-by user;
          key "index";
          leaf index {
            type string;
          }
          leaf Tdsg1 {
            type string;
          }
          leaf Tdsg2 {
            type string;
          }
          leaf Tdsg3 {
            type string;
          }
          leaf Tdsg4 {
            type string;
          }
        }
        list chan-list {
          // NCS patched for predictable order
          ordered-by user;
          key "id index";
          leaf id {
            type string;
          }
          leaf index {
            type string;
          }
          leaf freq {
            type string;
          }
        }
      }
      container load-balance {
        leaf docsis-enable {
          type empty;
        }
        container docsis30-enable {
          presence "true";
          leaf downstream-only {
            type empty;
          }
        }
        container modem {
          leaf max-failures {
            type string;
          }
        }
        list rule {
          // NCS patched for predictable order
          ordered-by user;
          key "rule-id";
          leaf rule-id {
            type string;
          }
          choice status-choice {
            container ds {
              container disable-throughput-lowerbound {
                leaf ds {
                  type string;
                }
              }
            }
            container us {
              container disable-throughput-lowerbound {
                leaf us {
                  type string;
                }
              }
            }
            leaf disabled {
              type empty;
            }
            leaf enabled {
              type empty;
            }
          }
        }
        list docsis-policy {
          // NCS patched for predictable order
          ordered-by user;
          key "policy-id";
          leaf policy-id {
            type string;
          }
          list rule {
            // NCS patched for predictable order
            ordered-by user;
            key "rule-id";
            leaf rule-id {
              type string;
            }
          }
          leaf tag {
            type string;
          }
          leaf override {
            type empty;
          }
        }
        container d20-ggrp-default {
          leaf init-tech-list {
            type string;
          }
          container method {
            container utilization {
              presence "true";
            }
          }
          container policy {
            leaf pure-ds-load {
              type empty;
            }
          }
          container threshold {
            container load {
              leaf value {
                type string;
              }
            }
          }
        }
        container d30-ggrp-default {
          leaf disable {
            type empty;
          }
          leaf init-tech-list {
            type string;
          }
          leaf docsis-policy {
            type string;
          }
          leaf policy {
            type string;
          }
          container threshold {
            container load {
              leaf load-value {
                type string;
              }
              leaf minimum {
                type string;
              }
            }
          }
        }
        container docsis-group {
          list FN {
            // NCS patched for predictable order
            ordered-by user;
            key "fn-id";
            leaf fn-id {
              type string;
            }
            container MD {
              leaf Cable {
                type string;
              }
            }
            uses ncs_template_cable-load-balance-docsis-group-grouping;
          }
          list docsis-group-list {
            // NCS patched for predictable order
            ordered-by user;
            key "docsis-group-id";
            leaf docsis-group-id {
              type string;
            }
            uses ncs_template_cable-load-balance-docsis-group-grouping;
          }
        }
        list group {
          // NCS patched for predictable order
          ordered-by user;
          key "id";
          leaf id {
            type string;
          }
        }
        container exclude {
          list oui {
            // NCS patched for predictable order
            ordered-by user;
            key "word";
            leaf word {
              type string;
            }
            leaf assignment {
              type empty;
            }
            leaf enforce {
              type empty;
            }
            leaf static {
              type empty;
            }
            leaf strict {
              type empty;
            }
          }
        }
      }
      container metering {
        choice cable-metering-choice {
          container destination {
            leaf ip-address {
              type string;
            }
            leaf port {
              type string;
            }
            leaf ip-address2 {
              type string;
            }
            leaf port2 {
              // NCS drop when statement
              type string;
            }
            leaf retries {
              type string;
            }
            leaf minutes {
              type string;
            }
            leaf security {
              type string;
            }
            leaf flow-aggregate {
              type empty;
            }
            leaf cpe-list-suppress {
              type empty;
            }
            leaf full-records {
              type empty;
            }
          }
          container ipdr-d3 {
            container session {
              leaf session-id {
                type string;
              }
              leaf type {
                type string;
              }
              leaf flow-aggregate {
                type empty;
              }
              leaf full-records {
                type empty;
              }
            }
          }
        }
        container ipdr {
          leaf interval {
            type string;
          }
          leaf session {
            type string;
          }
          leaf flow-aggregate {
            type empty;
          }
          leaf full-records {
            type empty;
          }
        }
        container source-interface {
          uses ncs_template_interface-name-grouping;
        }
        container data-per-session {
          leaf data-per-session {
            type string;
          }
          leaf timer {
            type string;
          }
        }
      }
      container rf-change-trigger {
        leaf percent {
          type string;
        }
        leaf count {
          type string;
        }
        leaf secondary {
          type empty;
        }
      }
      leaf rf-change-dampen-time {
        type string;
      }
      container resiliency {
        leaf ds-bonding {
          type empty;
        }
      }
      container throttle-modem {
        leaf init-rate {
          type string;
        }
        leaf holdoff-time {
          type string;
        }
        leaf flush-rate {
          type string;
        }
      }
      container ds-max-burst {
        presence "true";
        choice optional {
          leaf burst-threshold {
            type string;
            // NCS drop default statement
          }
          leaf peak-rate {
            type string;
          }
        }
      }
      container acfe {
        leaf enable {
          type empty;
        }
        leaf period {
          type string;
        }
      }
      container l2-vpn-service {
        container xconnect {
          container nsi {
            container dot1q {
              presence "true";
              container interface {
                uses ncs_template_interface-name-grouping;
              }
            }
            container mpls {
              presence "true";
            }
          }
        }
      }
      list dot1q-vc-map {
        // NCS patched for predictable order
        ordered-by user;
        key "mac-address";
        leaf mac-address {
          type string;
        }
        container ethernet-interface {
          uses ncs_template_interface-name-grouping;
        }
        leaf vlan-id {
          type string;
        }
        leaf cust-name {
          type string;
        }
      }
      list l2vpn {
        // NCS patched for predictable order
        ordered-by user;
        key "mac-address";
        leaf mac-address {
          type string;
        }
        leaf customer-name {
          type string;
        }
        container service {
          list instance {
            // NCS patched for predictable order
            ordered-by user;
            // NCS drop max-elements statement
            key "id";
            leaf id {
              type string;
            }
            leaf ethernet {
              type empty;
            }
            container xconnect {
              leaf address {
                type string;
              }
              leaf vcid {
                type string;
              }
              leaf encapsulation {
                type string;
              }
              leaf pw-type {
                type string;
              }
              container backup {
                list peer {
                  // NCS patched for predictable order
                  ordered-by user;
                  // NCS drop max-elements statement
                  key "peer-router-ip-addr vcid";
                  leaf peer-router-ip-addr {
                    type string;
                  }
                  leaf vcid {
                    type string;
                  }
                  leaf priority {
                    type string;
                  }
                }
                container delay {
                  leaf enable-delay {
                    type string;
                    // NCS drop default statement
                  }
                  leaf disable-delay {
                    type string;
                    // NCS drop default statement
                  }
                }
              }
            }
            container cable {
              container set {
                leaf mpls-experimental {
                  type string;
                }
              }
            }
          }
        }
      }
      container wideband {
        leaf auto-reset {
          type empty;
        }
      }
      list rcc-template {
        // NCS patched for predictable order
        ordered-by user;
        key "index";
        leaf index {
          type string;
        }
        leaf rcp-id {
          type string;
        }
        list receive-module {
          // NCS patched for predictable order
          ordered-by user;
          key "index";
          leaf index {
            type string;
          }
          leaf first-center-frequency {
            type string;
          }
          leaf connected-receive-module {
            type string;
          }
        }
        list receive-channel {
          // NCS patched for predictable order
          ordered-by user;
          key "index";
          leaf index {
            type string;
          }
          leaf center-frequency {
            type string;
          }
          leaf connected-receive-module {
            type string;
          }
          leaf primary {
            type empty;
          }
        }
      }
      container video {
        presence "true";
      }
      list fiber-node {
        // NCS patched for predictable order
        ordered-by user;
        key "fiber-node-id";
        leaf fiber-node-id {
          type string;
        }
        leaf description {
          type string;
        }
        container downstream {
          list Downstream-Cable {
            // NCS patched for predictable order
            ordered-by user;
            key "name";
            leaf name {
              type string;
            }
            leaf rf-channel {
              type string;
            }
          }
          list Modular-Cable {
            // NCS patched for predictable order
            ordered-by user;
            key "name";
            leaf name {
              type string;
            }
            leaf rf-channel {
              type string;
            }
          }
          list Integrated-Cable {
            // NCS patched for predictable order
            ordered-by user;
            key "name";
            leaf name {
              type string;
            }
            leaf rf-channel {
              type string;
            }
          }
          list sg-channel {
            // NCS patched for predictable order
            ordered-by user;
            key "low";
            leaf low {
              type string;
            }
            leaf high {
              type string;
            }
            choice cable-choice {
              leaf downstream-Cable {
                type string;
              }
              leaf integrated-Cable {
                type string;
              }
            }
            leaf rf-channel {
              type string;
            }
            leaf rf-channel-high {
              type string;
            }
          }
        }
        container upstream {
          list Upstream-Cable {
            // NCS patched for predictable order
            ordered-by user;
            key "name";
            leaf name {
              type string;
            }
            leaf connector {
              type string;
            }
          }
          list Cable {
            // NCS patched for predictable order
            ordered-by user;
            key "name";
            leaf name {
              type string;
            }
            leaf connector {
              type string;
            }
          }
          list sg-channel {
            // NCS patched for predictable order
            ordered-by user;
            key "low";
            leaf low {
              type string;
            }
            leaf high {
              type string;
            }
            leaf Upstream-Cable {
              type string;
            }
            leaf us-channel {
              type string;
            }
            leaf us-channel-high {
              type string;
            }
          }
        }
        container service-group {
          leaf profile {
            type string;
          }
        }
      }
      list rpd {
        // NCS patched for predictable order
        ordered-by user;
        key "name";
        leaf name {
          type string;
        }
        uses ncs_template_description-grouping;
        leaf identifier {
          type string;
        }
        container core-interface {
          list Te {
            // NCS patched for predictable order
            ordered-by user;
            key "name";
            leaf name {
              type string;
            }
            leaf principal {
              type empty;
            }
            list rpd-ds {
              // NCS patched for predictable order
              ordered-by user;
              key "port downstream-cable";
              leaf port {
                type string;
              }
              leaf downstream-cable {
                type string;
              }
              leaf profile {
                type string;
              }
            }
            list rpd-us {
              // NCS patched for predictable order
              ordered-by user;
              key "port upstream-cable";
              leaf port {
                type string;
              }
              leaf upstream-cable {
                type string;
              }
              leaf profile {
                type string;
              }
            }
          }
        }
        leaf r-dti {
          type string;
        }
        container rpd-event {
          leaf profile {
            type string;
          }
        }
        container ptp {
          leaf profile {
            type string;
          }
        }
      }
      container ipv6 {
        container pd-route {
          leaf prefix {
            type string;
          }
          leaf Bundle {
            type string;
          }
        }
        container source-verify {
          container leasequery-filter {
            container downstream {
              leaf threshold {
                type string;
              }
              leaf interval {
                type string;
              }
            }
          }
        }
      }
    }
    list l2tp-class {
      // NCS patched for predictable order
      ordered-by user;
      key "l2tp-class-name";
      leaf l2tp-class-name {
        type string;
      }
      leaf authentication {
        type empty;
      }
      leaf hello {
        type string;
        // NCS drop default statement
      }
      container password {
        uses ncs_template_password-grouping;
      }
      container retransmit {
        leaf retries {
          type string;
        }
        container timeout {
          choice timeout-choice {
            leaf max {
              type string;
            }
            leaf min {
              type string;
            }
          }
        }
        container initial {
          leaf retries {
            type string;
          }
        }
      }
    }
    container packetcable {
      presence "true";
      leaf multimedia {
        type empty;
      }
      container authorize {
        leaf vanilla-docsis-mta {
          type empty;
        }
      }
    }
    list depi-class {
      // NCS patched for predictable order
      ordered-by user;
      key "depi-class-name";
      leaf depi-class-name {
        type string;
      }
      container mode {
        leaf mpt {
          type empty;
        }
      }
      leaf l2tp-class {
        type string;
      }
    }
    list depi-tunnel {
      // NCS patched for predictable order
      ordered-by user;
      key "depi-tunnel-name";
      leaf depi-tunnel-name {
        type string;
      }
      leaf dest-ip {
        type string;
      }
      leaf l2tp-class {
        type string;
      }
      leaf depi-class {
        type string;
      }
      leaf protect-tunnel {
        type string;
      }
    }
    list chat-script {
      // NCS patched for predictable order
      ordered-by user;
      key "name";
      leaf name {
        type string;
      }
      leaf line {
        type string;
      }
    }
    container autonomic {
      container registrar {
        leaf domain-id {
          type string;
        }
        container CA {
          choice CA-choice {
            leaf local {
              type empty;
            }
            leaf url {
              type string;
            }
          }
        }
        leaf whitelist {
          type string;
        }
        leaf shut {
          type string;
          // NCS drop default statement
        }
      }
    }
    container autonomic-enable {
      leaf autonomic {
        type empty;
      }
    }
    container controller {
      list controller-tx-ex-list {
        // NCS patched for predictable order
        ordered-by user;
        key "name number";
        leaf name {
          type string;
        }
        leaf number {
          type string;
        }
        leaf framing {
          type string;
        }
        leaf fdl {
          type string;
        }
        list cem-group {
          // NCS patched for predictable order
          ordered-by user;
          key "id";
          leaf id {
            type string;
          }
          leaf unframed {
            type empty;
          }
          leaf-list timeslots {
            // NCS patched for predictable order
            ordered-by user;
            type string;
          }
        }
        container clock {
          container source {
            choice source-choice {
              container line {
                presence "true";
                leaf line-mode {
                  type string;
                }
              }
              leaf internal {
                type empty;
              }
              leaf loop-timed {
                type empty;
              }
              leaf free-running {
                type empty;
              }
            }
          }
        }
        leaf linecode {
          type string;
        }
        container cablelength {
          choice cablelength-choice {
            leaf value {
              type string;
            }
            leaf long {
              type string;
            }
            leaf short {
              type string;
            }
          }
        }
        container pri-group {
          list timeslots {
            // NCS patched for predictable order
            ordered-by user;
            key "id";
            leaf id {
              type string;
            }
            leaf nfas_d {
              type string;
            }
            leaf nfas_int {
              // NCS drop when statement
              type string;
            }
            leaf nfas_group {
              // NCS drop when statement
              type string;
            }
            leaf service {
              type string;
            }
          }
        }
        list channel-group {
          // NCS patched for predictable order
          ordered-by user;
          key "number";
          leaf number {
            type string;
          }
          leaf-list timeslots {
            // NCS patched for predictable order
            ordered-by user;
            type string;
          }
        }
        leaf description {
          type string;
        }
        list t1 {
          // NCS patched for predictable order
          ordered-by user;
          key "id";
          leaf id {
            type string;
          }
          leaf channel-group {
            type string;
          }
          leaf-list timeslots {
            // NCS patched for predictable order
            ordered-by user;
            type string;
          }
          leaf speed {
            type string;
          }
          container clock {
            leaf source {
              type string;
            }
          }
        }
        container ima-group {
          leaf group-number {
            type string;
          }
          leaf scrambling-payload {
            type empty;
          }
        }
        leaf shutdown {
          type empty;
        }
      }
      container BITS {
        container input {
          container applique {
            container E1 {
              choice E1-choice {
                case clock-case {
                  leaf clock-if {
                    type string;
                  }
                }
                case framing-case {
                  leaf framing {
                    type string;
                  }
                  leaf linecode {
                    type string;
                  }
                }
              }
            }
          }
        }
      }
      list Cellular {
        // NCS patched for predictable order
        ordered-by user;
        key "id";
        leaf id {
          type string;
        }
        leaf description {
          type string;
        }
        container lte {
          container gps {
            leaf enable {
              type empty;
            }
            container mode {
              leaf standalone {
                type empty;
              }
            }
            container nmea {
              choice nmea-choice {
                container ip {
                  presence "true";
                }
                container serial {
                  presence "true";
                  leaf streaming {
                    type string;
                  }
                }
              }
            }
          }
          container modem {
            container link-recovery {
              leaf enable {
                type empty;
              }
              container rssi {
                leaf onset-threshold {
                  type string;
                }
              }
              leaf monitor-timer {
                type string;
              }
              leaf wait-timer {
                type string;
              }
              leaf debounce-count {
                type string;
              }
            }
          }
        }
      }
      list VDSL {
        // NCS patched for predictable order
        ordered-by user;
        key "id";
        leaf id {
          type string;
        }
        leaf description {
          type string;
        }
      }
      list Upstream-Cable {
        // NCS patched for predictable order
        ordered-by user;
        key "name";
        leaf name {
          type string;
        }
        uses ncs_template_description-grouping;
        uses ncs_template_us-channel-grouping;
      }
      list Downstream-Cable {
        // NCS patched for predictable order
        ordered-by user;
        key "name";
        leaf name {
          type string;
        }
        uses ncs_template_description-grouping;
      }
      list Modular-Cable {
        // NCS patched for predictable order
        ordered-by user;
        key "name";
        leaf name {
          type string;
        }
        uses ncs_template_description-grouping;
        leaf ip-address {
          type string;
        }
        container modular-host {
          leaf subslot {
            type string;
          }
        }
        uses ncs_template_controller-modular-cable-rf-channel-grouping;
      }
      list Integrated-Cable {
        // NCS patched for predictable order
        ordered-by user;
        key "name";
        leaf name {
          type string;
        }
        uses ncs_template_description-grouping;
        leaf max-carrier {
          type string;
        }
        leaf base-channel-power {
          type string;
        }
        leaf freq-profile {
          type string;
        }
        container rf-chan {
          list rf-chan {
            // NCS patched for predictable order
            ordered-by user;
            key "start";
            leaf start {
              type string;
            }
            uses ncs_template_controller-integrated-cable-rf-chan-grouping;
          }
          list rf-chan-range {
            // NCS patched for predictable order
            ordered-by user;
            key "start end";
            leaf start {
              type string;
            }
            leaf end {
              type string;
            }
            uses ncs_template_controller-integrated-cable-rf-chan-grouping;
          }
        }
      }
      list wanphy {
        // NCS patched for predictable order
        ordered-by user;
        key "name";
        leaf name {
          type string;
        }
      }
      list dwdm {
        // NCS patched for predictable order
        ordered-by user;
        key "name";
        leaf name {
          type string;
        }
        leaf shutdown {
          type empty;
        }
      }
      list SONET {
        // NCS patched for predictable order
        ordered-by user;
        key "name";
        leaf name {
          type string;
        }
        leaf description {
          type string;
        }
        leaf shutdown {
          type empty;
        }
        leaf rate {
          type string;
        }
        leaf ais-shut {
          type string;
        }
        leaf TU-AIS {
          type string;
          // NCS drop default statement
        }
        leaf alarm-report {
          type string;
        }
        container threshold {
          leaf sf-ber {
            type string;
          }
        }
        leaf framing {
          type string;
        }
        container clock {
          leaf source {
            type string;
          }
        }
        container aug {
          leaf mapping {
            type string;
          }
        }
        container overhead {
          leaf j0 {
            type string;
          }
        }
        list au-3 {
          // NCS patched for predictable order
          ordered-by user;
          key "id";
          leaf id {
            type string;
          }
          container overhead {
            container j1 {
              leaf length {
                type string;
              }
            }
          }
          leaf mode {
            type string;
          }
          list tug-2 {
            // NCS patched for predictable order
            ordered-by user;
            key "tug-2 t1";
            leaf tug-2 {
              type string;
            }
            leaf t1 {
              type string;
            }
            container clock {
              leaf source {
                type string;
              }
            }
          }
        }
        list au-4 {
          // NCS patched for predictable order
          ordered-by user;
          key "id";
          leaf id {
            type string;
          }
          container threshold {
            leaf b3-tca {
              type string;
            }
          }
          list tug-3 {
            // NCS patched for predictable order
            ordered-by user;
            key "id";
            leaf id {
              type string;
            }
            leaf mode {
              type string;
            }
            list tug-2 {
              // NCS patched for predictable order
              ordered-by user;
              key "tug-2 e1";
              leaf tug-2 {
                type string;
              }
              leaf e1 {
                type string;
              }
              container ima-group {
                leaf group-number {
                  type string;
                }
              }
              list channel-group {
                // NCS patched for predictable order
                ordered-by user;
                key "id";
                leaf id {
                  type string;
                }
                leaf-list timeslots {
                  // NCS patched for predictable order
                  ordered-by user;
                  type string;
                }
              }
              list cem-group {
                // NCS patched for predictable order
                ordered-by user;
                key "id";
                leaf id {
                  type string;
                }
                leaf unframed {
                  type empty;
                }
                leaf-list timeslots {
                  // NCS patched for predictable order
                  ordered-by user;
                  type string;
                }
              }
              leaf framing {
                type string;
              }
              leaf unframed {
                type empty;
              }
              container clock {
                leaf source {
                  type string;
                }
              }
            }
          }
        }
        container sts-3c {
          list sts-1 {
            // NCS patched for predictable order
            ordered-by user;
            key "id";
            leaf id {
              type string;
            }
            leaf mode {
              type string;
            }
            container cem-group {
              leaf id {
                type string;
              }
              leaf cep {
                type empty;
              }
            }
            container clock {
              leaf source {
                type string;
              }
            }
          }
        }
        list sts-1 {
          // NCS patched for predictable order
          ordered-by user;
          key "id";
          leaf id {
            type string;
          }
          container clock {
            leaf source {
              type string;
            }
          }
          container cem-group {
            // NCS drop when statement
            leaf id {
              // NCS drop tailf-common:cli-diff-dependency statement
              type string;
            }
            leaf unframed {
              type empty;
            }
          }
          container t3 {
            // NCS drop when statement
            // NCS drop tailf-common:cli-diff-dependency statement
            container clock {
              leaf source {
                type string;
              }
            }
          }
          container vtg {
            // NCS drop when statement
            // NCS drop tailf-common:cli-diff-dependency statement
          }
          container mode {
            choice mode-choice {
              leaf ct3 {
                type empty;
              }
              leaf ct3-e1 {
                type empty;
              }
              leaf t3 {
                type empty;
              }
              leaf unframed {
                type empty;
              }
              leaf vt-15 {
                type empty;
              }
              leaf vt-2 {
                type empty;
              }
            }
          }
        }
      }
      list ISA {
        // NCS patched for predictable order
        ordered-by user;
        key "name";
        leaf name {
          type string;
        }
      }
      list nid {
        // NCS patched for predictable order
        ordered-by user;
        key "name";
        leaf name {
          type string;
        }
      }
      list MediaType {
        // NCS patched for predictable order
        ordered-by user;
        key "name";
        leaf name {
          type string;
        }
        uses ncs_template_description-grouping;
        leaf mode {
          type string;
        }
      }
    }
    container vc-class {
      list atm {
        // NCS patched for predictable order
        ordered-by user;
        key "name";
        leaf name {
          type string;
        }
        container vbr-nrt {
          leaf pcr {
            type string;
          }
          leaf scr {
            type string;
          }
          leaf mbs {
            type string;
          }
        }
      }
    }
    container fhrp {
      container version {
        leaf vrrp {
          type string;
          // NCS drop default statement
        }
      }
    }
    container ip {
      leaf subnet-zero {
        type string;
        // NCS drop default statement
      }
      leaf source-route {
        type string;
        // NCS drop default statement
      }
      leaf routing {
        // NCS drop tailf-common:cli-diff-dependency statement
        type string;
        // NCS drop default statement
      }
      container routing-conf {
        container routing {
          container protocol {
            container purge {
              leaf interface {
                type string;
                // NCS drop default statement
              }
            }
          }
        }
      }
      container options {
        leaf drop {
          type empty;
        }
      }
      container auth-proxy {
        leaf max-login-attempts {
          type string;
        }
        leaf max-nodata-conns {
          type string;
          // NCS drop default statement
        }
      }
      container admission {
        leaf max-login-attempts {
          type string;
        }
        leaf max-nodata-conns {
          type string;
        }
      }
      container arp {
        container proxy {
          leaf disable {
            type empty;
          }
        }
        container inspection {
          leaf-list bridge-domain {
            // NCS patched for predictable order
            ordered-by user;
            type string;
          }
          container bridge-domain-list {
            list bridge-domain {
              // NCS patched for predictable order
              ordered-by user;
              key "id";
              leaf id {
                type string;
              }
              container logging {
                choice logging-choice {
                  leaf acl-match {
                    type string;
                  }
                  leaf dhcp-bindings {
                    type string;
                  }
                }
              }
            }
          }
          leaf-list validate {
            // NCS patched for predictable order
            ordered-by user;
            type string;
          }
          container log-buffer {
            leaf entries {
              type string;
            }
            container logs {
              leaf number {
                type string;
              }
              leaf interval {
                type string;
              }
            }
          }
          leaf-list vlan {
            // NCS patched for predictable order
            ordered-by user;
            type string;
          }
          list filter {
            // NCS patched for predictable order
            ordered-by user;
            key "name";
            leaf name {
              type string;
            }
            leaf-list vlan {
              // NCS patched for predictable order
              ordered-by user;
              type string;
            }
          }
        }
      }
      choice gratuitous-arps-choice {
        container gratuitous-arps-conf {
          leaf gratuitous-arps {
            type string;
          }
        }
        container gratuitous-arps {
          leaf non-local {
            type string;
            // NCS drop default statement
          }
        }
        // NCS drop default statement
      }
      container cef-conf {
        leaf cef {
          type empty;
        }
      }
      container cef {
        // NCS drop tailf-common:cli-diff-dependency statement
        leaf distributed {
          type empty;
        }
        container optimize {
          container neighbor {
            leaf resolution {
              type string;
              // NCS drop default statement
            }
          }
        }
        container load-sharing {
          container algorithm {
            choice algorithm-choice {
              // NCS drop default statement
              leaf original {
                type empty;
              }
              container universal {
                presence "true";
                leaf id {
                  type string;
                }
              }
            }
          }
        }
      }
      list vrf {
        // NCS patched for predictable order
        ordered-by user;
        key "name";
        leaf name {
          // NCS drop tailf-common:cli-diff-dependency statement
          type string;
        }
        leaf description {
          type string;
        }
        leaf rd {
          type string;
        }
        container vpn {
          leaf id {
            type string;
          }
        }
        leaf context {
          type string;
        }
        container import {
          leaf map {
            // NCS drop tailf-common:cli-diff-dependency statement
            type string;
          }
          container ipv4 {
            // NCS drop tailf-common:cli-diff-dependency statement
            leaf ipv4-type {
              type string;
            }
            leaf upper-limit {
              type string;
            }
            leaf map {
              type string;
            }
          }
        }
        container export {
          leaf map {
            type string;
          }
        }
        container maximum {
          presence "true";
          leaf routes {
            type string;
          }
          choice maximum-choice {
            case threshold-case {
              leaf threshold {
                type string;
              }
              leaf reinstall {
                type string;
              }
            }
            case warning-case {
              leaf warning-only {
                type empty;
              }
            }
          }
        }
        container bgp {
          container next-hop {
            leaf Loopback {
              type string;
            }
          }
        }
        container mdt {
          presence "Backbone Multicast Distribution Tree";
          leaf default {
            type string;
          }
          container data {
            leaf mulicast-address {
              type string;
            }
            leaf wildcard-bits {
              type string;
            }
            choice mdt-data-choice {
              case mdt-data-threshold {
                leaf threshold {
                  type string;
                }
                leaf threshold-list {
                  tailf:alt-name "list";
                  type string;
                }
              }
              case mdt-data-list {
                leaf list {
                  type string;
                }
              }
            }
          }
          leaf log-reuse {
            type empty;
          }
        }
        container route-target {
          // NCS drop tailf-common:cli-diff-dependency statement
          uses ncs_template_route-target-grouping;
        }
      }
      container dhcp-server {
        list dhcp-server-list {
          // NCS patched for predictable order
          ordered-by user;
          key "server";
          leaf server {
            type string;
          }
        }
      }
      container dhcp {
        leaf smart-relay {
          type empty;
        }
        container use {
          container vrf {
            leaf connected {
              type string;
              // NCS drop default statement
            }
            leaf remote {
              type empty;
            }
          }
        }
        container conflict {
          leaf logging {
            type string;
            // NCS drop default statement
          }
        }
        container excluded-address {
          uses ncs_template_ip-dhcp-excluded-address-grouping;
          list vrf {
            // NCS patched for predictable order
            ordered-by user;
            key "name";
            leaf name {
              // NCS drop tailf-common:cli-diff-dependency statement
              // NCS drop tailf-common:cli-diff-dependency statement
              type string;
            }
            uses ncs_template_ip-dhcp-excluded-address-grouping;
          }
        }
        list pool {
          // NCS patched for predictable order
          ordered-by user;
          key "id";
          leaf id {
            type string;
          }
          leaf vrf {
            // NCS drop tailf-common:cli-diff-dependency statement
            // NCS drop tailf-common:cli-diff-dependency statement
            type string;
          }
          container import {
            leaf all {
              type empty;
            }
          }
          leaf bootfile {
            type string;
          }
          container host {
            leaf address {
              type string;
            }
            leaf mask {
              type string;
            }
          }
          choice hardware-or-client {
            leaf hardware-address {
              type string;
            }
            leaf client-identifier {
              type string;
            }
          }
          container network {
            leaf network-number {
              type string;
            }
            leaf mask {
              type string;
            }
          }
          leaf-list next-server {
            // NCS patched for predictable order
            ordered-by user;
            // NCS drop max-elements statement
            type string;
          }
          leaf-list netbios-name-server {
            // NCS patched for predictable order
            ordered-by user;
            // NCS drop max-elements statement
            type string;
          }
          leaf-list dns-server {
            // NCS patched for predictable order
            ordered-by user;
            // NCS drop max-elements statement
            type string;
          }
          leaf-list default-router {
            // NCS patched for predictable order
            ordered-by user;
            // NCS drop max-elements statement
            type string;
          }
          leaf domain-name {
            type string;
          }
          list option {
            // NCS patched for predictable order
            ordered-by user;
            key "code";
            leaf code {
              type string;
            }
            choice option-config {
              leaf ascii {
                type string;
              }
              leaf hex {
                type string;
              }
              leaf-list ip {
                // NCS patched for predictable order
                ordered-by user;
                type string;
              }
            }
            list instance {
              // NCS patched for predictable order
              ordered-by user;
              key "option-instance";
              leaf option-instance {
                type string;
              }
              choice option-config {
                leaf ascii {
                  type string;
                }
                leaf hex {
                  type string;
                }
                leaf-list ip {
                  // NCS patched for predictable order
                  ordered-by user;
                  type string;
                }
              }
            }
          }
          container lease {
            choice lease-choice {
              case a {
                leaf infinite {
                  type empty;
                }
              }
              case b {
                leaf days {
                  type string;
                }
                leaf hours {
                  type string;
                }
                leaf minutes {
                  type string;
                }
              }
            }
          }
          container update {
            leaf arp {
              type empty;
            }
          }
          list class {
            // NCS patched for predictable order
            ordered-by user;
            key "name";
            leaf name {
              type string;
            }
            container address {
              container range {
                leaf start-ip {
                  type string;
                }
                leaf end-ip {
                  type string;
                }
              }
            }
          }
          leaf netbios-node-type {
            type string;
          }
        }
        list class {
          // NCS patched for predictable order
          ordered-by user;
          key "id";
          leaf id {
            type string;
          }
          leaf remark {
            type string;
          }
          container relay {
            container agent {
              container information {
                presence "true";
              }
            }
          }
        }
        container snooping {
          leaf-list bridge-domain {
            // NCS patched for predictable order
            ordered-by user;
            // NCS drop tailf-common:cli-diff-dependency statement
            type string;
          }
          container information {
            container option {
              presence "true";
              leaf allow-untrusted {
                type empty;
              }
              container format {
                container remote-id {
                  choice remote-id-choice {
                    leaf hostname {
                      type empty;
                    }
                    leaf string {
                      type string;
                    }
                  }
                }
              }
            }
          }
          container database {
            leaf url {
              type string;
            }
          }
          container track {
            leaf host {
              type empty;
            }
          }
          container verify {
            leaf mac-address {
              type empty;
            }
            leaf no-relay-agent-address {
              type empty;
            }
          }
          leaf-list vlan {
            // NCS patched for predictable order
            ordered-by user;
            type string;
          }
        }
        container snooping-conf {
          leaf snooping {
            type empty;
          }
        }
        container relay {
          container information {
            container option {
              presence "true";
            }
            leaf check {
              type string;
              // NCS drop default statement
            }
            leaf trust-all {
              type empty;
            }
          }
          container prefer {
            leaf known-good-server {
              type empty;
            }
          }
        }
        container bootp {
          leaf ignore {
            type empty;
          }
        }
      }
      container bootp {
        leaf server {
          type string;
          // NCS drop default statement
        }
      }
      container domain {
        leaf round-robin {
          type empty;
        }
        container list-vrf {
          container list {
            list vrf {
              // NCS patched for predictable order
              ordered-by user;
              key "name";
              leaf name {
                // NCS drop tailf-common:cli-diff-dependency statement
                // NCS drop tailf-common:cli-diff-dependency statement
                type string;
              }
              leaf domain-name {
                type string;
              }
            }
          }
        }
        list list {
          // NCS patched for predictable order
          ordered-by user;
          key "name";
          leaf name {
            type string;
          }
        }
        leaf retry {
          type string;
        }
        leaf timeout {
          type string;
        }
        container lookup-conf {
          leaf lookup {
            type string;
            // NCS drop default statement
          }
        }
        container lookup {
          leaf nsap {
            type string;
            // NCS drop default statement
          }
          leaf recursive {
            type empty;
          }
          container source-interface {
            uses ncs_template_interface-name-grouping;
          }
          leaf vrf {
            // NCS drop tailf-common:cli-diff-dependency statement
            // NCS drop tailf-common:cli-diff-dependency statement
            type string;
          }
        }
        container name-vrf {
          container name {
            list vrf {
              // NCS patched for predictable order
              ordered-by user;
              key "name";
              leaf name {
                // NCS drop tailf-common:cli-diff-dependency statement
                // NCS drop tailf-common:cli-diff-dependency statement
                type string;
              }
              leaf domain-name {
                type string;
              }
            }
          }
        }
        leaf name {
          type string;
        }
        leaf multicast {
          type string;
        }
        container recursive {
          leaf retry {
            type string;
          }
          leaf allow-soa {
            type empty;
          }
        }
      }
      container host {
        uses ncs_template_ip-host-grouping;
        list vrf {
          // NCS patched for predictable order
          ordered-by user;
          key "name";
          leaf name {
            // NCS drop tailf-common:cli-diff-dependency statement
            // NCS drop tailf-common:cli-diff-dependency statement
            type string;
          }
          uses ncs_template_ip-host-grouping;
        }
      }
      container name-server {
        uses ncs_template_ip-name-server-grouping;
        list vrf {
          // NCS patched for predictable order
          ordered-by user;
          key "name";
          leaf name {
            // NCS drop tailf-common:cli-diff-dependency statement
            // NCS drop tailf-common:cli-diff-dependency statement
            type string;
          }
          uses ncs_template_ip-name-server-grouping;
        }
      }
      container mcr-conf {
        leaf multicast-routing {
          type empty;
        }
      }
      container multicast-routing {
        // NCS drop tailf-common:cli-diff-dependency statement
        list vrf {
          // NCS patched for predictable order
          ordered-by user;
          // NCS drop tailf-common:cli-diff-dependency statement
          key "name";
          leaf name {
            // NCS drop tailf-common:cli-diff-dependency statement
            // NCS drop tailf-common:cli-diff-dependency statement
            type string;
          }
          leaf distributed {
            type empty;
          }
        }
        leaf distributed {
          type empty;
        }
      }
      container multicast {
        leaf route-limit {
          type string;
        }
        container multipath {
          presence "true";
          leaf s-g-hash {
            type string;
          }
        }
        list vrf {
          // NCS patched for predictable order
          ordered-by user;
          key "name";
          leaf name {
            // NCS drop tailf-common:cli-diff-dependency statement
            // NCS drop tailf-common:cli-diff-dependency statement
            type string;
          }
          container route-limit {
            leaf limit {
              type string;
            }
            leaf threshold {
              type string;
            }
          }
          container multipath {
            presence "true";
          }
        }
      }
      container icmp {
        container rate-limit {
          container unreachable {
            leaf DF {
              type empty;
            }
            leaf ms {
              type string;
            }
            leaf log {
              type empty;
            }
            leaf packets {
              // NCS drop when statement
              type string;
            }
            leaf interval-ms {
              // NCS drop when statement
              type string;
            }
          }
        }
        leaf redirect {
          type string;
          // NCS drop default statement
        }
      }
      container igmp {
        uses ncs_template_ip-igmp-grouping;
        container snooping-conf {
          container snooping {
            leaf l2-entry-limit {
              type string;
            }
            leaf last-member-query-interval {
              type string;
            }
            container source-only-learning {
              leaf age-timer {
                type string;
                // NCS drop default statement
              }
            }
          }
        }
        leaf snooping {
          type string;
          // NCS drop default statement
        }
        container snooping-vlan {
          // NCS drop when statement
          container snooping {
            container vlan {
              list no-list {
                // NCS patched for predictable order
                ordered-by user;
                key "id";
                leaf id {
                  type string;
                }
              }
            }
          }
        }
        list vrf {
          // NCS patched for predictable order
          ordered-by user;
          key "name";
          leaf name {
            // NCS drop tailf-common:cli-diff-dependency statement
            // NCS drop tailf-common:cli-diff-dependency statement
            type string;
          }
          uses ncs_template_ip-igmp-grouping;
        }
      }
      container msdp {
        uses ncs_template_ip-msdp-grouping;
        list vrf {
          // NCS patched for predictable order
          ordered-by user;
          key "name";
          leaf name {
            // NCS drop tailf-common:cli-diff-dependency statement
            // NCS drop tailf-common:cli-diff-dependency statement
            type string;
          }
          uses ncs_template_ip-msdp-grouping;
        }
      }
      container device {
        container tracking {
          presence "true";
          container probe {
            container auto-source {
              presence "true";
              container fallback {
                leaf address {
                  type string;
                }
                leaf mask {
                  type string;
                }
              }
              leaf override {
                type empty;
              }
            }
            leaf delay {
              type string;
            }
          }
        }
      }
      container finger {
        presence "true";
        leaf rfc-compliant {
          type empty;
        }
      }
      container tcp {
        leaf selective-ack {
          type empty;
        }
        leaf mss {
          type string;
        }
        container path-mtu-discovery {
          presence "true";
          leaf age-timer {
            type string;
          }
        }
        leaf window-size {
          type string;
        }
        leaf synwait-time {
          type string;
        }
      }
      container telnet {
        leaf tos {
          type string;
        }
        container source-interface {
          uses ncs_template_interface-name-grouping;
        }
      }
      container ftp {
        leaf passive {
          type string;
          // NCS drop default statement
        }
        container source-interface {
          uses ncs_template_interface-name-grouping;
        }
        leaf username {
          type string;
        }
        container password {
          uses ncs_template_password-grouping;
        }
      }
      container tftp {
        container source-interface {
          uses ncs_template_interface-name-grouping;
        }
        container boot-interface {
          uses ncs_template_interface-name-grouping;
        }
        leaf blocksize {
          type string;
        }
      }
      container ssh {
        leaf time-out {
          type string;
          // NCS drop default statement
        }
        list port {
          // NCS patched for predictable order
          ordered-by user;
          key "port";
          leaf port {
            type string;
          }
          leaf rotary {
            type string;
          }
          leaf rotary-high {
            type string;
          }
        }
        leaf break-string {
          type string;
        }
        leaf authentication-retries {
          type string;
          // NCS drop default statement
        }
        leaf dscp {
          type string;
        }
        container logging {
          leaf events {
            type empty;
          }
        }
        leaf version {
          type string;
        }
        leaf precedence {
          type string;
        }
        leaf stricthostkeycheck {
          type empty;
        }
        container source-interface {
          uses ncs_template_interface-name-grouping;
        }
        container dh {
          container min {
            leaf size {
              type string;
              // NCS drop default statement
            }
          }
        }
        container server {
          container authenticate {
            container user {
              leaf publickey {
                type string;
                // NCS drop default statement
              }
              leaf keyboard {
                type string;
                // NCS drop default statement
              }
              leaf password {
                type string;
                // NCS drop default statement
              }
            }
          }
          uses ncs_template_ip-ssh-algorithm-grouping;
        }
        container client {
          uses ncs_template_ip-ssh-algorithm-grouping;
        }
        container rsa {
          leaf keypair-name {
            type string;
          }
        }
        container pubkey-chain {
          list username {
            // NCS patched for predictable order
            ordered-by user;
            key "name";
            leaf name {
              type string;
            }
            list key-hash {
              // NCS patched for predictable order
              ordered-by user;
              key "key-type";
              leaf key-type {
                type string;
              }
              leaf key-name {
                type string;
              }
            }
          }
        }
      }
      container scp {
        container server {
          leaf enable {
            type empty;
          }
        }
      }
      container local {
        container policy {
          leaf route-map {
            type string;
          }
        }
        list pool {
          // NCS patched for predictable order
          ordered-by user;
          key "id";
          leaf id {
            type string;
          }
          leaf start {
            type string;
          }
          leaf last {
            type string;
          }
          leaf group {
            type string;
          }
        }
      }
      leaf default-gateway {
        type string;
      }
      leaf-list default-network {
        // NCS patched for predictable order
        ordered-by user;
        type string;
      }
      leaf classless {
        type string;
        // NCS drop default statement
      }
      container forward-protocol {
        leaf nd {
          type empty;
        }
        leaf sdns {
          type string;
        }
        leaf turbo-flood {
          type string;
        }
        container spanning-tree {
          presence "true";
          leaf any-local-broadcast {
            type empty;
          }
        }
        choice udp-choice {
          leaf udp {
            type string;
            // NCS drop default statement
          }
          container udp-conf {
            container udp {
              list service {
                // NCS patched for predictable order
                ordered-by user;
                key "name";
                leaf name {
                  type string;
                }
                leaf disabled {
                  type empty;
                }
              }
            }
          }
        }
      }
      container rcmd {
        leaf domain-lookup {
          type string;
          // NCS drop default statement
        }
        leaf rcp-enable {
          type empty;
        }
        leaf rsh-enable {
          type empty;
        }
        list remote-host {
          // NCS patched for predictable order
          ordered-by user;
          key "local-username host remote-username";
          leaf local-username {
            type string;
          }
          leaf host {
            type string;
          }
          leaf remote-username {
            type string;
          }
          leaf enable {
            type empty;
          }
        }
        container source-interface {
          uses ncs_template_interface-name-grouping;
        }
      }
      container http {
        leaf server {
          type string;
        }
        leaf access-class {
          type string;
        }
        container authentication {
          choice authentication-choice {
            container aaa {
              presence "true";
              leaf exec-authorization {
                // NCS drop tailf-common:cli-diff-dependency statement
                type string;
              }
            }
            leaf local {
              type empty;
            }
          }
        }
        leaf secure-server {
          type string;
        }
        container secure-active-session-modules {
          choice modules-choice {
            leaf name {
              type string;
            }
            leaf all {
              type empty;
            }
            leaf none {
              type empty;
            }
            // NCS drop default statement
          }
        }
        container active-session-modules {
          choice modules-choice {
            leaf name {
              type string;
            }
            leaf all {
              type empty;
            }
            leaf none {
              type empty;
            }
            // NCS drop default statement
          }
        }
        container timeout-policy {
          leaf idle {
            type string;
          }
          leaf life {
            type string;
          }
          leaf requests {
            type string;
          }
        }
        container client {
          container source-interface {
            uses ncs_template_interface-name-grouping;
          }
          container proxy-server {
            leaf address {
              type string;
            }
            leaf proxy-port {
              type string;
            }
          }
        }
        leaf help-path {
          type string;
        }
      }
      container ospf {
        leaf name-lookup {
          type empty;
        }
      }
      container bgp-community {
        leaf new-format {
          type empty;
        }
      }
      container community-list {
        list number {
          // NCS patched for predictable order
          ordered-by user;
          key "no";
          leaf no {
            type string;
          }
          uses ncs_template_ip-community-list-grouping;
        }
        list standard {
          // NCS patched for predictable order
          ordered-by user;
          key "name";
          leaf name {
            type string;
          }
          uses ncs_template_ip-community-list-grouping;
        }
        list expanded {
          // NCS patched for predictable order
          ordered-by user;
          key "name";
          leaf name {
            type string;
          }
          uses ncs_template_ip-community-list-grouping;
        }
      }
      container extcommunity-list {
        list number {
          // NCS patched for predictable order
          ordered-by user;
          key "no";
          leaf no {
            type string;
          }
          uses ncs_template_ip-extcommunity-list-grouping;
        }
        container standard {
          list no-mode-list {
            // NCS patched for predictable order
            ordered-by user;
            key "name";
            leaf name {
              type string;
            }
            uses ncs_template_ip-extcommunity-list-grouping;
          }
          list mode-list {
            // NCS patched for predictable order
            ordered-by user;
            key "name";
            leaf name {
              type string;
            }
            list entry {
              // NCS patched for predictable order
              ordered-by user;
              key "id";
              leaf id {
                type string;
              }
              leaf expr {
                type string;
              }
            }
          }
        }
        container expanded {
          list no-mode-list {
            // NCS patched for predictable order
            ordered-by user;
            key "name";
            leaf name {
              type string;
            }
            uses ncs_template_ip-extcommunity-list-grouping;
          }
          list mode-list {
            // NCS patched for predictable order
            ordered-by user;
            key "name";
            leaf name {
              type string;
            }
            list entry {
              // NCS patched for predictable order
              ordered-by user;
              key "id";
              leaf id {
                type string;
              }
              leaf expr {
                type string;
              }
            }
          }
        }
      }
      container as-path {
        list access-list {
          // NCS patched for predictable order
          ordered-by user;
          key "name";
          leaf name {
            type string;
          }
          list as-path-rule {
            // NCS patched for predictable order
            ordered-by user;
            key "operation rule";
            leaf operation {
              type string;
            }
            leaf rule {
              type string;
            }
          }
        }
      }
      container flow-cache {
        leaf entries {
          type string;
        }
        container timeout {
          leaf inactive {
            type string;
          }
          leaf active {
            type string;
          }
        }
      }
      container flow-export {
        container source {
          uses ncs_template_interface-name-grouping;
        }
        leaf version {
          type string;
        }
        container template {
          // NCS drop tailf-common:cli-diff-dependency statement
          container options {
            leaf export-stats {
              type empty;
            }
          }
          leaf timeout-rate {
            type string;
            // NCS drop default statement
          }
          leaf refresh-rate {
            type string;
            // NCS drop default statement
          }
        }
        container destination {
          leaf ip {
            type string;
          }
          leaf port {
            type string;
          }
        }
      }
      container flow-aggregation {
        list cache {
          // NCS patched for predictable order
          ordered-by user;
          key "name";
          leaf name {
            type string;
          }
          container cache {
            container timeout {
              leaf active {
                type string;
              }
            }
          }
          container export {
            list destination {
              // NCS patched for predictable order
              ordered-by user;
              key "address";
              leaf address {
                type string;
              }
              leaf port {
                type string;
              }
            }
          }
        }
      }
      container dns {
        list view {
          // NCS patched for predictable order
          ordered-by user;
          key "name";
          leaf name {
            type string;
          }
          uses ncs_template_ip-dns-view-grouping;
        }
        container view-vrf {
          list view {
            // NCS patched for predictable order
            ordered-by user;
            key "vrf name";
            leaf vrf {
              // NCS drop tailf-common:cli-diff-dependency statement
              // NCS drop tailf-common:cli-diff-dependency statement
              type string;
            }
            leaf name {
              type string;
            }
            uses ncs_template_ip-dns-view-grouping;
          }
        }
        list view-list {
          // NCS patched for predictable order
          ordered-by user;
          key "name";
          leaf name {
            type string;
          }
          list view {
            // NCS patched for predictable order
            ordered-by user;
            key "name";
            leaf name {
              type string;
            }
            leaf order {
              type string;
            }
            container restrict {
              leaf name-group {
                type string;
              }
              leaf authenticate {
                type empty;
              }
            }
          }
          container view-vrf {
            list view {
              // NCS patched for predictable order
              ordered-by user;
              key "vrf name";
              leaf vrf {
                // NCS drop tailf-common:cli-diff-dependency statement
                // NCS drop tailf-common:cli-diff-dependency statement
                type string;
              }
              leaf name {
                type string;
              }
              leaf order {
                type string;
              }
              container restrict {
                leaf name-group {
                  type string;
                }
                leaf authenticate {
                  type empty;
                }
              }
            }
          }
        }
        list name-list {
          // NCS patched for predictable order
          ordered-by user;
          key "id operation";
          leaf id {
            type string;
          }
          leaf operation {
            type string;
          }
          leaf regexp {
            type string;
          }
        }
        container server {
          presence "true";
          leaf view-group {
            type string;
          }
        }
        container spoofing {
          presence "true";
        }
      }
      container mobile {
        container secure {
          list home-agent {
            // NCS patched for predictable order
            ordered-by user;
            key "lower-address";
            leaf lower-address {
              // NCS drop tailf-common:cli-diff-dependency statement
              type string;
            }
            leaf upper-address {
              type string;
            }
            choice spi-choice {
              case single-spi {
                container spi {
                  uses ncs_template_mobile-ip-spi-grouping;
                }
              }
              case range-spi {
                container inbound-spi {
                  uses ncs_template_mobile-ip-spi-grouping;
                }
                container outbound-spi {
                  uses ncs_template_mobile-ip-spi-grouping;
                }
              }
            }
            container key {
              choice key-choice {
                leaf ascii {
                  type string;
                }
                leaf hex {
                  type string;
                }
              }
            }
            container algorithm {
              choice algorithm-choice {
                leaf hmac-md5 {
                  type empty;
                }
                container md5 {
                  container mode {
                    leaf prefix-suffix {
                      type empty;
                    }
                  }
                }
              }
            }
            leaf ignore-spi {
              type empty;
            }
          }
        }
        container router {
          // NCS drop tailf-common:cli-diff-dependency statement
          presence "true";
          container address {
            leaf ipv4-address {
              // NCS drop tailf-common:cli-diff-dependency statement
              type string;
            }
            leaf ipv4-mask {
              type string;
            }
          }
          container collocated {
            leaf single-tunnel {
              // NCS drop tailf-common:cli-diff-dependency statement
              type empty;
            }
          }
          list home-agent {
            // NCS patched for predictable order
            ordered-by user;
            // NCS drop tailf-common:cli-diff-dependency statement
            key "address";
            leaf address {
              type string;
            }
            leaf priority {
              type string;
              // NCS drop default statement
            }
          }
          list mobile-network {
            // NCS patched for predictable order
            ordered-by user;
            key "name";
            leaf name {
              // NCS drop tailf-common:cli-diff-dependency statement
              type string;
            }
            container policy {
              leaf mobile-map {
                type string;
              }
            }
          }
          container register {
            container extend {
              leaf expire {
                // NCS drop tailf-common:cli-diff-dependency statement
                type string;
              }
              leaf retry {
                type string;
              }
              leaf interval {
                type string;
              }
              leaf reverse-tunnel {
                type empty;
              }
            }
          }
          leaf reverse-tunnel {
            type empty;
          }
          container tunnel {
            container mode {
              leaf gre {
                type empty;
              }
            }
          }
          container template {
            leaf Tunnel {
              type string;
            }
          }
        }
      }
      container pim {
        // NCS drop tailf-common:cli-diff-dependency statement
        uses ncs_template_ip-pim-grouping;
        list vrf {
          // NCS patched for predictable order
          ordered-by user;
          key "id";
          leaf id {
            // NCS drop tailf-common:cli-diff-dependency statement
            // NCS drop tailf-common:cli-diff-dependency statement
            type string;
          }
          uses ncs_template_ip-pim-grouping;
        }
      }
      container rsvp {
        container signalling {
          container refresh {
            container reduction-conf {
              container reduction {
                leaf ack-delay {
                  type string;
                }
              }
            }
            leaf reduction {
              type empty;
            }
          }
          container hello {
            presence "true";
            container graceful-restart {
              leaf mode {
                type string;
              }
            }
          }
        }
      }
      container nat {
        container settings {
          leaf mode {
            type string;
            // NCS drop default statement
          }
        }
        container translation {
          leaf finrst-timeout {
            type string;
          }
          leaf icmp-timeout {
            type string;
          }
          leaf tcp-timeout {
            type string;
          }
          container max-entries {
            leaf all-host {
              type string;
            }
            list vrf {
              // NCS patched for predictable order
              ordered-by user;
              // NCS drop tailf-common:cli-diff-dependency statement
              // NCS drop tailf-common:cli-diff-dependency statement
              key "name";
              leaf name {
                type string;
              }
              leaf number {
                type string;
              }
            }
            container list {
              leaf access-list {
                type string;
              }
              leaf number {
                type string;
              }
            }
          }
        }
        container service {
          container list-ftp-tcp {
            list list {
              // NCS patched for predictable order
              ordered-by user;
              key "access-list port";
              leaf access-list {
                type string;
              }
              leaf ftp {
                type empty;
              }
              leaf tcp {
                type empty;
              }
              leaf port {
                type string;
              }
            }
          }
        }
        list pool {
          // NCS patched for predictable order
          ordered-by user;
          key "id";
          leaf id {
            type string;
          }
          leaf start-address {
            type string;
          }
          leaf end-address {
            // NCS drop when statement
            type string;
          }
          choice prefix-choice {
            leaf netmask {
              type string;
            }
            leaf prefix-length {
              type string;
            }
          }
          leaf accounting {
            type string;
          }
          choice nat-choice {
            leaf arp-ping {
              type empty;
            }
            leaf type {
              type string;
            }
            leaf add-route {
              type empty;
            }
          }
        }
        container inside {
          container source {
            list list {
              // NCS patched for predictable order
              ordered-by user;
              key "id";
              leaf id {
                type string;
              }
              uses ncs_template_ip-nat-inside-grouping;
              uses ncs_template_ip-nat-inside-options-grouping;
            }
            container list-vrf {
              list list {
                // NCS patched for predictable order
                ordered-by user;
                // NCS drop tailf-common:cli-diff-dependency statement
                // NCS drop tailf-common:cli-diff-dependency statement
                key "id vrf";
                leaf id {
                  type string;
                }
                uses ncs_template_ip-nat-inside-vrf-grouping;
                uses ncs_template_ip-nat-inside-options-grouping;
              }
            }
            container static {
              list nat-static-address-list {
                // NCS patched for predictable order
                ordered-by user;
                key "local-ip global-ip";
                leaf local-ip {
                  type string;
                }
                leaf global-ip {
                  type string;
                }
                uses ncs_template_ip-nat-source-static-grouping;
              }
              list nat-static-address-list-vrf {
                // NCS patched for predictable order
                ordered-by user;
                key "local-ip global-ip vrf";
                leaf local-ip {
                  type string;
                }
                leaf global-ip {
                  type string;
                }
                leaf vrf {
                  // NCS drop tailf-common:cli-diff-dependency statement
                  // NCS drop tailf-common:cli-diff-dependency statement
                  type string;
                }
                uses ncs_template_ip-nat-source-static-grouping;
              }
              list nat-static-transport-list {
                // NCS patched for predictable order
                ordered-by user;
                key "proto local-ip local-port global-ip global-port";
                leaf proto {
                  type string;
                }
                leaf local-ip {
                  type string;
                }
                leaf local-port {
                  type string;
                }
                leaf global-ip {
                  type string;
                }
                leaf global-port {
                  type string;
                }
                uses ncs_template_ip-nat-source-static-grouping;
              }
              list nat-static-transport-list-vrf {
                // NCS patched for predictable order
                ordered-by user;
                key "proto local-ip local-port global-ip global-port vrf";
                leaf proto {
                  type string;
                }
                leaf local-ip {
                  type string;
                }
                leaf local-port {
                  type string;
                }
                leaf global-ip {
                  type string;
                }
                leaf global-port {
                  type string;
                }
                leaf vrf {
                  // NCS drop tailf-common:cli-diff-dependency statement
                  // NCS drop tailf-common:cli-diff-dependency statement
                  type string;
                }
                uses ncs_template_ip-nat-source-static-grouping;
              }
              list nat-static-transport-interface-list {
                // NCS patched for predictable order
                ordered-by user;
                key "proto local-ip local-port";
                leaf proto {
                  type string;
                }
                leaf local-ip {
                  type string;
                }
                leaf local-port {
                  type string;
                }
                container interface {
                  uses ncs_template_interface-name-grouping;
                }
                leaf global-port {
                  type string;
                }
              }
            }
            list route-map {
              // NCS patched for predictable order
              ordered-by user;
              key "id";
              leaf id {
                type string;
              }
              uses ncs_template_ip-nat-inside-grouping;
              uses ncs_template_ip-nat-inside-options-grouping;
            }
            container route-map-vrf {
              list route-map {
                // NCS patched for predictable order
                ordered-by user;
                // NCS drop tailf-common:cli-diff-dependency statement
                // NCS drop tailf-common:cli-diff-dependency statement
                key "id vrf";
                leaf id {
                  type string;
                }
                uses ncs_template_ip-nat-inside-vrf-grouping;
                uses ncs_template_ip-nat-inside-options-grouping;
              }
            }
          }
          container destination {
            list list {
              // NCS patched for predictable order
              ordered-by user;
              key "id";
              leaf id {
                type string;
              }
              leaf pool {
                type string;
              }
              leaf redundancy {
                type string;
              }
              leaf mapping-id {
                type string;
              }
            }
          }
        }
        container outside {
          container source {
            list list {
              // NCS patched for predictable order
              ordered-by user;
              key "id";
              leaf id {
                type string;
              }
              leaf pool {
                type string;
              }
              uses ncs_template_ip-nat-outside-source-grouping;
            }
            container list-vrf {
              list list {
                // NCS patched for predictable order
                ordered-by user;
                key "id vrf";
                leaf id {
                  type string;
                }
                leaf pool {
                  type string;
                }
                leaf vrf {
                  // NCS drop tailf-common:cli-diff-dependency statement
                  // NCS drop tailf-common:cli-diff-dependency statement
                  type string;
                }
                uses ncs_template_ip-nat-outside-source-grouping;
              }
            }
            list route-map {
              // NCS patched for predictable order
              ordered-by user;
              key "id";
              leaf id {
                type string;
              }
              leaf pool {
                type string;
              }
              uses ncs_template_ip-nat-outside-source-grouping;
            }
            container route-map-vrf {
              list route-map {
                // NCS patched for predictable order
                ordered-by user;
                key "id vrf";
                leaf id {
                  type string;
                }
                leaf pool {
                  type string;
                }
                leaf vrf {
                  // NCS drop tailf-common:cli-diff-dependency statement
                  // NCS drop tailf-common:cli-diff-dependency statement
                  type string;
                }
                uses ncs_template_ip-nat-outside-source-grouping;
              }
            }
            container static {
              list nat-static-address-list {
                // NCS patched for predictable order
                ordered-by user;
                key "global-ip local-ip";
                leaf global-ip {
                  type string;
                }
                leaf local-ip {
                  type string;
                }
                uses ncs_template_ip-nat-source-static-grouping;
              }
              list nat-static-address-list-vrf {
                // NCS patched for predictable order
                ordered-by user;
                key "global-ip local-ip";
                leaf global-ip {
                  type string;
                }
                leaf local-ip {
                  type string;
                }
                leaf vrf {
                  // NCS drop tailf-common:cli-diff-dependency statement
                  // NCS drop tailf-common:cli-diff-dependency statement
                  type string;
                }
                uses ncs_template_ip-nat-source-static-grouping;
              }
              list nat-static-transport-list {
                // NCS patched for predictable order
                ordered-by user;
                key "proto global-ip global-port local-ip local-port";
                leaf proto {
                  type string;
                }
                leaf global-ip {
                  type string;
                }
                leaf global-port {
                  type string;
                }
                leaf local-ip {
                  type string;
                }
                leaf local-port {
                  type string;
                }
                uses ncs_template_ip-nat-source-static-grouping;
              }
              list nat-static-transport-list-vrf {
                // NCS patched for predictable order
                ordered-by user;
                key "proto global-ip global-port local-ip local-port vrf";
                leaf proto {
                  type string;
                }
                leaf global-ip {
                  type string;
                }
                leaf global-port {
                  type string;
                }
                leaf local-ip {
                  type string;
                }
                leaf local-port {
                  type string;
                }
                leaf vrf {
                  // NCS drop tailf-common:cli-diff-dependency statement
                  // NCS drop tailf-common:cli-diff-dependency statement
                  type string;
                }
                uses ncs_template_ip-nat-source-static-grouping;
              }
            }
          }
        }
      }
      container route {
        container static {
          leaf adjust-time {
            type string;
          }
          leaf inter-vrf {
            type string;
            // NCS drop default statement
          }
          container bfd {
            list ip-route-bfd-forwarding-list {
              // NCS patched for predictable order
              ordered-by user;
              key "interface ip-address";
              leaf interface {
                // NCS drop tailf-common:cli-diff-dependency statement
                type string;
              }
              leaf ip-address {
                type string;
              }
              leaf group {
                type string;
              }
            }
          }
          leaf install-routes-recurse-via-nexthop {
            type empty;
          }
          container install-routes-recurse-via-nexthop-vrf {
            container install-routes-recurse-via-nexthop {
              list vrf {
                // NCS patched for predictable order
                ordered-by user;
                key "name";
                leaf name {
                  // NCS drop tailf-common:cli-diff-dependency statement
                  // NCS drop tailf-common:cli-diff-dependency statement
                  type string;
                }
              }
            }
          }
        }
        leaf profile {
          type empty;
        }
        uses ncs_template_ip-route-grouping {
          refine "ip-route-interface-forwarding-list/interface" {
            // NCS drop tailf-common:cli-diff-dependency statement
          }
          refine "ip-route-interface-list/interface" {
            // NCS drop tailf-common:cli-diff-dependency statement
          }
        }
        list vrf {
          // NCS patched for predictable order
          ordered-by user;
          // NCS drop tailf-common:cli-diff-dependency statement
          key "name";
          leaf name {
            // NCS drop tailf-common:cli-diff-dependency statement
            // NCS drop tailf-common:cli-diff-dependency statement
            type string;
          }
          uses ncs_template_ip-route-grouping {
            refine "ip-route-interface-forwarding-list/interface" {
              // NCS drop tailf-common:cli-diff-dependency statement
            }
            refine "ip-route-interface-list/interface" {
              // NCS drop tailf-common:cli-diff-dependency statement
            }
          }
        }
      }
      container explicit-path {
        list identifier {
          // NCS patched for predictable order
          ordered-by user;
          key "number";
          leaf number {
            type string;
          }
          leaf mode {
            type string;
          }
          uses ncs_template_ip-explicit-path-grouping;
        }
        list name {
          // NCS patched for predictable order
          ordered-by user;
          key "name";
          leaf name {
            type string;
          }
          leaf mode {
            type string;
          }
          uses ncs_template_ip-explicit-path-grouping;
        }
      }
      container tacacs {
        container source-interface {
          uses ncs_template_interface-name-grouping;
        }
      }
      container access-list {
        // NCS drop tailf-common:cli-diff-dependency statement
        container logging {
          leaf interval {
            type string;
          }
          leaf hash-generation {
            type empty;
          }
        }
        leaf persistent {
          type empty;
        }
        container standard {
          // NCS drop when statement
          list std-named-acl {
            // NCS patched for predictable order
            ordered-by user;
            key "name";
            leaf name {
              type string;
            }
            list std-access-list-rule {
              // NCS patched for predictable order
              ordered-by user;
              key "rule";
              leaf rule {
                // NCS drop tailf-common:cli-diff-dependency statement
                type string;
              }
            }
          }
        }
        container extended {
          // NCS drop when statement
          list ext-named-acl {
            // NCS patched for predictable order
            ordered-by user;
            key "name";
            leaf name {
              type string;
            }
            list ext-access-list-rule {
              // NCS patched for predictable order
              ordered-by user;
              key "rule";
              leaf rule {
                // NCS drop tailf-common:cli-diff-dependency statement
                type string;
              }
            }
          }
        }
        list filter-list {
          // NCS patched for predictable order
          ordered-by user;
          // NCS drop when statement
          // NCS drop tailf-common:cli-diff-dependency statement
          key "name";
          leaf name {
            type string;
          }
          leaf type {
            type string;
          }
          list entry-list {
            // NCS patched for predictable order
            ordered-by user;
            key "seq";
            leaf seq {
              type string;
            }
            leaf entry {
              // NCS drop tailf-common:cli-diff-dependency statement
              type string;
            }
          }
        }
      }
      container prefix-list {
        leaf sequence-number {
          type string;
          // NCS drop default statement
        }
        list prefixes {
          // NCS patched for predictable order
          ordered-by user;
          // NCS drop when statement
          // NCS drop tailf-common:cli-diff-dependency statement
          key "name";
          leaf name {
            type string;
          }
          leaf description {
            type string;
          }
          list seq {
            // NCS patched for predictable order
            ordered-by user;
            key "no";
            leaf no {
              type string;
            }
            container deny {
              leaf ip {
                type string;
              }
              leaf ge {
                type string;
              }
              leaf le {
                type string;
              }
            }
            container permit {
              leaf ip {
                type string;
              }
              leaf ge {
                type string;
              }
              leaf le {
                type string;
              }
            }
          }
        }
        list prefixes-no-seq {
          // NCS patched for predictable order
          ordered-by user;
          // NCS drop when statement
          // NCS drop tailf-common:cli-diff-dependency statement
          key "name";
          leaf name {
            type string;
          }
          leaf description {
            type string;
          }
          list entry {
            // NCS patched for predictable order
            ordered-by user;
            key "rule";
            leaf rule {
              type string;
            }
          }
        }
      }
      container radius {
        container source-interface {
          uses ncs_template_interface-name-grouping;
        }
        container source-interface-vrf {
          list source-interface {
            // NCS patched for predictable order
            ordered-by user;
            // NCS drop tailf-common:cli-diff-dependency statement
            key "vrf";
            leaf name {
              type string;
            }
            leaf vrf {
              // NCS drop tailf-common:cli-diff-dependency statement
              // NCS drop tailf-common:cli-diff-dependency statement
              type string;
            }
          }
        }
      }
      container sla {
        // NCS drop tailf-common:cli-diff-dependency statement
        // NCS drop tailf-common:cli-diff-dependency statement
        container auto {
          leaf discovery {
            type empty;
          }
        }
        container responder-twamp {
          container responder {
            container twamp {
              presence "true";
              leaf timeout {
                type string;
              }
            }
          }
        }
        container responder {
          presence "true";
        }
        container responder-udp-echo {
          container responder {
            container udp-echo {
              leaf ipaddress {
                type string;
              }
              leaf port {
                type string;
              }
            }
          }
        }
        container server {
          container twamp {
            presence "true";
            leaf port {
              type string;
              // NCS drop default statement
            }
            container timer {
              leaf inactivity {
                type string;
              }
            }
          }
        }
        container logging {
          leaf traps {
            type empty;
          }
        }
        leaf key-chain {
          type string;
        }
        list ip-sla-list {
          // NCS patched for predictable order
          ordered-by user;
          // NCS drop tailf-common:cli-diff-dependency statement
          // NCS drop tailf-common:cli-diff-dependency statement
          key "id";
          leaf id {
            type string;
          }
          list tcp-connect {
            // NCS patched for predictable order
            ordered-by user;
            key "destination destination-port";
            leaf destination {
              type string;
            }
            leaf destination-port {
              type string;
            }
            leaf source-ip {
              type string;
            }
            leaf source-port {
              type string;
            }
            leaf control {
              type string;
              // NCS drop default statement
            }
          }
          list udp-jitter {
            // NCS patched for predictable order
            ordered-by user;
            key "destination destination-port";
            leaf destination {
              type string;
            }
            leaf destination-port {
              type string;
            }
            leaf source-ip {
              type string;
            }
            leaf source-port {
              type string;
            }
            leaf num-packets {
              type string;
              // NCS drop default statement
            }
            leaf codec {
              type string;
            }
            leaf codec-numpackets {
              // NCS drop when statement
              type string;
            }
            leaf interval {
              type string;
              // NCS drop default statement
            }
            leaf control {
              type string;
              // NCS drop default statement
            }
          }
          list icmp-echo {
            // NCS patched for predictable order
            ordered-by user;
            key "host";
            leaf host {
              type string;
            }
            choice source-choice {
              container source-interface {
                uses ncs_template_interface-name-grouping;
              }
              leaf source-ip {
                type string;
              }
            }
          }
          list udp-echo {
            // NCS patched for predictable order
            ordered-by user;
            key "host port";
            leaf host {
              type string;
            }
            leaf port {
              type string;
            }
            leaf control {
              type string;
            }
            leaf source-ip {
              type string;
            }
            leaf source-port {
              type string;
            }
          }
          container ethernet {
            list ethernet-list {
              // NCS patched for predictable order
              ordered-by user;
              key "type mpid domain";
              leaf type {
                type string;
              }
              leaf mpid {
                type string;
              }
              leaf domain {
                type string;
              }
              choice vlan-or-port {
                leaf port {
                  type empty;
                }
                leaf vlan {
                  type string;
                }
              }
            }
            container y1731 {
              list delay {
                // NCS patched for predictable order
                ordered-by user;
                key "name";
                leaf name {
                  type string;
                }
                leaf burst {
                  type empty;
                }
                leaf domain {
                  type string;
                }
                choice evc-or-vlan {
                  leaf evc {
                    type string;
                  }
                  leaf vlan {
                    type string;
                  }
                }
                choice mpid-or-mac {
                  leaf mac-address {
                    type string;
                  }
                  leaf mpid {
                    type string;
                  }
                }
                leaf cos {
                  type string;
                }
                container source {
                  choice mpid-or-mac {
                    leaf mac-address {
                      type string;
                    }
                    leaf mpid {
                      type string;
                    }
                  }
                }
              }
              container delay-receive {
                container delay {
                  list receive {
                    // NCS patched for predictable order
                    ordered-by user;
                    key "name";
                    leaf name {
                      type string;
                    }
                    leaf domain {
                      type string;
                    }
                    choice evc-or-vlan {
                      leaf evc {
                        type string;
                      }
                      leaf vlan {
                        type string;
                      }
                    }
                    leaf cos {
                      type string;
                    }
                    choice mpid-or-mac {
                      leaf mac-address {
                        type string;
                      }
                      leaf mpid {
                        type string;
                      }
                    }
                  }
                }
              }
              list loss {
                // NCS patched for predictable order
                ordered-by user;
                key "name";
                leaf name {
                  type string;
                }
                leaf burst {
                  type empty;
                }
                leaf domain {
                  type string;
                }
                choice evc-or-vlan {
                  leaf evc {
                    type string;
                  }
                  leaf vlan {
                    type string;
                  }
                }
                choice mpid-or-mac {
                  leaf mac-address {
                    type string;
                  }
                  leaf mpid {
                    type string;
                  }
                }
                leaf cos {
                  type string;
                }
                container source {
                  choice mpid-or-mac {
                    leaf mac-address {
                      type string;
                    }
                    leaf mpid {
                      type string;
                    }
                  }
                }
              }
            }
          }
          container http {
            leaf get {
              type string;
            }
          }
          list service-performance {
            // NCS patched for predictable order
            ordered-by user;
            key "type";
            leaf type {
              type string;
            }
            leaf dest-mac-addr {
              // NCS drop when statement
              type string;
            }
            leaf dest-ip-addr {
              // NCS drop when statement
              type string;
            }
            leaf vrf {
              // NCS drop when statement
              type string;
            }
            container interface {
              uses ncs_template_interface-name-grouping;
            }
            container service {
              leaf instance {
                type string;
              }
            }
            leaf ethernet {
              type string;
            }
          }
          uses ncs_template_description-grouping;
          leaf tos {
            type string;
          }
          leaf verify-data {
            type empty;
          }
          leaf data-pattern {
            type string;
          }
          leaf vrf {
            type string;
          }
          leaf owner {
            type string;
          }
          leaf tag {
            type string;
          }
          container frequency {
            leaf seconds {
              // NCS drop tailf-common:cli-diff-dependency statement
              // NCS drop tailf-common:cli-diff-dependency statement
              type string;
              // NCS drop default statement
            }
            leaf time {
              type string;
            }
          }
          leaf timeout {
            type string;
          }
          leaf threshold {
            type string;
          }
          container history {
            leaf hours-of-statistics-kept {
              type string;
              // NCS drop default statement
            }
            leaf distributions-of-statistics-kept {
              type string;
              // NCS drop default statement
            }
            leaf statistics-distribution-interval {
              type string;
              // NCS drop default statement
            }
            leaf lives-kept {
              type string;
              // NCS drop default statement
            }
            leaf buckets-kept {
              type string;
              // NCS drop default statement
            }
            leaf filter {
              type string;
            }
            container enhanced {
              leaf interval {
                type string;
              }
              leaf buckets {
                type string;
              }
            }
            leaf interval {
              type string;
            }
          }
          container duration {
            leaf time {
              type string;
            }
          }
          list measurement-type {
            // NCS patched for predictable order
            ordered-by user;
            key "direction";
            leaf direction {
              type string;
            }
            leaf delay {
              type empty;
            }
            leaf jitter {
              type empty;
            }
            leaf loss {
              type empty;
            }
            leaf receive {
              type empty;
            }
            leaf throughput {
              type empty;
            }
          }
          container profile {
            container packet {
              leaf inner-cos {
                type string;
              }
              leaf outer-cos {
                type string;
              }
              leaf inner-vlan {
                type string;
              }
              leaf outer-vlan {
                type string;
              }
              leaf source-ip-addr {
                type string;
              }
              leaf packet-size {
                type string;
              }
              leaf src-mac-addr {
                type string;
              }
            }
            list traffic {
              // NCS patched for predictable order
              ordered-by user;
              key "direction";
              leaf direction {
                type string;
              }
              container rate-step {
                container kbps {
                  leaf-list step {
                    // NCS patched for predictable order
                    ordered-by user;
                    type string;
                  }
                }
              }
            }
          }
          leaf cos {
            type string;
          }
          leaf request-data-size {
            type string;
          }
          container aggregate {
            leaf interval {
              type string;
            }
          }
          container availability {
            leaf algorithm {
              type string;
            }
          }
        }
        list schedule {
          // NCS patched for predictable order
          ordered-by user;
          key "operation-number";
          leaf operation-number {
            type string;
          }
          leaf life {
            type string;
          }
          container start-time {
            choice start-time-choice {
              leaf after {
                type string;
              }
              leaf now {
                type empty;
              }
              leaf pending {
                type empty;
              }
              leaf time {
                type string;
              }
            }
          }
          leaf ageout {
            type string;
          }
          leaf recurring {
            type empty;
          }
        }
        container ethernet-monitor {
          list ip-sla-ethernet-monitor-list {
            // NCS patched for predictable order
            ordered-by user;
            key "id";
            leaf id {
              type string;
            }
            list type {
              // NCS patched for predictable order
              ordered-by user;
              key "type domain vlan";
              leaf type {
                type string;
              }
              leaf domain {
                type string;
              }
              leaf vlan {
                type string;
              }
              leaf cos {
                type string;
              }
              leaf request-data-size {
                type string;
              }
            }
          }
          list schedule {
            // NCS patched for predictable order
            ordered-by user;
            key "operation-number";
            leaf operation-number {
              type string;
            }
            leaf schedule-period {
              type string;
            }
            container start-time {
              choice start-time-choice {
                leaf after {
                  type string;
                }
                leaf now {
                  type empty;
                }
                leaf pending {
                  type empty;
                }
                leaf time {
                  type string;
                }
              }
            }
          }
          list reaction-configuration {
            // NCS patched for predictable order
            ordered-by user;
            key "operation-number";
            leaf operation-number {
              type string;
            }
            container react {
              container rtt {
                presence "true";
              }
              container timeout {
                presence "true";
              }
            }
          }
        }
        list reaction-configuration {
          // NCS patched for predictable order
          ordered-by user;
          key "operation-number react";
          leaf operation-number {
            type string;
          }
          leaf react {
            type string;
          }
          container threshold-value {
            leaf upper-threshold {
              type string;
            }
            leaf lower-threshold {
              type string;
            }
          }
          container threshold-type {
            choice threshold-type-choice {
              case average {
                leaf average {
                  type empty;
                }
                leaf n {
                  type string;
                }
              }
              case consecutive {
                leaf consecutive {
                  type empty;
                }
                leaf number {
                  type string;
                }
              }
              leaf immediate {
                type empty;
              }
              leaf never {
                type empty;
              }
              container xOfy {
                leaf x {
                  type string;
                }
                leaf y {
                  type string;
                }
              }
            }
          }
          leaf action-type {
            type string;
          }
        }
        list reaction-trigger {
          // NCS patched for predictable order
          ordered-by user;
          key "operation-number";
          leaf operation-number {
            type string;
          }
          leaf target-operation {
            type string;
          }
        }
        container enable {
          leaf timestamp {
            type empty;
          }
          leaf reaction-alerts {
            type empty;
          }
        }
      }
      container wccp {
        uses ncs_template_ip-wccp-grouping;
        list vrf {
          // NCS patched for predictable order
          ordered-by user;
          key "name";
          leaf name {
            // NCS drop tailf-common:cli-diff-dependency statement
            // NCS drop tailf-common:cli-diff-dependency statement
            type string;
          }
          uses ncs_template_ip-wccp-grouping;
        }
      }
      container nbar {
        list attribute-map {
          // NCS patched for predictable order
          ordered-by user;
          key "name";
          leaf name {
            type string;
          }
          container attribute {
            leaf business-relevance {
              type string;
            }
            leaf traffic-class {
              type string;
            }
            leaf application-group {
              type string;
            }
          }
        }
        list custom {
          // NCS patched for predictable order
          ordered-by user;
          key "name";
          leaf name {
            type string;
          }
          container composite {
            leaf server-name {
              type string;
            }
            leaf id {
              type string;
            }
          }
        }
        list attribute-set {
          // NCS patched for predictable order
          ordered-by user;
          key "protocol-name";
          leaf protocol-name {
            type string;
          }
          leaf profile-name {
            type string;
          }
        }
        container protocol-discovery {
          presence "true";
        }
      }
      container inspect {
        list name {
          // NCS patched for predictable order
          ordered-by user;
          key "name";
          leaf name {
            type string;
          }
          list rule {
            // NCS patched for predictable order
            ordered-by user;
            key "rule";
            leaf rule {
              type string;
            }
          }
        }
      }
      container spd {
        leaf enable {
          type string;
          // NCS drop default statement
        }
      }
      container source {
        list binding {
          // NCS patched for predictable order
          ordered-by user;
          key "mac-address";
          leaf mac-address {
            // NCS drop tailf-common:cli-diff-dependency statement
            // NCS drop tailf-common:cli-diff-dependency statement
            // NCS drop tailf-common:cli-diff-dependency statement
            // NCS drop tailf-common:cli-diff-dependency statement
            // NCS drop tailf-common:cli-diff-dependency statement
            // NCS drop tailf-common:cli-diff-dependency statement
            // NCS drop tailf-common:cli-diff-dependency statement
            type string;
          }
          leaf vlan {
            type string;
          }
          leaf ip-address {
            type string;
          }
          container interface {
            uses ncs_template_interface-name-grouping;
          }
        }
      }
    }
    container isdn {
      leaf switch-type {
        type string;
      }
      container leased-line {
        leaf BRI {
          type string;
        }
      }
    }
    container vmps {
      leaf reconfirm {
        type string;
      }
      leaf retry {
        type string;
      }
      list server {
        // NCS patched for predictable order
        ordered-by user;
        key "name";
        leaf name {
          type string;
        }
        leaf primary {
          type empty;
        }
      }
    }
    container ipv6 {
      leaf unicast-routing {
        type empty;
      }
      leaf source-route {
        type string;
      }
      leaf cef {
        type empty;
      }
      container cef-conf {
        container cef {
          // NCS drop tailf-common:cli-diff-dependency statement
          container accounting {
            leaf per-prefix {
              type empty;
            }
            leaf prefix-length {
              type empty;
            }
          }
          leaf distributed {
            type empty;
          }
          container load-sharing {
            container algorithm {
              choice algorithm-choice {
                leaf original {
                  type empty;
                }
                container universal {
                  leaf id {
                    type string;
                  }
                }
              }
            }
          }
        }
      }
      leaf flowset {
        type empty;
      }
      container icmp {
        container error-interval {
          leaf milliseconds {
            type string;
          }
          leaf bucketsize {
            type string;
          }
        }
      }
      container wccp {
        uses ncs_template_ip-wccp-grouping;
        list vrf {
          // NCS patched for predictable order
          ordered-by user;
          key "name";
          leaf name {
            // NCS drop tailf-common:cli-diff-dependency statement
            type string;
          }
          uses ncs_template_ip-wccp-grouping;
        }
      }
      leaf multicast-routing {
        type empty;
      }
      container multicast {
        container rpf {
          container backoff {
            leaf initial-delay {
              type string;
            }
            leaf max-delay {
              type string;
            }
          }
          leaf use-bgp {
            type empty;
          }
        }
      }
      container spd {
        container queue {
          leaf min-threshold {
            type string;
          }
          leaf max-threshold {
            // NCS drop tailf-common:cli-diff-dependency statement
            type string;
          }
        }
      }
      container route {
        // NCS drop tailf-common:cli-diff-dependency statement
        container static {
          list bfd {
            // NCS patched for predictable order
            ordered-by user;
            key "interface ipv6-address";
            leaf interface {
              // NCS drop tailf-common:cli-diff-dependency statement
              type string;
            }
            leaf ipv6-address {
              type string;
            }
            leaf unassociated {
              type empty;
            }
          }
        }
        list vrf {
          // NCS patched for predictable order
          ordered-by user;
          key "name";
          leaf name {
            // NCS drop tailf-common:cli-diff-dependency statement
            type string;
          }
          uses ncs_template_ipv6-route-grouping;
        }
        container no-vrf {
          uses ncs_template_ipv6-route-grouping;
        }
      }
      container prefix-list {
        leaf sequence-number {
          type string;
          // NCS drop default statement
        }
        list prefixes {
          // NCS patched for predictable order
          ordered-by user;
          // NCS drop when statement
          // NCS drop tailf-common:cli-diff-dependency statement
          key "name";
          leaf name {
            type string;
          }
          leaf description {
            type string;
          }
          list seq {
            // NCS patched for predictable order
            ordered-by user;
            key "no";
            leaf no {
              type string;
            }
            container deny {
              leaf ip {
                type string;
              }
              leaf ge {
                type string;
              }
              leaf le {
                type string;
              }
            }
            container permit {
              leaf ip {
                type string;
              }
              leaf ge {
                type string;
              }
              leaf le {
                type string;
              }
            }
          }
        }
        list prefixes-no-seq {
          // NCS patched for predictable order
          ordered-by user;
          // NCS drop when statement
          // NCS drop tailf-common:cli-diff-dependency statement
          key "name";
          leaf name {
            type string;
          }
          leaf description {
            type string;
          }
          list entry {
            // NCS patched for predictable order
            ordered-by user;
            key "rule";
            leaf rule {
              type string;
            }
          }
        }
      }
      container access-list {
        list named-acl {
          // NCS patched for predictable order
          ordered-by user;
          key "name";
          leaf name {
            type string;
          }
          list access-list-rule {
            // NCS patched for predictable order
            ordered-by user;
            key "rule";
            leaf rule {
              type string;
            }
          }
        }
      }
      container router {
        list rip {
          // NCS patched for predictable order
          ordered-by user;
          key "name";
          leaf name {
            type string;
          }
          container address-family {
            container ipv6 {
              list vrf {
                // NCS patched for predictable order
                ordered-by user;
                key "name";
                leaf name {
                  // NCS drop tailf-common:cli-diff-dependency statement
                  // NCS drop tailf-common:cli-diff-dependency statement
                  type string;
                }
              }
            }
          }
          container distribute-list {
            list prefix-list {
              // NCS patched for predictable order
              ordered-by user;
              key "direction";
              leaf direction {
                type string;
              }
              leaf prefix-list-name {
                type string;
              }
            }
          }
        }
        list eigrp {
          // NCS patched for predictable order
          ordered-by user;
          key "as-no";
          leaf as-no {
            type string;
          }
          container eigrp {
            leaf router-id {
              type string;
            }
          }
          leaf shutdown {
            type empty;
          }
        }
        list ospf {
          // NCS patched for predictable order
          ordered-by user;
          key "id";
          leaf id {
            type string;
          }
          uses ncs_template_router-ospf-common-grouping;
          uses ncs_template_router-ospf-common-af-grouping;
          uses ncs_template_router-ospf-grouping;
        }
      }
      container neighbor {
        list neighbor-list {
          // NCS patched for predictable order
          ordered-by user;
          key "address interface";
          leaf address {
            type string;
          }
          leaf interface {
            // NCS drop tailf-common:cli-diff-dependency statement
            type string;
          }
          leaf hardware-address {
            type string;
          }
        }
      }
      container dhcp {
        list pool {
          // NCS patched for predictable order
          ordered-by user;
          key "name";
          leaf name {
            type string;
          }
          leaf vrf {
            type string;
          }
          leaf dns-server {
            type string;
          }
          leaf domain-name {
            type string;
          }
        }
      }
      container rip {
        container vrf-mode {
          leaf enable {
            type empty;
          }
        }
      }
    }
    container subscriber {
      leaf templating {
        type empty;
      }
    }
    container multilink {
      leaf virtual-template {
        type string;
      }
      leaf bundle-name {
        type string;
      }
    }
    container flow {
      list exporter {
        // NCS patched for predictable order
        ordered-by user;
        key "name";
        leaf name {
          type string;
        }
        leaf description {
          type string;
        }
        container destination {
          leaf address {
            type string;
          }
          leaf vrf {
            // NCS drop tailf-common:cli-diff-dependency statement
            // NCS drop tailf-common:cli-diff-dependency statement
            type string;
          }
        }
        container source {
          uses ncs_template_interface-name-grouping;
        }
        leaf dscp {
          type string;
        }
        container transport {
          leaf udp {
            type string;
          }
        }
        leaf export-protocol {
          type string;
        }
        container template {
          container data {
            leaf timeout {
              type string;
            }
          }
        }
        container option {
          container interface-table {
            presence "true";
            leaf timeout {
              type string;
            }
          }
          container exporter-stats {
            presence "true";
            leaf timeout {
              type string;
            }
          }
          container sampler-table {
            presence "true";
            leaf timeout {
              type string;
            }
          }
          container c3pl-class-table {
            presence "true";
            leaf timeout {
              type string;
            }
          }
          container c3pl-policy-table {
            presence "true";
            leaf timeout {
              type string;
            }
          }
          container application-attributes {
            presence "true";
            leaf timeout {
              type string;
            }
          }
          container application-table {
            presence "true";
            leaf timeout {
              type string;
            }
          }
        }
      }
      list record {
        // NCS patched for predictable order
        ordered-by user;
        key "name";
        leaf name {
          type string;
        }
        leaf type {
          type string;
        }
        leaf description {
          type string;
        }
        container match {
          container ipv4 {
            leaf tos {
              type empty;
            }
            leaf ttl {
              type empty;
            }
            leaf protocol {
              type empty;
            }
            container source {
              leaf address {
                type empty;
              }
              container prefix {
                presence "true";
                leaf minimum-mask {
                  type string;
                }
              }
              container mask {
                presence "true";
                leaf minimum-mask {
                  type string;
                }
              }
            }
            container destination {
              leaf address {
                type empty;
              }
            }
          }
          container ipv6 {
            leaf traffic-class {
              type empty;
            }
            leaf protocol {
              type empty;
            }
            container source {
              leaf address {
                type empty;
              }
            }
            container destination {
              leaf address {
                type empty;
              }
            }
          }
          container connection {
            leaf transaction-id {
              type empty;
            }
            container client {
              container ipv4 {
                leaf address {
                  type empty;
                }
              }
              container ipv6 {
                leaf address {
                  type empty;
                }
              }
            }
            container server {
              container ipv4 {
                leaf address {
                  type empty;
                }
              }
              container ipv6 {
                leaf address {
                  type empty;
                }
              }
              container transport {
                leaf port {
                  type empty;
                }
              }
            }
          }
          container policy {
            container qos {
              container classification {
                leaf hierarchy {
                  type empty;
                }
              }
              container queue {
                leaf drops {
                  type empty;
                }
                leaf index {
                  type empty;
                }
              }
            }
          }
          container transport {
            leaf source-port {
              type empty;
            }
            leaf destination-port {
              type empty;
            }
          }
          container interface {
            container input {
              presence "true";
              leaf snmp {
                type empty;
              }
            }
            container output {
              presence "true";
              leaf snmp {
                type empty;
              }
            }
          }
          container flow {
            leaf direction {
              type empty;
            }
            container sampler {
              presence "true";
              container hash {
                leaf digest-value {
                  type empty;
                }
              }
            }
          }
          container application {
            container name {
              presence "true";
              leaf account-on-resolution {
                type empty;
              }
            }
          }
        }
        container collect {
          container routing {
            container source {
              container as {
                presence "true";
              }
            }
            container destination {
              container as {
                presence "true";
              }
            }
            container vrf {
              leaf input {
                type empty;
              }
              leaf output {
                type empty;
              }
            }
            container next-hop {
              container address {
                container ipv4 {
                  presence "true";
                  leaf bgp {
                    type empty;
                  }
                }
                container ipv6 {
                  presence "true";
                  leaf bgp {
                    type empty;
                  }
                }
              }
            }
          }
          container ipv4 {
            leaf dscp {
              type empty;
            }
            leaf id {
              type empty;
            }
            container source {
              container mask {
                presence "true";
              }
              container prefix {
                presence "true";
              }
            }
            container destination {
              container mask {
                presence "true";
              }
            }
          }
          container ipv6 {
            leaf dscp {
              type empty;
            }
            container source {
              container mask {
                presence "true";
              }
            }
            container destination {
              container mask {
                presence "true";
              }
            }
          }
          container transport {
            container tcp {
              container flags {
                presence "true";
              }
            }
          }
          container interface {
            leaf input {
              type empty;
            }
            leaf output {
              type empty;
            }
          }
          container flow {
            leaf sampler {
              type empty;
            }
            leaf direction {
              type empty;
            }
          }
          container counter {
            container bytes {
              presence "true";
              leaf long {
                type empty;
              }
            }
            container packets {
              presence "true";
              leaf long {
                type empty;
              }
            }
            leaf flows {
              type empty;
            }
          }
          container timestamp {
            container sys-uptime {
              leaf first {
                type empty;
              }
              leaf last {
                type empty;
              }
            }
            container absolute {
              leaf first {
                type empty;
              }
              leaf last {
                type empty;
              }
            }
          }
          container application {
            container name {
              presence "true";
            }
            container http {
              leaf host {
                type empty;
              }
            }
          }
          container connection {
            leaf initiator {
              type empty;
            }
            leaf new-connections {
              type empty;
            }
            container server {
              container counter {
                leaf responses {
                  type empty;
                }
                container packets {
                  leaf long {
                    type empty;
                  }
                }
                container bytes {
                  container network {
                    leaf long {
                      type empty;
                    }
                  }
                }
              }
            }
            container delay {
              container response {
                container to-server {
                  container histogram {
                    leaf bucket1 {
                      type empty;
                    }
                    leaf bucket2 {
                      type empty;
                    }
                    leaf bucket3 {
                      type empty;
                    }
                    leaf bucket4 {
                      type empty;
                    }
                    leaf bucket5 {
                      type empty;
                    }
                    leaf bucket6 {
                      type empty;
                    }
                    leaf bucket7 {
                      type empty;
                    }
                    leaf late {
                      type empty;
                    }
                  }
                }
                container client-to-server {
                  leaf sum {
                    type empty;
                  }
                }
              }
              container network {
                container to-server {
                  leaf sum {
                    type empty;
                  }
                }
                container to-client {
                  leaf sum {
                    type empty;
                  }
                }
              }
              container application {
                leaf sum {
                  type empty;
                }
              }
            }
            container transaction {
              container counter {
                leaf complete {
                  type empty;
                }
              }
            }
            container client {
              container counter {
                container packets {
                  leaf retransmitted {
                    type empty;
                  }
                  leaf long {
                    type empty;
                  }
                }
                container bytes {
                  container network {
                    leaf long {
                      type empty;
                    }
                  }
                }
              }
            }
          }
          container policy {
            container qos {
              container queue {
                leaf drops {
                  type empty;
                }
                leaf index {
                  type empty;
                }
              }
              container classification {
                leaf hierarchy {
                  type empty;
                }
              }
            }
          }
        }
      }
      list monitor {
        // NCS patched for predictable order
        ordered-by user;
        key "name";
        leaf name {
          type string;
        }
        leaf type {
          type string;
        }
        leaf description {
          type string;
        }
        leaf record {
          type string;
        }
        list exporter {
          // NCS patched for predictable order
          ordered-by user;
          key "name";
          leaf name {
            type string;
          }
        }
        container cache {
          container timeout {
            leaf inactive {
              type string;
            }
            leaf active {
              type string;
            }
            leaf update {
              type string;
            }
            leaf synchronized {
              type string;
            }
          }
          leaf type {
            type string;
          }
          leaf entries {
            type string;
          }
        }
        container history {
          leaf size {
            type string;
          }
        }
      }
    }
    list domain {
      // NCS patched for predictable order
      ordered-by user;
      key "name";
      leaf name {
        type string;
      }
      list vrf {
        // NCS patched for predictable order
        ordered-by user;
        key "name";
        leaf name {
          // NCS drop tailf-common:cli-diff-dependency statement
          // NCS drop tailf-common:cli-diff-dependency statement
          type string;
        }
        uses ncs_template_domain-master-grouping;
        uses ncs_template_domain-border-grouping;
      }
      uses ncs_template_domain-master-grouping {
        refine "master" {
          // NCS drop tailf-common:cli-diff-dependency statement
        }
      }
      uses ncs_template_domain-border-grouping {
        refine "border" {
          // NCS drop tailf-common:cli-diff-dependency statement
        }
        augment "border" {
          container advanced {
            presence "true";
            uses ncs_template_domain-advanced-smart-probes-grouping;
          }
        }
      }
    }
    container archive {
      container log {
        container config {
          container logging {
            leaf enable {
              type empty;
            }
            leaf size {
              type string;
              // NCS drop default statement
            }
          }
          leaf hidekeys {
            type empty;
          }
          container notify {
            container syslog {
              presence "true";
              leaf contenttype {
                type string;
              }
            }
          }
          container record {
            leaf rc {
              type empty;
            }
          }
        }
      }
      leaf path {
        type string;
      }
      leaf maximum {
        type string;
      }
      leaf write-memory {
        type empty;
      }
    }
    container file {
      leaf prompt {
        type string;
        // NCS drop default statement
      }
      leaf verify {
        type string;
      }
    }
    container object-group {
      list network {
        // NCS patched for predictable order
        ordered-by user;
        key "name";
        leaf name {
          type string;
        }
        leaf description {
          type string;
        }
        list host {
          // NCS patched for predictable order
          ordered-by user;
          key "name";
          leaf name {
            type string;
          }
        }
        list subnet {
          // NCS patched for predictable order
          ordered-by user;
          key "network-address network-mask";
          leaf network-address {
            type string;
          }
          leaf network-mask {
            type string;
          }
        }
      }
      list service {
        // NCS patched for predictable order
        ordered-by user;
        key "name";
        leaf name {
          type string;
        }
        leaf description {
          type string;
        }
        leaf-list protocol {
          // NCS patched for predictable order
          ordered-by user;
          type string;
        }
        container icmp-options {
          container icmp {
            list match {
              // NCS patched for predictable order
              ordered-by user;
              key "port";
              leaf port {
                type string;
              }
              uses ncs_template_object-group-service-protocol-match;
            }
            list range {
              // NCS patched for predictable order
              ordered-by user;
              key "begin end";
              leaf begin {
                type string;
              }
              leaf end {
                type string;
              }
            }
          }
        }
        container udp-options {
          container udp {
            list match {
              // NCS patched for predictable order
              ordered-by user;
              key "port";
              leaf port {
                type string;
              }
              uses ncs_template_object-group-service-protocol-match;
            }
            list range {
              // NCS patched for predictable order
              ordered-by user;
              key "begin end";
              leaf begin {
                type string;
              }
              leaf end {
                type string;
              }
            }
          }
        }
        container tcp-options {
          container tcp {
            list match {
              // NCS patched for predictable order
              ordered-by user;
              key "port";
              leaf port {
                type string;
              }
              uses ncs_template_object-group-service-protocol-match;
            }
            list range {
              // NCS patched for predictable order
              ordered-by user;
              key "begin end";
              leaf begin {
                type string;
              }
              leaf end {
                type string;
              }
            }
          }
        }
        container tcp-udp {
          list match {
            // NCS patched for predictable order
            ordered-by user;
            key "port";
            leaf port {
              type string;
            }
            uses ncs_template_object-group-service-protocol-match;
          }
          list range {
            // NCS patched for predictable order
            ordered-by user;
            key "begin end";
            leaf begin {
              type string;
            }
            leaf end {
              type string;
            }
          }
        }
      }
      list security {
        // NCS patched for predictable order
        ordered-by user;
        key "name";
        leaf name {
          type string;
        }
        leaf description {
          type string;
        }
      }
    }
    container key {
      container config-key {
        leaf password-encrypt {
          type string;
        }
      }
      list chain {
        // NCS patched for predictable order
        ordered-by user;
        key "name";
        leaf name {
          type string;
        }
        list key {
          // NCS patched for predictable order
          ordered-by user;
          key "id";
          leaf id {
            type string;
          }
          container key-string {
            uses ncs_template_password-grouping;
          }
          leaf cryptographic-algorithm {
            type string;
          }
          container accept-lifetime {
            choice accept-lifetime-choice {
              case global {
                uses ncs_template_lifetime-grouping;
              }
              container local {
                uses ncs_template_lifetime-grouping;
              }
            }
          }
          container send-lifetime {
            choice send-lifetime-choice {
              case global {
                uses ncs_template_lifetime-grouping;
              }
              container local {
                uses ncs_template_lifetime-grouping;
              }
            }
          }
        }
      }
    }
    container flowspec {
      presence "true";
      container local-install {
        leaf interface-all {
          type empty;
        }
      }
      container address-family {
        container ipv4 {
          container local-install {
            leaf interface-all {
              type empty;
            }
          }
        }
        container ipv6 {
          container local-install {
            leaf interface-all {
              type empty;
            }
          }
        }
      }
      list vrf {
        // NCS patched for predictable order
        ordered-by user;
        key "name";
        leaf name {
          // NCS drop tailf-common:cli-diff-dependency statement
          // NCS drop tailf-common:cli-diff-dependency statement
          type string;
        }
        container address-family {
          container ipv4 {
            container local-install {
              leaf interface-all {
                type empty;
              }
            }
          }
          container ipv6 {
            container local-install {
              leaf interface-all {
                type empty;
              }
            }
          }
        }
      }
    }
    list username {
      // NCS patched for predictable order
      ordered-by user;
      key "name";
      leaf name {
        type string;
      }
      leaf privilege {
        type string;
        // NCS drop default statement
      }
      container secret {
        leaf type {
          type string;
        }
        leaf secret {
          type string;
        }
      }
      container password {
        uses ncs_template_password-grouping;
      }
    }
    list table-map {
      // NCS patched for predictable order
      ordered-by user;
      key "name";
      leaf name {
        type string;
      }
      container map {
        list from {
          // NCS patched for predictable order
          ordered-by user;
          key "id";
          leaf id {
            type string;
          }
          leaf to {
            type string;
          }
        }
      }
      leaf default {
        type string;
      }
    }
    container sdm {
      container prefer {
        presence "true";
        choice sdm-prefer-choice {
          leaf access {
            type empty;
          }
          leaf default {
            type empty;
          }
          leaf dual-ipv4-and-ipv6 {
            type string;
          }
          leaf routing {
            type empty;
          }
          leaf qos {
            type empty;
          }
          leaf vlan {
            type empty;
          }
        }
      }
    }
    container mls {
      container acl {
        container tcam {
          leaf default-result {
            type string;
          }
          container log-update {
            presence "true";
            leaf rate-limit-msg {
              type string;
            }
          }
          leaf share-global {
            type string;
            // NCS drop default statement
          }
        }
      }
      container cef {
        container error {
          leaf action {
            type string;
          }
        }
      }
      container ip {
        container multicast {
          presence "true";
          container consistency-check {
            presence "true";
            container type {
              container rp-sp {
                presence "true";
              }
            }
            leaf settle-time {
              type string;
            }
          }
          leaf flow-stat-timer {
            type string;
          }
        }
      }
      container ipv6 {
        leaf vrf {
          type empty;
        }
      }
      container aging {
        container fast {
          presence "true";
          leaf time {
            type string;
          }
          leaf threshold {
            type string;
          }
        }
        container normal {
          leaf seconds {
            type string;
          }
        }
        container long {
          leaf timeout {
            type string;
          }
        }
      }
      container netflow {
        presence "true";
        leaf interface {
          type empty;
        }
        container usage {
          container notify {
            leaf percentage {
              type string;
            }
            leaf seconds {
              type string;
            }
          }
        }
      }
      container flow {
        leaf ip {
          type string;
        }
        choice ipv6-choice {
          container no-ipv6 {
            leaf ipv6 {
              type string;
              // NCS drop default statement
            }
          }
          container ipv6 {
            choice ipv6-choice2 {
              leaf interface-destination {
                type empty;
              }
              leaf interface-destination-source {
                type empty;
              }
              leaf interface-full {
                type empty;
              }
              leaf interface-source {
                type empty;
              }
            }
          }
        }
      }
      container sampling {
        leaf time-based {
          type string;
        }
      }
      container mls-qos-conf {
        leaf qos {
          type empty;
        }
      }
      container qos {
        list aggregate-policer {
          // NCS patched for predictable order
          ordered-by user;
          key "name";
          leaf name {
            type string;
          }
          leaf target-bit-rate {
            type string;
          }
          leaf burst-normal {
            type string;
          }
          leaf burst-max {
            // NCS drop when statement
            type string;
          }
          leaf pir {
            type string;
          }
          container conform-action {
            choice action-choice {
              leaf drop {
                type empty;
              }
              leaf set-dscp-transmit {
                type string;
              }
              leaf set-mpls-exp-imposition-transmit {
                type string;
              }
              leaf set-prec-transmit {
                type string;
              }
              leaf transmit {
                type empty;
              }
            }
          }
          leaf exceed-action {
            type string;
          }
          leaf violate-action {
            type string;
          }
        }
        container cos {
          leaf policy-map {
            type empty;
          }
        }
        container rewrite {
          container ip {
            container dscp {
              presence "true";
              leaf slot {
                type string;
              }
            }
          }
        }
        container map {
          list dscp-mutation {
            // NCS patched for predictable order
            ordered-by user;
            key "name";
            leaf name {
              type string;
            }
            leaf mutated-dscp1 {
              type string;
            }
            leaf mutated-dscp2 {
              type string;
            }
            leaf mutated-dscp3 {
              type string;
            }
            leaf mutated-dscp4 {
              type string;
            }
            leaf mutated-dscp5 {
              type string;
            }
            leaf mutated-dscp6 {
              type string;
            }
            leaf mutated-dscp7 {
              type string;
            }
            leaf mutated-dscp8 {
              type string;
            }
            leaf to {
              type string;
            }
          }
          leaf-list cos-dscp {
            // NCS patched for predictable order
            ordered-by user;
            type string;
          }
          leaf-list ip-prec-dscp {
            // NCS patched for predictable order
            ordered-by user;
            type string;
          }
          list exp-mutation {
            // NCS patched for predictable order
            ordered-by user;
            key "name";
            leaf name {
              type string;
            }
            leaf mutated-exp1 {
              type string;
            }
            leaf mutated-exp2 {
              type string;
            }
            leaf mutated-exp3 {
              type string;
            }
            leaf mutated-exp4 {
              type string;
            }
            leaf mutated-exp5 {
              type string;
            }
            leaf mutated-exp6 {
              type string;
            }
            leaf mutated-exp7 {
              type string;
            }
            leaf mutated-exp8 {
              type string;
            }
          }
        }
        container srr-queue {
          list cos-dscp-list {
            // NCS patched for predictable order
            ordered-by user;
            key "direction maptype";
            leaf direction {
              type string;
            }
            leaf maptype {
              type string;
            }
            list queue-threshold-list {
              // NCS patched for predictable order
              ordered-by user;
              key "queue threshold";
              leaf queue {
                type string;
              }
              leaf threshold {
                type string;
              }
              leaf-list values {
                // NCS patched for predictable order
                ordered-by user;
                type string;
              }
            }
          }
          container input {
            list priority-queue {
              // NCS patched for predictable order
              ordered-by user;
              key "queue";
              leaf queue {
                type string;
              }
              leaf bandwidth {
                type string;
              }
            }
            container bandwidth {
              leaf weight1 {
                type string;
              }
              leaf weight2 {
                type string;
              }
            }
            list threshold {
              // NCS patched for predictable order
              ordered-by user;
              key "queue";
              leaf queue {
                type string;
              }
              leaf threshold-percentage1 {
                type string;
              }
              leaf threshold-percentage2 {
                type string;
              }
            }
            container buffers {
              leaf percentage1 {
                type string;
              }
              leaf percentage2 {
                type string;
              }
            }
          }
        }
        container queue-set {
          container output {
            list threshold-list {
              // NCS patched for predictable order
              ordered-by user;
              key "queue threshold";
              leaf queue {
                type string;
              }
              leaf threshold {
                type string;
              }
              leaf drop-threshold1 {
                type string;
              }
              leaf drop-threshold2 {
                type string;
              }
              leaf reserved-threshold {
                type string;
              }
              leaf maximum-threshold {
                type string;
              }
            }
            list buffers-list {
              // NCS patched for predictable order
              ordered-by user;
              key "queue";
              leaf queue {
                type string;
              }
              container buffers {
                leaf allocation1 {
                  type string;
                }
                leaf allocation2 {
                  type string;
                }
                leaf allocation3 {
                  type string;
                }
                leaf allocation4 {
                  type string;
                }
              }
            }
          }
        }
        list min-reserve {
          // NCS patched for predictable order
          ordered-by user;
          key "level";
          leaf level {
            type string;
          }
          leaf buffersize {
            type string;
          }
        }
      }
      container rate-limit {
        container multicast {
          list ipv4 {
            // NCS patched for predictable order
            ordered-by user;
            key "name";
            leaf name {
              type string;
            }
            leaf pps {
              type string;
            }
            leaf packets-in-burst {
              type string;
            }
          }
        }
        container all {
          container mtu-failure {
            leaf pps {
              type string;
            }
            leaf packets-in-burst {
              type string;
            }
          }
          container ttl-failure {
            leaf pps {
              type string;
            }
            leaf packets-in-burst {
              type string;
            }
          }
        }
        container layer2 {
          container l2pt {
            leaf packets-per-second {
              type string;
            }
            leaf packets-in-burst {
              type string;
            }
          }
          container pdu {
            leaf packets-per-second {
              type string;
            }
            leaf packets-in-burst {
              type string;
            }
          }
          container mac-security {
            leaf packets-per-second {
              type string;
            }
            leaf packets-in-burst {
              type string;
            }
          }
        }
      }
      container verify {
        container ip {
          leaf checksum {
            type string;
            // NCS drop default statement
          }
          container length {
            leaf consistent {
              type string;
              // NCS drop default statement
            }
            leaf minimum {
              type string;
              // NCS drop default statement
            }
          }
          leaf same-address {
            type empty;
          }
          leaf syslog {
            type empty;
          }
        }
      }
      container mpls {
        leaf tunnel-recir {
          type empty;
        }
      }
    }
    container policer {
      list aggregate {
        // NCS patched for predictable order
        ordered-by user;
        key "name";
        leaf name {
          type string;
        }
        leaf cir {
          type string;
        }
        leaf bc {
          type string;
        }
        leaf conform-action {
          type empty;
        }
        leaf set-qos-transmit {
          // NCS drop when statement
          type string;
        }
        leaf set-dot1ad-dei-transmit {
          // NCS drop when statement
          type string;
        }
        leaf set-prec-transmit {
          // NCS drop when statement
          type string;
        }
        container set-prec-transmit-table {
          // NCS drop when statement
          leaf table {
            type string;
          }
        }
        leaf set-dscp-transmit {
          // NCS drop when statement
          type string;
        }
        container set-dscp-transmit-table {
          // NCS drop when statement
          leaf table {
            type string;
          }
        }
        leaf set-cos-transmit {
          // NCS drop when statement
          type string;
        }
        container set-cos-transmit-table {
          // NCS drop when statement
          leaf table {
            type string;
          }
        }
        leaf transmit {
          // NCS drop when statement
          type empty;
        }
        leaf exceed-action {
          type empty;
        }
        leaf drop {
          // NCS drop when statement
          type empty;
        }
        container exceed-transmit {
          leaf transmit {
            // NCS drop when statement
            type empty;
          }
        }
      }
    }
    container redundancy {
      presence "true";
      leaf maintenance-mode {
        type empty;
      }
      leaf mode {
        type string;
      }
      list linecard-group {
        // NCS patched for predictable order
        ordered-by user;
        key "id";
        leaf id {
          type string;
        }
        leaf cable {
          type empty;
        }
        leaf internal-switch {
          type empty;
        }
        leaf description {
          type string;
        }
        leaf class {
          type string;
        }
        container reserve {
          leaf cardtype {
            type string;
          }
        }
        container rf-switch {
          leaf snmp-community {
            type string;
          }
        }
        container member {
          list slot {
            // NCS patched for predictable order
            ordered-by user;
            key "id";
            leaf id {
              type string;
            }
            choice primary-secondary-choice {
              leaf primary {
                type empty;
              }
              leaf secondary {
                type empty;
              }
            }
          }
          list subslot {
            // NCS patched for predictable order
            ordered-by user;
            key "id";
            leaf id {
              type string;
            }
            leaf working {
              type empty;
            }
            container protect {
              presence "true";
              choice config-choice {
                leaf config {
                  type string;
                }
                container no-config {
                  leaf config {
                    type string;
                    // NCS drop default statement
                  }
                }
              }
            }
          }
        }
        container conf {
          leaf revertive {
            type empty;
          }
        }
      }
      container main-cpu {
        container auto-sync {
          leaf running-config {
            type empty;
          }
          leaf config-register {
            type empty;
          }
          leaf bootvar {
            type empty;
          }
          leaf startup-config {
            type empty;
          }
          leaf standard {
            type empty;
          }
        }
        container switchover {
          container pxf {
            container restart {
              leaf number-of-crashes {
                type string;
              }
              leaf time-period {
                type string;
              }
            }
          }
        }
      }
      container interchassis {
        list group {
          // NCS patched for predictable order
          ordered-by user;
          key "id";
          leaf id {
            type string;
          }
          container member {
            leaf ip {
              type string;
            }
          }
          container mlacp {
            leaf system-mac {
              type string;
            }
            leaf system-priority {
              type string;
            }
            leaf node-id {
              type string;
            }
          }
        }
      }
    }
    container bfd-template {
      list single-hop {
        // NCS patched for predictable order
        ordered-by user;
        key "name";
        leaf name {
          type string;
        }
        container interval {
          leaf min-tx {
            type string;
          }
          leaf min-rx {
            tailf:code-name "bfd-template-min-rx";
            type string;
          }
          leaf multiplier {
            type string;
          }
        }
      }
    }
    leaf process-max-time {
      type string;
    }
    container map-class {
      list frame-relay {
        // NCS patched for predictable order
        ordered-by user;
        key "name";
        leaf name {
          type string;
        }
        container frame-relay {
          leaf fragment {
            type string;
          }
        }
        container service-policy {
          uses ncs_template_service-policy-grouping;
        }
      }
    }
    container class {
      list cem {
        // NCS patched for predictable order
        ordered-by user;
        key "name";
        leaf name {
          type string;
        }
        leaf payload-size {
          type string;
        }
        leaf dejitter-buffer {
          type string;
        }
        leaf idle-pattern {
          type string;
        }
      }
    }
    list class-map {
      // NCS patched for predictable order
      ordered-by user;
      // NCS drop tailf-common:cli-diff-dependency statement
      key "name";
      leaf name {
        type string;
      }
      leaf type {
        type string;
      }
      leaf protocol {
        // NCS drop when statement
        type string;
      }
      leaf prematch {
        type string;
      }
      leaf description {
        type string;
      }
      container match {
        uses ncs_template_class-map-match-grouping;
        container not {
          uses ncs_template_class-map-match-grouping;
        }
      }
    }
    container class-map-filter-control {
      list class-map {
        // NCS patched for predictable order
        ordered-by user;
        key "name";
        leaf name {
          type string;
        }
        leaf type {
          type string;
        }
        leaf domain {
          type string;
        }
        leaf prematch {
          type string;
        }
        container match {
          container method {
            leaf webauth {
              type empty;
            }
            leaf mab {
              type empty;
            }
            leaf dot1x {
              type empty;
            }
          }
          container result-type {
            container method {
              container dot1x {
                uses ncs_template_result-type-method-grouping;
              }
              container mab {
                uses ncs_template_result-type-method-grouping;
              }
              container webauth {
                uses ncs_template_result-type-method-grouping;
              }
            }
          }
        }
      }
    }
    list policy-map {
      // NCS patched for predictable order
      ordered-by user;
      // NCS drop tailf-common:cli-diff-dependency statement
      // NCS drop tailf-common:cli-diff-dependency statement
      // NCS drop tailf-common:cli-diff-dependency statement
      key "name";
      leaf name {
        type string;
      }
      leaf type {
        type string;
      }
      leaf protocol {
        type string;
      }
      leaf description {
        type string;
      }
      list class {
        // NCS patched for predictable order
        ordered-by user;
        // NCS drop tailf-common:cli-diff-dependency statement
        key "name";
        leaf type {
          type string;
        }
        leaf name {
          type string;
        }
        uses ncs_template_policy-map-class-grouping;
      }
      container class-default {
        list class {
          // NCS patched for predictable order
          ordered-by user;
          key "name";
          leaf name {
            type string;
          }
          uses ncs_template_policy-map-class-grouping;
        }
      }
    }
    container policy-map-event-control {
      list policy-map {
        // NCS patched for predictable order
        ordered-by user;
        key "name";
        leaf name {
          // NCS drop tailf-common:cli-diff-dependency statement
          // NCS drop tailf-common:cli-diff-dependency statement
          type string;
        }
        leaf type {
          type string;
        }
        leaf domain {
          type string;
        }
        list event {
          // NCS patched for predictable order
          ordered-by user;
          key "name match";
          leaf name {
            type string;
          }
          leaf match {
            type string;
          }
          list class-list {
            // NCS patched for predictable order
            ordered-by user;
            key "id";
            leaf id {
              type string;
            }
            leaf class {
              type string;
            }
            leaf execute {
              type string;
            }
            list action-list {
              // NCS patched for predictable order
              ordered-by user;
              key "id";
              leaf id {
                type string;
              }
              leaf action {
                type string;
              }
              leaf action-string {
                type string;
              }
            }
          }
        }
      }
    }
    container dot11 {
      leaf syslog {
        type empty;
      }
      list ssid {
        // NCS patched for predictable order
        ordered-by user;
        key "id";
        leaf id {
          type string;
        }
        leaf vlan {
          type string;
        }
        container authentication {
          container open {
            presence "true";
            choice open-choice {
              leaf mac-address {
                type string;
              }
              leaf eap {
                type string;
              }
            }
          }
          leaf network-eap {
            type string;
          }
          container key-management {
            container wpa {
              presence "true";
              leaf version {
                type string;
              }
              leaf optional {
                type empty;
              }
            }
          }
        }
        leaf guest-mode {
          type empty;
        }
        container mbssid {
          leaf guest-mode {
            type empty;
          }
        }
        container wpa-psk {
          choice wpa-psk-choice {
            container ascii {
              uses ncs_template_password-grouping;
            }
            container hex {
              uses ncs_template_password-grouping;
            }
          }
        }
      }
      container arp-cache {
        presence "true";
        leaf optional {
          type empty;
        }
      }
    }
    container bridge {
      leaf irb {
        type empty;
      }
      list bridge-list {
        // NCS patched for predictable order
        ordered-by user;
        key "id";
        leaf id {
          type string;
        }
        leaf protocol {
          type string;
        }
        container route {
          leaf ip {
            type empty;
          }
        }
      }
    }
    container bridge-domain {
      list bridge-domain-list {
        // NCS patched for predictable order
        ordered-by user;
        // NCS drop tailf-common:cli-diff-dependency statement
        key "id";
        leaf id {
          type string;
        }
        container member {
          leaf vfi {
            type string;
          }
          list interface-list {
            // NCS patched for predictable order
            ordered-by user;
            key "name service-instance";
            leaf name {
              // NCS drop tailf-common:cli-diff-dependency statement
              type string;
            }
            leaf service-instance {
              type string;
            }
          }
          list ip-list {
            // NCS patched for predictable order
            ordered-by user;
            key "address";
            leaf address {
              type string;
            }
            leaf vcid {
              type string;
            }
            choice encapsulation-template-choice {
              container encapsulation {
                leaf mpls {
                  type empty;
                }
              }
              leaf template {
                type string;
              }
            }
          }
        }
        container mac {
          container limit {
            container maximum {
              leaf addresses {
                type string;
              }
            }
          }
          leaf aging-time {
            type string;
          }
        }
      }
    }
    list service-group {
      // NCS patched for predictable order
      ordered-by user;
      key "id";
      leaf id {
        type string;
      }
      leaf description {
        type string;
      }
      container service-policy {
        uses ncs_template_service-policy-grouping;
      }
    }
    container service-instance {
      container mdns-sd {
        list service {
          // NCS patched for predictable order
          ordered-by user;
          key "name regtype domain";
          leaf name {
            type string;
          }
          leaf regtype {
            type string;
          }
          leaf domain {
            type string;
          }
          leaf target-hostname {
            type string;
          }
          leaf priority {
            type string;
          }
          leaf weight {
            type string;
          }
          leaf port {
            type string;
          }
          leaf txt {
            type string;
          }
          leaf ipv4addr {
            type string;
          }
          leaf ipv6addr {
            type string;
          }
        }
      }
    }
    container service-insertion {
      // NCS drop tailf-common:cli-diff-dependency statement
      // NCS drop tailf-common:cli-diff-dependency statement
      list service-node-group {
        // NCS patched for predictable order
        ordered-by user;
        key "name";
        leaf name {
          type string;
        }
        leaf description {
          type string;
        }
        list service-node {
          // NCS patched for predictable order
          ordered-by user;
          key "ip-address";
          leaf ip-address {
            type string;
          }
        }
        leaf node-discovery {
          type string;
        }
      }
      list appnav-controller-group {
        // NCS patched for predictable order
        ordered-by user;
        key "name";
        leaf name {
          type string;
        }
        leaf description {
          type string;
        }
        list appnav-controller {
          // NCS patched for predictable order
          ordered-by user;
          key "ip-address";
          leaf ip-address {
            // NCS drop tailf-common:cli-diff-dependency statement
            type string;
          }
        }
      }
      list service-context {
        // NCS patched for predictable order
        ordered-by user;
        key "name";
        leaf name {
          type string;
        }
        leaf appnav-controller-group {
          type string;
        }
        leaf service-node-group {
          type string;
        }
        leaf service-policy {
          type string;
        }
        container vrf {
          choice c-type {
            leaf name {
              type string;
            }
            leaf default {
              type empty;
            }
            leaf global {
              type empty;
            }
          }
        }
        leaf enable {
          type empty;
        }
      }
    }
    container vtp {
      leaf file {
        type string;
      }
      leaf interface {
        // NCS drop tailf-common:cli-diff-dependency statement
        type string;
      }
      leaf password {
        type string;
      }
      leaf pruning {
        type empty;
      }
      leaf version {
        type string;
      }
      leaf domain {
        type string;
      }
      leaf mode {
        type string;
      }
    }
    container link {
      container state {
        leaf-list track {
          // NCS patched for predictable order
          ordered-by user;
          type string;
        }
      }
    }
    container vlan {
      choice vlan-accounting-choice {
        leaf accounting {
          type string;
          // NCS drop default statement
        }
        container accounting-input {
          container accounting {
            leaf input {
              type string;
              // NCS drop default statement
            }
          }
        }
        container accounting-output {
          container accounting {
            leaf output {
              type string;
              // NCS drop default statement
            }
          }
        }
      }
      container internal {
        container allocation {
          leaf policy {
            type string;
          }
        }
      }
      container dot1q {
        container tag {
          leaf native {
            type empty;
          }
        }
      }
      container access-log {
        leaf maxflow {
          type string;
        }
        leaf ratelimit {
          type string;
        }
        leaf threshold {
          type string;
        }
      }
      list filter {
        // NCS patched for predictable order
        ordered-by user;
        key "name";
        leaf name {
          type string;
        }
        leaf-list vlan-list {
          // NCS patched for predictable order
          ordered-by user;
          type string;
        }
      }
      list vlan-list {
        // NCS patched for predictable order
        ordered-by user;
        key "id";
        leaf id {
          type string;
        }
        leaf name {
          // NCS drop tailf-common:cli-diff-dependency statement
          type string;
        }
        leaf state {
          type string;
        }
        leaf mtu {
          type string;
        }
        leaf remote-span {
          type empty;
        }
        leaf uni-vlan {
          type string;
        }
      }
      list configuration {
        // NCS patched for predictable order
        ordered-by user;
        key "id";
        leaf id {
          type string;
        }
        container service-policy {
          uses ncs_template_service-policy-grouping;
        }
      }
      list access-map {
        // NCS patched for predictable order
        ordered-by user;
        key "name number";
        leaf name {
          type string;
        }
        leaf number {
          type string;
        }
        leaf action {
          type string;
        }
        container match {
          container mac {
            leaf-list address {
              // NCS patched for predictable order
              ordered-by user;
              type string;
            }
          }
          container ip {
            leaf-list address {
              // NCS patched for predictable order
              ordered-by user;
              type string;
            }
          }
        }
      }
    }
    container lldp {
      leaf run {
        type empty;
      }
    }
    container EXEC;
    container pm-agent {
      presence "true";
      container tenant {
        leaf id {
          type string;
        }
        leaf name {
          type string;
        }
      }
      container region {
        leaf id {
          type string;
        }
        leaf name {
          type string;
        }
      }
      container site {
        leaf id {
          type string;
        }
        leaf name {
          type string;
        }
      }
      container device {
        container id {
          leaf id {
            type string;
          }
          leaf name {
            type string;
          }
        }
        leaf type {
          type string;
        }
      }
      container pmcs {
        list ipv4 {
          // NCS patched for predictable order
          ordered-by user;
          key "address";
          leaf address {
            type string;
          }
        }
        list ipv6 {
          // NCS patched for predictable order
          ordered-by user;
          key "address";
          leaf address {
            type string;
          }
        }
      }
      list instance-id {
        // NCS patched for predictable order
        ordered-by user;
        key "id";
        leaf id {
          type string;
        }
        container enterprise-prefix {
          leaf prefix-list {
            type string;
          }
          container ipv4 {
            leaf prefix-list {
              type string;
            }
          }
          container ipv6 {
            leaf prefix-list {
              type string;
            }
          }
        }
      }
      leaf shutdown {
        type empty;
      }
    }
    container crypto {
      list keyring {
        // NCS patched for predictable order
        ordered-by user;
        key "name";
        leaf name {
          type string;
        }
        leaf vrf {
          // NCS drop tailf-common:cli-diff-dependency statement
          // NCS drop tailf-common:cli-diff-dependency statement
          type string;
        }
        container pre-shared-key {
          list address {
            // NCS patched for predictable order
            ordered-by user;
            key "address";
            leaf address {
              type string;
            }
            leaf mask {
              type string;
            }
            container key {
              uses ncs_template_crypto-key-grouping;
            }
          }
        }
      }
      container logging {
        leaf session {
          type empty;
        }
        leaf ikev2 {
          type empty;
        }
      }
      container ikev2 {
        list name-mangler {
          // NCS patched for predictable order
          ordered-by user;
          key "name";
          leaf name {
            type string;
          }
          leaf fqdn {
            type string;
          }
        }
        container authorization {
          list policy {
            // NCS patched for predictable order
            ordered-by user;
            key "name";
            leaf name {
              type string;
            }
            leaf pool {
              type string;
            }
            leaf netmask {
              type string;
            }
            container aaa {
              container attribute {
                leaf list {
                  type string;
                }
              }
            }
            container route {
              container set {
                container access-list {
                  leaf ipv4 {
                    type string;
                  }
                  leaf ipv6 {
                    type string;
                  }
                }
                container interface {
                  presence "true";
                  list interface-list {
                    // NCS patched for predictable order
                    ordered-by user;
                    key "name";
                    leaf name {
                      type string;
                    }
                  }
                }
              }
              container accept {
                container any {
                  choice any-choice {
                    leaf distance {
                      type string;
                      // NCS drop default statement
                    }
                    leaf tag {
                      type string;
                    }
                  }
                }
              }
            }
            leaf session-lifetime {
              type string;
            }
          }
        }
        container redirect {
          container client {
            presence "true";
            leaf max-redirects {
              type string;
              // NCS drop default statement
            }
          }
        }
        list keyring {
          // NCS patched for predictable order
          ordered-by user;
          key "name";
          leaf name {
            type string;
          }
          list peer {
            // NCS patched for predictable order
            ordered-by user;
            key "name";
            leaf name {
              type string;
            }
            leaf description {
              type string;
            }
            container address {
              choice address-choice {
                case ipv4 {
                  leaf ipv4-address {
                    type string;
                  }
                  leaf ipv4-mask {
                    type string;
                    // NCS drop default statement
                  }
                }
                case ipv6 {
                  leaf ipv6-address {
                    type string;
                  }
                }
              }
            }
            container identity {
              choice identity-choice {
                leaf key-id {
                  type string;
                }
                container fqdn {
                  leaf domain {
                    type empty;
                  }
                  leaf name {
                    type string;
                  }
                }
              }
            }
            container pre-shared-key {
              choice pre-shared-key-choice {
                case one-case {
                  uses ncs_template_crypto-key-grouping;
                }
                case local-remote-case {
                  container local {
                    uses ncs_template_crypto-key-grouping;
                  }
                  container remote {
                    uses ncs_template_crypto-key-grouping;
                  }
                }
              }
            }
          }
        }
        list proposal {
          // NCS patched for predictable order
          ordered-by user;
          key "name";
          leaf name {
            type string;
          }
          leaf-list encryption {
            // NCS patched for predictable order
            ordered-by user;
            type string;
          }
          leaf-list integrity {
            // NCS patched for predictable order
            ordered-by user;
            type string;
          }
          leaf-list group {
            // NCS patched for predictable order
            ordered-by user;
            type string;
          }
        }
        list policy {
          // NCS patched for predictable order
          ordered-by user;
          key "name";
          leaf name {
            type string;
          }
          leaf proposal {
            type string;
          }
          container match {
            leaf fvrf {
              // NCS drop tailf-common:cli-diff-dependency statement
              type string;
            }
            container address {
              list local {
                // NCS patched for predictable order
                ordered-by user;
                key "address";
                leaf address {
                  type string;
                }
              }
            }
          }
        }
        list profile {
          // NCS patched for predictable order
          ordered-by user;
          key "name";
          leaf name {
            type string;
          }
          leaf description {
            type string;
          }
          container match {
            container address {
              list local {
                // NCS patched for predictable order
                ordered-by user;
                key "address";
                leaf address {
                  type string;
                }
              }
            }
            leaf fvrf {
              // NCS drop tailf-common:cli-diff-dependency statement
              type string;
            }
            container identity {
              container remote {
                leaf any {
                  type empty;
                }
                list key-id {
                  // NCS patched for predictable order
                  ordered-by user;
                  key "name";
                  leaf name {
                    type string;
                  }
                }
                container fqdn {
                  list fqdn-list {
                    // NCS patched for predictable order
                    ordered-by user;
                    key "name";
                    leaf name {
                      type string;
                    }
                  }
                  list domain {
                    // NCS patched for predictable order
                    ordered-by user;
                    key "name";
                    leaf name {
                      type string;
                    }
                  }
                }
                list address {
                  // NCS patched for predictable order
                  ordered-by user;
                  key "name";
                  leaf name {
                    type string;
                  }
                  leaf mask {
                    type string;
                  }
                }
              }
            }
          }
          container identity {
            container local {
              choice local-choice {
                leaf dn {
                  type empty;
                }
                leaf email {
                  type string;
                }
                leaf fqdn {
                  type string;
                }
                leaf address {
                  type string;
                }
              }
            }
          }
          container authentication {
            container local {
              choice method-choice {
                container eap {
                  presence "true";
                }
                leaf ecdsa-sig {
                  type empty;
                }
                container pre-share {
                  presence "true";
                  container key {
                    uses ncs_template_crypto-key-grouping;
                  }
                }
                leaf rsa-sig {
                  type empty;
                }
              }
            }
            container remote {
              presence "true";
              choice method-choice {
                container eap {
                  presence "true";
                  leaf query-identity {
                    type empty;
                  }
                }
                leaf ecdsa-sig {
                  type empty;
                }
                container pre-share {
                  presence "true";
                  container key {
                    uses ncs_template_crypto-key-grouping;
                  }
                }
                leaf rsa-sig {
                  type empty;
                }
              }
            }
          }
          container pki {
            leaf-list trustpoint {
              // NCS patched for predictable order
              ordered-by user;
              type string;
            }
          }
          container keyring {
            choice keyring-choice {
              container aaa {
                leaf name {
                  type string;
                }
                leaf name-mangler {
                  type string;
                }
              }
              leaf local {
                type string;
              }
            }
          }
          container nat {
            leaf keepalive {
              type string;
            }
          }
          container aaa {
            container authentication {
              leaf eap {
                type string;
              }
            }
            container authorization {
              container group {
                container psk {
                  uses ncs_template_crypto-ikev2-profile-aaa-authorization-group-list {
                    refine "list/password/secret";
                  }
                }
                container eap {
                  uses ncs_template_crypto-ikev2-profile-aaa-authorization-group-list {
                    refine "list/password/secret";
                  }
                }
              }
              container user {
                container psk {
                  leaf cached {
                    type empty;
                  }
                  leaf list {
                    type string;
                  }
                }
              }
            }
          }
          container virtual-template {
            leaf number {
              type string;
            }
            leaf mode {
              type string;
            }
          }
          leaf lifetime {
            type string;
            // NCS drop default statement
          }
          container dpd {
            leaf interval {
              type string;
            }
            leaf retry-interval {
              type string;
            }
            leaf queries {
              type string;
            }
          }
        }
        container fragmentation {
          presence "true";
          leaf mtu {
            type string;
          }
        }
        container http-url {
          leaf cert {
            type string;
            // NCS drop default statement
          }
        }
        container client {
          list flexvpn {
            // NCS patched for predictable order
            ordered-by user;
            key "name";
            leaf name {
              type string;
            }
            container peer {
              list peer-list {
                // NCS patched for predictable order
                ordered-by user;
                key "sequence";
                leaf sequence {
                  type string;
                }
                choice address-choice {
                  leaf ipv4-address {
                    type string;
                  }
                  leaf ipv6-address {
                    type string;
                  }
                  case fqdn {
                    leaf fqdn {
                      type string;
                    }
                    leaf dynamic {
                      type empty;
                    }
                    leaf ipv6 {
                      type empty;
                    }
                  }
                }
                leaf track {
                  type string;
                }
              }
              leaf reactivate {
                type empty;
              }
            }
            list source {
              // NCS patched for predictable order
              ordered-by user;
              key "seq";
              leaf seq {
                type string;
              }
              container interface {
                uses ncs_template_interface-name-grouping;
              }
              leaf track {
                type string;
              }
            }
            container client {
              container connect {
                leaf Tunnel {
                  type string;
                }
              }
            }
          }
        }
        container dpd {
          leaf interval {
            type string;
          }
          leaf retry-interval {
            type string;
          }
          leaf mode {
            type string;
          }
        }
      }
      container pki {
        list server {
          // NCS patched for predictable order
          ordered-by user;
          // NCS drop max-elements statement
          key "cs-label";
          leaf cs-label {
            type string;
          }
          leaf shutdown {
            type empty;
          }
          container database {
            container archive {
              leaf format {
                type string;
              }
              container password {
                leaf type {
                  type string;
                }
                leaf secret {
                  type string;
                }
              }
            }
          }
          leaf grant {
            type string;
          }
          leaf hash {
            type string;
          }
        }
        list trustpoint {
          // NCS patched for predictable order
          ordered-by user;
          key "id";
          leaf id {
            type string;
          }
          container serial-number {
            presence "true";
            leaf none {
              type empty;
            }
          }
          leaf ip-address {
            // NCS drop tailf-common:cli-diff-dependency statement
            type string;
          }
          container enrollment {
            leaf http-proxy {
              type string;
            }
            container mode {
              leaf ra {
                type empty;
              }
            }
            leaf pkcs12 {
              type empty;
            }
            leaf profile {
              type string;
            }
            container retry {
              leaf count {
                type string;
              }
              leaf period {
                type string;
              }
            }
            leaf selfsigned {
              type empty;
            }
            container terminal {
              presence "true";
              leaf pem {
                type empty;
              }
            }
            leaf url {
              type string;
            }
          }
          container password {
            uses ncs_template_password-grouping;
          }
          leaf subject-name {
            type string;
          }
          leaf fqdn {
            type string;
          }
          container usage {
            leaf ike {
              type empty;
            }
            leaf ssl-server {
              type empty;
            }
            leaf ssl-client {
              type empty;
            }
          }
          leaf-list revocation-check {
            // NCS patched for predictable order
            ordered-by user;
            type string;
          }
          container source {
            container interface {
              uses ncs_template_interface-name-grouping;
            }
          }
          container rsakeypair {
            leaf key-label {
              type string;
            }
            leaf key-size {
              type string;
            }
            leaf encryption-key-size {
              type string;
            }
          }
          container auto-enroll {
            presence "true";
            leaf percent {
              type string;
            }
            leaf regenerate {
              type empty;
            }
          }
        }
        container certificate {
          list chain {
            // NCS patched for predictable order
            ordered-by user;
            key "name";
            leaf name {
              // NCS drop tailf-common:cli-diff-dependency statement
              type string;
            }
            list certificate {
              // NCS patched for predictable order
              ordered-by user;
              key "serial";
              leaf serial {
                type string;
              }
              leaf cert-type {
                type string;
              }
              leaf rollover {
                type empty;
              }
              leaf cert {
                type string;
              }
            }
          }
        }
        container token {
          list token-name {
            // NCS patched for predictable order
            ordered-by user;
            key "name";
            leaf name {
              type string;
            }
            uses ncs_template_crypto-pki-token-grouping;
          }
        }
        container default {
          uses ncs_template_crypto-pki-token-grouping;
        }
      }
      container isakmp {
        container default {
          leaf policy {
            type string;
            // NCS drop default statement
          }
        }
        leaf enable {
          type string;
          // NCS drop default statement
        }
        leaf identity {
          type string;
          // NCS drop default statement
        }
        leaf fragmentation {
          type empty;
        }
        leaf invalid-spi-recovery {
          type empty;
        }
        container client {
          container configuration {
            list group {
              // NCS patched for predictable order
              ordered-by user;
              key "name";
              leaf name {
                type string;
              }
              container key {
                uses ncs_template_crypto-key-grouping {
                  refine "secret";
                }
              }
              leaf pool {
                type string;
              }
              leaf netmask {
                type string;
              }
            }
          }
        }
        list profile {
          // NCS patched for predictable order
          ordered-by user;
          key "name";
          leaf name {
            type string;
          }
          leaf description {
            type string;
          }
          leaf vrf {
            // NCS drop tailf-common:cli-diff-dependency statement
            // NCS drop tailf-common:cli-diff-dependency statement
            type string;
          }
          list keyring {
            // NCS patched for predictable order
            ordered-by user;
            key "name";
            leaf name {
              // NCS drop tailf-common:cli-diff-dependency statement
              type string;
            }
          }
          container self-identity {
            choice self-identity-choice {
              container address {
                presence "true";
              }
              container fqdn {
                presence "true";
              }
              leaf user-fqdn {
                type string;
              }
            }
          }
          container match {
            leaf fvrf {
              // NCS drop tailf-common:cli-diff-dependency statement
              type string;
            }
            container identity {
              list group {
                // NCS patched for predictable order
                ordered-by user;
                key "name";
                leaf name {
                  type string;
                }
              }
              container address {
                list ipv4 {
                  // NCS patched for predictable order
                  ordered-by user;
                  key "address mask";
                  leaf address {
                    type string;
                  }
                  leaf mask {
                    type string;
                  }
                  leaf vrf {
                    // NCS drop tailf-common:cli-diff-dependency statement
                    // NCS drop tailf-common:cli-diff-dependency statement
                    type string;
                  }
                }
                container ipv4-host {
                  list ipv4 {
                    // NCS patched for predictable order
                    ordered-by user;
                    key "address";
                    leaf address {
                      type string;
                    }
                    leaf vrf {
                      // NCS drop tailf-common:cli-diff-dependency statement
                      // NCS drop tailf-common:cli-diff-dependency statement
                      type string;
                    }
                  }
                }
                list ipv6 {
                  // NCS patched for predictable order
                  ordered-by user;
                  key "address";
                  leaf address {
                    type string;
                  }
                  leaf vrf {
                    // NCS drop tailf-common:cli-diff-dependency statement
                    // NCS drop tailf-common:cli-diff-dependency statement
                    type string;
                  }
                }
              }
              container host {
                leaf domain-name {
                  type string;
                }
                list domain-name-vrf {
                  // NCS patched for predictable order
                  ordered-by user;
                  key "domain";
                  leaf domain {
                    type string;
                  }
                  leaf vrf {
                    // NCS drop tailf-common:cli-diff-dependency statement
                    // NCS drop tailf-common:cli-diff-dependency statement
                    type string;
                  }
                }
                container domain {
                  list domain-name-vrf {
                    // NCS patched for predictable order
                    ordered-by user;
                    key "domain";
                    leaf domain {
                      type string;
                    }
                    leaf vrf {
                      // NCS drop tailf-common:cli-diff-dependency statement
                      // NCS drop tailf-common:cli-diff-dependency statement
                      type string;
                    }
                  }
                  leaf domain-name {
                    type string;
                  }
                }
              }
            }
          }
          container client {
            container authentication {
              leaf list {
                type string;
              }
            }
            container configuration {
              container address {
                leaf initiate {
                  type empty;
                }
                leaf respond {
                  type empty;
                }
              }
            }
          }
          container isakmp {
            container authorization {
              leaf list {
                type string;
              }
            }
          }
          container keepalive {
            leaf seconds {
              type string;
            }
            leaf retry {
              type string;
            }
          }
          container local-address {
            choice local-address-choice {
              leaf ipv4-address {
                type string;
              }
              leaf ipv6-address {
                type string;
              }
              container interface {
                uses ncs_template_interface-name-grouping;
              }
            }
          }
          leaf virtual-template {
            type string;
          }
          leaf qos-group {
            type string;
          }
        }
        list policy {
          // NCS patched for predictable order
          ordered-by user;
          key "priority";
          leaf priority {
            type string;
          }
          container encr {
            leaf algorithm {
              type string;
              // NCS drop default statement
            }
            leaf bits {
              // NCS drop when statement
              type string;
              // NCS drop default statement
            }
          }
          leaf hash {
            type string;
            // NCS drop default statement
          }
          leaf authentication {
            type string;
          }
          leaf group {
            type string;
          }
          leaf lifetime {
            type string;
            // NCS drop default statement
          }
        }
        container keepalive {
          leaf seconds {
            type string;
          }
          leaf retry-seconds {
            type string;
          }
          leaf option {
            type string;
            // NCS drop default statement
          }
        }
        container nat {
          container keepalive {
            leaf seconds {
              type string;
            }
          }
        }
        list key {
          // NCS patched for predictable order
          ordered-by user;
          key "address";
          leaf address {
            type string;
          }
          leaf encrypted {
            type string;
          }
          leaf keystring {
            type string;
          }
          leaf mask {
            type string;
          }
          leaf no-xauth {
            type empty;
          }
        }
        container key-ipv6-list {
          list key {
            // NCS patched for predictable order
            ordered-by user;
            key "ipv6";
            leaf ipv6 {
              type string;
            }
            leaf encrypted {
              type string;
            }
            leaf keystring {
              type string;
            }
            leaf address {
              type empty;
            }
            leaf no-xauth {
              type empty;
            }
          }
        }
        container key-hostname-list {
          list key {
            // NCS patched for predictable order
            ordered-by user;
            key "hostname";
            leaf hostname {
              type string;
            }
            leaf encrypted {
              type string;
            }
            leaf keystring {
              type string;
            }
            leaf no-xauth {
              type empty;
            }
          }
        }
      }
      container ipsec {
        container optional {
          presence "true";
          leaf retry {
            type string;
          }
        }
        container security-association {
          leaf idle-time {
            type string;
          }
          container lifetime {
            leaf kilobytes {
              type string;
            }
            leaf seconds {
              type string;
            }
          }
          container replay {
            leaf disable {
              type empty;
            }
            leaf window-size {
              type string;
            }
          }
        }
        list transform-set {
          // NCS patched for predictable order
          ordered-by user;
          key "name";
          leaf name {
            type string;
          }
          leaf transform1 {
            type string;
          }
          leaf transform2 {
            type string;
          }
          leaf transform2-bits {
            type string;
            // NCS drop default statement
          }
          leaf transform3 {
            type string;
          }
          leaf transform4 {
            type string;
          }
          container mode {
            choice mode-choice {
              container transport {
                presence "true";
                leaf require {
                  type empty;
                }
              }
              leaf tunnel {
                type empty;
              }
              // NCS drop default statement
            }
          }
        }
        container default {
          leaf transform-set {
            type string;
            // NCS drop default statement
          }
        }
        leaf fragmentation {
          type string;
        }
        leaf df-bit {
          type string;
        }
        leaf nat-transparency {
          type string;
        }
        list profile {
          // NCS patched for predictable order
          ordered-by user;
          key "name";
          leaf name {
            type string;
          }
          container set {
            container security-association {
              leaf dfbit {
                type string;
              }
              container lifetime {
                leaf kilobytes {
                  type string;
                }
                choice time-based-choice {
                  // NCS drop default statement
                  leaf seconds {
                    type string;
                    // NCS drop default statement
                  }
                  leaf days {
                    type string;
                  }
                }
              }
              container idle-time {
                leaf seconds {
                  type string;
                }
                leaf default {
                  type empty;
                }
              }
              container replay {
                leaf disable {
                  type empty;
                }
                leaf window-size {
                  type string;
                }
              }
              container dummy {
                choice dummy-choice {
                  leaf pps {
                    type string;
                  }
                  leaf seconds {
                    type string;
                  }
                }
              }
              leaf ecn {
                type string;
              }
            }
            leaf transform-set {
              type string;
            }
            leaf pfs {
              type string;
            }
            leaf identity {
              type string;
            }
            leaf mixed-mode {
              type empty;
            }
            choice ike-profile {
              leaf isakmp-profile {
                type string;
              }
              leaf ikev2-profile {
                type string;
              }
            }
          }
          leaf responder-only {
            type empty;
          }
        }
      }
      container call {
        container admission {
          container limit {
            container ike {
              leaf in-negotiation-sa {
                type string;
              }
            }
          }
        }
      }
      container gdoi {
        list group {
          // NCS patched for predictable order
          ordered-by user;
          key "name";
          leaf name {
            type string;
          }
          leaf ipv6 {
            type empty;
          }
          container identity {
            choice identify-choice {
              leaf number {
                type string;
              }
              container address {
                leaf ipv4 {
                  type string;
                }
              }
            }
          }
          container server {
            container local {
              presence "true";
              // NCS drop must statement
              // NCS drop tailf-common:cli-diff-dependency statement
              container rekey {
                container lifetime {
                  choice lifetime-choice {
                    leaf seconds {
                      type string;
                      // NCS drop default statement
                    }
                    leaf days {
                      type string;
                    }
                    // NCS drop default statement
                  }
                }
                container retransmit {
                  leaf number-of-seconds {
                    type string;
                  }
                  choice retransmit-choice {
                    leaf number {
                      type string;
                    }
                    leaf periodic {
                      type empty;
                    }
                  }
                }
                container authentication {
                  choice authentication-choice {
                    leaf mypubkey {
                      type empty;
                    }
                    leaf pubkey {
                      type empty;
                    }
                  }
                  leaf rsa {
                    type string;
                  }
                }
                container transport {
                  leaf unicast {
                    type empty;
                  }
                }
              }
              container replay {
                container time {
                  leaf window-size {
                    type string;
                  }
                }
              }
              container sa {
                list ipsec {
                  // NCS patched for predictable order
                  ordered-by user;
                  key "id";
                  leaf id {
                    type string;
                  }
                  leaf profile {
                    type string;
                  }
                  container match {
                    container address {
                      choice address-choice {
                        leaf ipv4 {
                          type string;
                        }
                        leaf ipv6 {
                          type string;
                        }
                      }
                    }
                  }
                  container replay {
                    container counter {
                      leaf window-size {
                        type string;
                      }
                    }
                  }
                  container tag {
                    container cts {
                      leaf sgt {
                        type empty;
                      }
                    }
                  }
                }
              }
              container address {
                leaf ipv4 {
                  type string;
                }
              }
              container redundancy {
                container local {
                  presence "true";
                  leaf priority {
                    type string;
                  }
                }
                container peer {
                  container address {
                    leaf ipv4 {
                      type string;
                    }
                  }
                }
              }
            }
            container address {
              list ipv4 {
                // NCS patched for predictable order
                ordered-by user;
                // NCS drop must statement
                // NCS drop tailf-common:cli-diff-dependency statement
                key "name";
                leaf name {
                  type string;
                }
              }
            }
          }
          container client {
            container registration {
              container interface {
                uses ncs_template_interface-name-grouping;
              }
            }
          }
        }
      }
      list dynamic-map {
        // NCS patched for predictable order
        ordered-by user;
        key "name map-entry";
        leaf name {
          type string;
        }
        leaf map-entry {
          type string;
        }
        container set {
          leaf isakmp-profile {
            type string;
          }
          leaf-list transform-set {
            // NCS patched for predictable order
            ordered-by user;
            type string;
          }
        }
        container match {
          leaf address {
            type string;
          }
        }
      }
      list map {
        // NCS patched for predictable order
        ordered-by user;
        key "name";
        leaf name {
          type string;
        }
        leaf ipv6 {
          type empty;
        }
        container local-address {
          uses ncs_template_interface-name-grouping;
        }
        container gdoi {
          container fail-close {
            presence "true";
            container match {
              leaf address {
                type string;
              }
            }
            leaf activate {
              type empty;
            }
          }
        }
        list seq-list {
          // NCS patched for predictable order
          ordered-by user;
          key "id";
          leaf id {
            type string;
          }
          leaf policy {
            type string;
          }
          leaf dynamic {
            // NCS drop when statement
            type string;
          }
          leaf profile {
            // NCS drop when statement
            type string;
          }
          leaf description {
            type string;
          }
          container set {
            // NCS drop when statement
            leaf-list transform-set {
              // NCS patched for predictable order
              ordered-by user;
              // NCS drop max-elements statement
              type string;
            }
            leaf isakmp-profile {
              type string;
            }
            leaf-list peer {
              // NCS patched for predictable order
              ordered-by user;
              type string;
            }
            container security-association {
              container level {
                leaf per-host {
                  type empty;
                }
              }
              leaf dfbit {
                type string;
              }
              container lifetime {
                leaf kilobytes {
                  type string;
                }
                choice days-seconds-choice {
                  leaf days {
                    type string;
                  }
                  leaf seconds {
                    type string;
                    // NCS drop default statement
                  }
                }
              }
              container idle-time {
                leaf seconds {
                  type string;
                }
                leaf default {
                  type empty;
                }
              }
              container replay {
                leaf disable {
                  type empty;
                }
                leaf window-size {
                  type string;
                  // NCS drop default statement
                }
              }
              container dummy {
                choice dummy-choice {
                  leaf pps {
                    type string;
                  }
                  leaf seconds {
                    type string;
                  }
                }
              }
              leaf ecn {
                type string;
              }
            }
            leaf pfs {
              type string;
            }
            container reverse-route {
              leaf distance {
                type string;
                // NCS drop default statement
              }
              leaf tag {
                type string;
              }
            }
            leaf group {
              type string;
            }
          }
          container gdoi-set {
            // NCS drop when statement
            container set {
              leaf group {
                type string;
              }
            }
          }
          container match {
            leaf address {
              type string;
            }
          }
          container reverse-route {
            presence "true";
            leaf remote-peer {
              type string;
            }
            leaf gateway {
              // NCS drop when statement
              type empty;
            }
            leaf static {
              type empty;
            }
          }
          container qos {
            leaf pre-classify {
              type empty;
            }
          }
        }
      }
      container gkm {
        list group {
          // NCS patched for predictable order
          ordered-by user;
          key "name";
          leaf name {
            type string;
          }
          container identity {
            choice identity-choice {
              leaf number {
                type string;
              }
              container address {
                leaf ipv4 {
                  type string;
                }
              }
            }
          }
          container server {
            list address {
              // NCS patched for predictable order
              ordered-by user;
              key "protocol address";
              leaf protocol {
                type string;
              }
              leaf address {
                type string;
              }
            }
          }
          container client {
            container protocol {
              leaf gikev2 {
                type string;
              }
            }
            container registration {
              container interface {
                uses ncs_template_interface-name-grouping;
              }
            }
          }
        }
      }
      container ssl {
        list proposal {
          // NCS patched for predictable order
          ordered-by user;
          key "name";
          leaf name {
            type string;
          }
          leaf-list protection {
            // NCS patched for predictable order
            ordered-by user;
            type string;
          }
        }
        container authorization {
          list policy {
            // NCS patched for predictable order
            ordered-by user;
            key "name";
            leaf name {
              type string;
            }
            leaf pool {
              type string;
            }
            container dns {
              leaf primary-server {
                type string;
              }
              leaf secondary-server {
                type string;
              }
            }
            leaf banner {
              type string;
            }
            leaf def-domain {
              type string;
            }
          }
        }
        list policy {
          // NCS patched for predictable order
          ordered-by user;
          key "name";
          leaf name {
            type string;
          }
          container ssl {
            leaf proposal {
              type string;
            }
          }
          container pki {
            leaf trustpoint {
              type string;
            }
            leaf sign {
              type empty;
            }
          }
          container ip {
            container address {
              leaf local {
                type string;
              }
              leaf port {
                type string;
              }
            }
          }
          leaf shutdown {
            type empty;
          }
        }
        list profile {
          // NCS patched for predictable order
          ordered-by user;
          key "name";
          leaf name {
            type string;
          }
          container match {
            leaf policy {
              type string;
            }
            leaf url {
              type string;
            }
          }
          container aaa {
            container authentication {
              leaf list {
                type string;
              }
            }
            container authorization {
              container user {
                leaf list {
                  type string;
                }
                leaf aaa-username {
                  type string;
                }
              }
            }
          }
          container authentication {
            container remote {
              leaf user-credentials {
                type empty;
              }
            }
          }
          leaf shutdown {
            type empty;
          }
        }
      }
      list tls-tunnel {
        // NCS patched for predictable order
        ordered-by user;
        key "name";
        leaf name {
          type string;
        }
        list server {
          // NCS patched for predictable order
          ordered-by user;
          // NCS drop max-elements statement
          key "protocol address";
          leaf protocol {
            type string;
          }
          leaf address {
            type string;
          }
          leaf port {
            type string;
          }
        }
        leaf protection {
          type string;
          // NCS drop default statement
        }
        list local-interface {
          // NCS patched for predictable order
          ordered-by user;
          key "name";
          leaf name {
            // NCS drop tailf-common:cli-diff-dependency statement
            type string;
          }
          leaf priority {
            type string;
          }
        }
        container psk {
          leaf id {
            type string;
          }
          container key {
            uses ncs_template_crypto-key-grouping;
          }
        }
        container overlay-address {
          // NCS drop tailf-common:cli-diff-dependency statement
          // NCS drop tailf-common:cli-diff-dependency statement
          leaf address {
            type string;
          }
          leaf vrf {
            type string;
          }
        }
        leaf shutdown {
          type empty;
        }
      }
    }
    container transport-map {
      container type {
        list persistent {
          // NCS patched for predictable order
          ordered-by user;
          key "name";
          leaf name {
            type string;
          }
          leaf type {
            type string;
          }
          leaf authentication-retries {
            type string;
          }
          container rsa {
            leaf keypair-name {
              type string;
            }
          }
          container transport {
            container interface {
              uses ncs_template_interface-name-grouping;
            }
          }
        }
      }
    }
    container macro {
      container auto {
        leaf monitor {
          type string;
          // NCS drop default statement
        }
      }
      list name {
        // NCS patched for predictable order
        ordered-by user;
        key "name";
        leaf name {
          type string;
        }
        leaf commands {
          type string;
        }
      }
    }
    container buffers {
      container huge {
        leaf size {
          type string;
        }
      }
    }
    container track {
      list track-object {
        // NCS patched for predictable order
        ordered-by user;
        // NCS drop tailf-common:cli-diff-dependency statement
        // NCS drop tailf-common:cli-diff-dependency statement
        key "object-number";
        leaf object-number {
          type string;
        }
        choice track-type {
          container rtr {
            leaf operation-number {
              type string;
            }
            leaf option {
              type string;
            }
          }
          container list {
            leaf boolean {
              type string;
            }
          }
          container interface {
            uses ncs_template_interface-name-grouping;
            container ip {
              leaf routing {
                type empty;
              }
            }
            leaf line-protocol {
              type empty;
            }
          }
          container ip {
            container route {
              leaf prefix {
                type string;
              }
              leaf mask {
                type string;
              }
              choice option-choice {
                leaf reachability {
                  type empty;
                }
                container metric {
                  leaf threshold {
                    type empty;
                  }
                }
              }
            }
            container sla {
              leaf operation-number {
                type string;
              }
              choice option-choice {
                leaf reachability {
                  type empty;
                }
                leaf state {
                  type empty;
                }
                // NCS drop default statement
              }
            }
          }
          container ipv6 {
            container route {
              leaf prefix {
                type string;
              }
              choice option-choice {
                leaf reachability {
                  type empty;
                }
                container metric {
                  leaf threshold {
                    type empty;
                  }
                }
              }
            }
          }
        }
        list object {
          // NCS patched for predictable order
          ordered-by user;
          // NCS drop when statement
          key "id";
          leaf id {
            type string;
          }
          leaf not {
            type empty;
          }
        }
        container ip-vrf {
          // NCS drop when statement
          container ip {
            leaf vrf {
              type string;
            }
          }
        }
        container ipv6-vrf {
          // NCS drop when statement
          container ipv6 {
            leaf vrf {
              type string;
            }
          }
        }
        container delay {
          leaf down {
            type string;
          }
          leaf up {
            type string;
          }
        }
      }
    }
    container csdb {
      container tcp {
        leaf finwait-time {
          type string;
          // NCS drop default statement
        }
        leaf idle-time {
          type string;
          // NCS drop default statement
        }
        container reassembly {
          leaf max-memory {
            type string;
            // NCS drop default statement
          }
          leaf max-queue-length {
            type string;
            // NCS drop default statement
          }
        }
        leaf synwait-time {
          type string;
          // NCS drop default statement
        }
      }
      container udp {
        leaf idle-time {
          type string;
          // NCS drop default statement
        }
      }
      container icmp {
        leaf idle-time {
          type string;
          // NCS drop default statement
        }
      }
      container session {
        leaf max-session {
          type string;
          // NCS drop default statement
        }
      }
    }
    container ethernet {
      container lmi {
        leaf global {
          type empty;
        }
        leaf ce {
          type empty;
        }
      }
      list evc {
        // NCS patched for predictable order
        ordered-by user;
        key "name";
        leaf name {
          type string;
        }
        container oam {
          container protocol {
            choice protocol-choice {
              leaf ldp {
                type empty;
              }
              container cfm {
                leaf domain {
                  type string;
                }
              }
            }
          }
        }
      }
      container cfm {
        // NCS drop tailf-common:cli-diff-dependency statement
        leaf enable {
          type empty;
        }
        leaf ieee {
          type empty;
        }
        leaf global {
          type empty;
        }
        container logging {
          presence "true";
        }
        container traceroute {
          container cache {
            presence "true";
            leaf size {
              type string;
              // NCS drop default statement
            }
            leaf hold-time {
              type string;
              // NCS drop default statement
            }
          }
        }
        container mip {
          list auto-create {
            // NCS patched for predictable order
            ordered-by user;
            key "evc";
            leaf evc {
              type string;
            }
            leaf level {
              type string;
            }
          }
        }
        list domain {
          // NCS patched for predictable order
          ordered-by user;
          // NCS drop tailf-common:cli-diff-dependency statement
          key "name";
          leaf name {
            type string;
          }
          leaf level {
            type string;
          }
          container mip {
            container auto-create {
              presence "true";
              leaf lower-mep-only {
                type empty;
              }
            }
          }
          container mep {
            leaf archive-hold-time {
              type string;
              // NCS drop default statement
            }
          }
          leaf sender-id {
            type string;
          }
          list service {
            // NCS patched for predictable order
            ordered-by user;
            key "csi-id";
            leaf csi-id {
              type string;
            }
            leaf port {
              type empty;
            }
            leaf evc {
              type string;
            }
            leaf vlan {
              type string;
            }
            leaf direction {
              type string;
            }
            container continuity-check {
              presence "true";
              leaf interval {
                type string;
              }
            }
            leaf sender-id {
              type string;
            }
            container ais {
              leaf period {
                type string;
                // NCS drop default statement
              }
              leaf level {
                type string;
              }
            }
            container efd {
              container notify {
                leaf g8032 {
                  type empty;
                }
              }
            }
          }
        }
        container mep {
          container crosscheck {
            leaf start-delay {
              type string;
            }
          }
        }
      }
      container ring {
        container g8032 {
          list profile {
            // NCS patched for predictable order
            ordered-by user;
            key "profile-name";
            leaf profile-name {
              type string;
            }
            container timer {
              leaf wtr {
                type string;
              }
              leaf guard {
                type string;
              }
            }
          }
          list g8032-list {
            // NCS patched for predictable order
            ordered-by user;
            key "ring-name";
            leaf ring-name {
              type string;
            }
            container exclusion-list {
              leaf-list vlan-ids {
                // NCS patched for predictable order
                ordered-by user;
                type string;
              }
            }
            container port0 {
              container interface {
                uses ncs_template_interface-name-grouping;
              }
              container monitor {
                container service {
                  leaf instance {
                    type string;
                  }
                }
              }
            }
            choice port1-choice {
              container port1 {
                container interface {
                  uses ncs_template_interface-name-grouping;
                }
                container monitor {
                  container service {
                    leaf instance {
                      type string;
                    }
                  }
                }
              }
              container port1-none {
                container port1 {
                  leaf none {
                    type empty;
                  }
                }
              }
            }
            list instance {
              // NCS patched for predictable order
              ordered-by user;
              key "instance-id";
              leaf instance-id {
                type string;
              }
              leaf profile {
                type string;
              }
              container rpl {
                leaf port {
                  type string;
                }
                leaf type {
                  type string;
                }
              }
              container inclusion-list {
                leaf-list vlan-ids {
                  // NCS patched for predictable order
                  ordered-by user;
                  type string;
                }
              }
              container aps-channel {
                container port0 {
                  container service {
                    leaf instance {
                      type string;
                    }
                  }
                }
                container port1 {
                  choice port1-choice {
                    container service {
                      leaf instance {
                        type string;
                      }
                    }
                    leaf none {
                      type empty;
                    }
                  }
                }
              }
            }
          }
        }
      }
      list tcn-propagation {
        // NCS patched for predictable order
        ordered-by user;
        key "source to";
        leaf source {
          type string;
        }
        leaf to {
          type string;
        }
      }
    }
    container performance {
      container monitor {
        list context {
          // NCS patched for predictable order
          ordered-by user;
          key "name";
          leaf name {
            type string;
          }
          leaf profile {
            type string;
          }
          container exporter {
            list destination {
              // NCS patched for predictable order
              ordered-by user;
              key "address source";
              leaf address {
                type string;
              }
              leaf source {
                // NCS drop tailf-common:cli-diff-dependency statement
                type string;
              }
              leaf vrf {
                type string;
              }
              leaf transport {
                type string;
              }
              leaf port {
                type string;
              }
            }
          }
          container traffic-monitor {
            container all {
              presence "true";
              leaf ipv4 {
                type empty;
              }
              leaf ipv6 {
                type empty;
              }
            }
            container url {
              presence "true";
              leaf ipv4 {
                type empty;
              }
              leaf class-replace {
                type string;
              }
              leaf cache-size {
                type string;
              }
            }
            container application-client-server-stats {
              presence "true";
            }
            container application-stats {
              presence "true";
            }
            container application-response-time {
              presence "true";
            }
            container media {
              presence "true";
            }
          }
        }
      }
    }
    container l2 {
      list vfi {
        // NCS patched for predictable order
        ordered-by user;
        key "name";
        leaf name {
          // NCS drop tailf-common:cli-diff-dependency statement
          type string;
        }
        leaf point-to-point {
          type empty;
        }
        leaf manual {
          type empty;
        }
        leaf autodiscovery {
          type empty;
        }
        leaf evc {
          // NCS drop when statement
          type string;
        }
        container vpn {
          leaf id {
            type string;
          }
        }
        leaf bridge-domain {
          type string;
        }
        leaf mtu {
          type string;
        }
        leaf rd {
          type string;
        }
        container route-target {
          // NCS drop tailf-common:cli-diff-dependency statement
          uses ncs_template_route-target-grouping;
        }
        list neighbor {
          // NCS patched for predictable order
          ordered-by user;
          key "id";
          leaf id {
            type string;
          }
          leaf vcid {
            type string;
          }
          leaf encapsulation {
            type string;
          }
          leaf pw-class {
            type string;
          }
          leaf no-split-horizon {
            type empty;
          }
        }
      }
    }
    container interface {
      list Null {
        // NCS patched for predictable order
        ordered-by user;
        key "name";
        leaf name {
          type string;
        }
        container ip {
          leaf unreachables {
            type string;
            // NCS drop default statement
          }
        }
        container ipv6 {
          leaf unreachables {
            type string;
            // NCS drop default statement
          }
        }
      }
      list Loopback {
        // NCS patched for predictable order
        ordered-by user;
        key "name";
        leaf name {
          type string;
        }
        uses ncs_template_interface-common-pre-grouping;
        uses ncs_template_interface-common-grouping;
      }
      list VirtualPortGroup {
        // NCS patched for predictable order
        ordered-by user;
        key "name";
        leaf name {
          type string;
        }
        uses ncs_template_interface-common-pre-grouping;
        uses ncs_template_interface-common-grouping;
        uses ncs_template_interface-pointtopoint-grouping;
      }
      list Dot11Radio {
        // NCS patched for predictable order
        ordered-by user;
        key "name";
        leaf name {
          type string;
        }
        uses ncs_template_interface-common-pre-grouping;
        uses ncs_template_interface-ethernet-pre-grouping;
        uses ncs_template_interface-common-grouping;
        uses ncs_template_interface-ethernet-post-grouping;
        container encryption {
          uses ncs_template_interface-encryption-mode-grouping;
          list vlan {
            // NCS patched for predictable order
            ordered-by user;
            key "id";
            leaf id {
              type string;
            }
            uses ncs_template_interface-encryption-mode-grouping;
          }
        }
        container broadcast-key {
          list vlan {
            // NCS patched for predictable order
            ordered-by user;
            key "name";
            leaf name {
              type string;
            }
            leaf change {
              type string;
            }
          }
        }
        list ssid {
          // NCS patched for predictable order
          ordered-by user;
          key "name";
          leaf name {
            type string;
          }
        }
        container antenna {
          leaf gain {
            type string;
          }
        }
        leaf peakdetect {
          type empty;
        }
        leaf mbssid {
          type empty;
        }
        leaf speed {
          type string;
        }
        container dfs {
          container band {
            choice band-choice {
              leaf block {
                type string;
                // NCS drop default statement
              }
              container block-conf {
                leaf one {
                  tailf:alt-name "1";
                  type empty;
                }
                leaf two {
                  tailf:alt-name "2";
                  type empty;
                }
                leaf three {
                  tailf:alt-name "3";
                  type empty;
                }
                leaf four {
                  tailf:alt-name "4";
                  type empty;
                }
                leaf block {
                  type empty;
                }
              }
            }
          }
        }
        container packet {
          leaf retries {
            type string;
          }
        }
        container channel {
          leaf dfs {
            type empty;
          }
        }
        container channel-conf {
          container channel {
            leaf least-congested {
              type empty;
            }
            leaf-list frequency {
              // NCS patched for predictable order
              ordered-by user;
              type string;
            }
          }
        }
        container station-role {
          container root {
            presence "true";
          }
        }
        container rts {
          leaf threshold {
            type string;
          }
          leaf retries {
            type string;
          }
        }
        container world-mode {
          container dot11d {
            leaf country-code {
              type string;
            }
            leaf location {
              type string;
            }
          }
        }
        leaf infrastructure-client {
          type empty;
        }
      }
      list Embedded-Service-Engine {
        // NCS patched for predictable order
        ordered-by user;
        key "name";
        leaf name {
          type string;
        }
        uses ncs_template_interface-common-pre-grouping;
        uses ncs_template_interface-common-grouping;
      }
      list Service-Engine {
        // NCS patched for predictable order
        ordered-by user;
        key "name";
        leaf name {
          type string;
        }
        uses ncs_template_interface-common-pre-grouping;
        uses ncs_template_interface-common-grouping;
      }
      list Tunnel {
        // NCS patched for predictable order
        ordered-by user;
        key "name";
        leaf name {
          type string;
        }
        uses ncs_template_interface-common-pre-grouping;
        uses ncs_template_interface-common-grouping;
        uses ncs_template_interface-tunnel-grouping;
      }
      list Port-channel {
        // NCS patched for predictable order
        ordered-by user;
        key "name";
        leaf name {
          type string;
        }
        uses ncs_template_interface-common-pre-grouping;
        uses ncs_template_interface-ethernet-pre-grouping;
        uses ncs_template_interface-switch-grouping;
        uses ncs_template_interface-ethernet-switch-grouping;
        uses ncs_template_interface-common-switch-grouping;
        uses ncs_template_interface-ethernet-post-grouping;
        container mlacp {
          container interchassis {
            leaf group {
              type string;
            }
          }
        }
        container port-channel {
          container load-balance {
            leaf flow-based {
              // NCS drop tailf-common:cli-diff-dependency statement
              // NCS drop tailf-common:cli-diff-dependency statement
              type empty;
            }
            leaf link {
              type string;
            }
            container weighted {
              container default {
                leaf weight {
                  type string;
                }
              }
              leaf rebalance {
                type string;
              }
            }
          }
          leaf min-links {
            type string;
          }
        }
      }
      container Port-channel-subinterface {
        list Port-channel {
          // NCS patched for predictable order
          ordered-by user;
          key "name";
          leaf name {
            // NCS drop tailf-common:cli-diff-dependency statement
            type string;
          }
          uses ncs_template_interface-common-pre-grouping;
          uses ncs_template_interface-ethernet-pre-grouping;
          uses ncs_template_sub-interface-switch-grouping;
          uses ncs_template_sub-interface-ethernet-switch-grouping;
          uses ncs_template_sub-interface-common-switch-grouping;
          uses ncs_template_sub-interface-ethernet-post-grouping;
        }
      }
      list Multilink {
        // NCS patched for predictable order
        ordered-by user;
        key "name";
        leaf name {
          type string;
        }
        uses ncs_template_interface-common-pre-grouping;
        uses ncs_template_interface-common-grouping;
        uses ncs_template_interface-pointtopoint-grouping;
      }
      list MFR {
        // NCS patched for predictable order
        ordered-by user;
        key "name";
        leaf name {
          type string;
        }
        uses ncs_template_interface-common-pre-grouping;
        uses ncs_template_interface-common-grouping;
        uses ncs_template_interface-pointtopoint-grouping;
      }
      container MFR-subinterface {
        list MFR {
          // NCS patched for predictable order
          ordered-by user;
          key "name";
          leaf name {
            // NCS drop tailf-common:cli-diff-dependency statement
            type string;
          }
          leaf type {
            type string;
          }
          uses ncs_template_interface-common-pre-grouping;
          uses ncs_template_sub-interface-common-grouping;
        }
      }
      list BRI {
        // NCS patched for predictable order
        ordered-by user;
        key "name";
        leaf name {
          type string;
        }
        uses ncs_template_interface-common-pre-grouping;
        uses ncs_template_interface-common-grouping;
        uses ncs_template_interface-pointtopoint-grouping;
      }
      list Ethernet {
        // NCS patched for predictable order
        ordered-by user;
        key "name";
        leaf name {
          type string;
        }
        uses ncs_template_interface-common-pre-grouping;
        uses ncs_template_interface-ethernet-pre-grouping;
        uses ncs_template_interface-switch-grouping;
        uses ncs_template_interface-ethernet-switch-grouping;
        uses ncs_template_interface-common-switch-grouping;
        uses ncs_template_interface-ethernet-post-grouping;
      }
      list FastEthernet {
        // NCS patched for predictable order
        ordered-by user;
        key "name";
        leaf name {
          type string;
        }
        uses ncs_template_interface-common-pre-grouping;
        uses ncs_template_interface-ethernet-pre-grouping;
        uses ncs_template_interface-switch-grouping;
        uses ncs_template_interface-ethernet-switch-grouping;
        uses ncs_template_interface-common-switch-grouping;
        uses ncs_template_interface-ethernet-post-grouping;
      }
      list GigabitEthernet {
        // NCS patched for predictable order
        ordered-by user;
        key "name";
        leaf name {
          type string;
        }
        uses ncs_template_interface-common-pre-grouping;
        uses ncs_template_interface-ethernet-pre-grouping;
        uses ncs_template_interface-switch-grouping;
        uses ncs_template_interface-ethernet-switch-grouping;
        uses ncs_template_interface-common-switch-grouping;
        uses ncs_template_interface-ethernet-post-grouping;
      }
      list TenGigabitEthernet {
        // NCS patched for predictable order
        ordered-by user;
        key "name";
        leaf name {
          type string;
        }
        uses ncs_template_interface-common-pre-grouping;
        uses ncs_template_interface-ethernet-pre-grouping;
        uses ncs_template_interface-switch-grouping;
        uses ncs_template_interface-ethernet-switch-grouping;
        uses ncs_template_interface-common-switch-grouping;
        uses ncs_template_interface-ethernet-post-grouping;
      }
      list FortyGigabitEthernet {
        // NCS patched for predictable order
        ordered-by user;
        key "name";
        leaf name {
          type string;
        }
        uses ncs_template_interface-common-pre-grouping;
        uses ncs_template_interface-ethernet-pre-grouping;
        uses ncs_template_interface-switch-grouping;
        uses ncs_template_interface-ethernet-switch-grouping;
        uses ncs_template_interface-common-switch-grouping;
        uses ncs_template_interface-ethernet-post-grouping;
      }
      list HundredGigE {
        // NCS patched for predictable order
        ordered-by user;
        key "name";
        leaf name {
          type string;
        }
        uses ncs_template_interface-common-pre-grouping;
        uses ncs_template_interface-ethernet-pre-grouping;
        uses ncs_template_interface-switch-grouping;
        uses ncs_template_interface-ethernet-switch-grouping;
        uses ncs_template_interface-common-switch-grouping;
        uses ncs_template_interface-ethernet-post-grouping;
      }
      list Wlan-GigabitEthernet {
        // NCS patched for predictable order
        ordered-by user;
        key "name";
        leaf name {
          type string;
        }
        uses ncs_template_interface-common-pre-grouping;
        uses ncs_template_interface-ethernet-pre-grouping;
        uses ncs_template_interface-switch-grouping;
        uses ncs_template_interface-ethernet-switch-grouping;
        uses ncs_template_interface-common-switch-grouping;
        uses ncs_template_interface-ethernet-post-grouping;
      }
      list wlan-ap {
        // NCS patched for predictable order
        ordered-by user;
        key "name";
        leaf name {
          type string;
        }
        uses ncs_template_interface-common-pre-grouping;
        uses ncs_template_interface-ethernet-pre-grouping;
        uses ncs_template_interface-ethernet-grouping;
        uses ncs_template_interface-common-grouping;
        uses ncs_template_interface-ethernet-post-grouping;
      }
      list Dialer {
        // NCS patched for predictable order
        ordered-by user;
        key "name";
        leaf name {
          type string;
        }
        uses ncs_template_interface-common-pre-grouping;
        uses ncs_template_interface-common-grouping;
        uses ncs_template_interface-pointtopoint-grouping;
      }
      list ATM {
        // NCS patched for predictable order
        ordered-by user;
        key "name";
        leaf name {
          type string;
        }
        leaf point-to-point {
          type empty;
        }
        uses ncs_template_interface-common-pre-grouping;
        uses ncs_template_interface-common-grouping;
        container ima {
          leaf version {
            type string;
          }
          leaf group-id {
            type string;
          }
        }
        container atm {
          container bandwidth {
            leaf dynamic {
              type empty;
            }
          }
          container mcpt-timers {
            leaf timer-1 {
              type string;
            }
            leaf timer-2 {
              type string;
            }
            leaf timer-3 {
              type string;
            }
          }
          leaf enable-ilmi-trap {
            type string;
            // NCS drop default statement
          }
          container ilmi-keepalive {
            presence "true";
          }
          container route-bridged {
            leaf ip {
              type empty;
            }
            leaf ipv6 {
              type empty;
            }
          }
        }
        list pvc {
          // NCS patched for predictable order
          ordered-by user;
          key "name";
          leaf name {
            type string;
          }
          leaf l2transport {
            type empty;
          }
          leaf class-vc {
            type string;
          }
          container cell-packing {
            leaf maxcells {
              type string;
            }
            leaf mcpt-timer {
              type string;
            }
          }
          leaf encapsulation {
            type string;
          }
          container service-policy {
            uses ncs_template_service-policy-grouping;
          }
          container pppoe-client {
            list dial-pool-number {
              // NCS patched for predictable order
              ordered-by user;
              key "id";
              leaf id {
                type string;
              }
              leaf dial-on-demand {
                type empty;
              }
              leaf restart {
                type string;
              }
              leaf mac-override {
                type empty;
              }
              leaf service-name {
                type string;
              }
            }
            leaf ppp-max-payload {
              type string;
            }
          }
          uses ncs_template_xconnect-grouping;
        }
      }
      list CEM {
        // NCS patched for predictable order
        ordered-by user;
        key "name";
        leaf name {
          type string;
        }
        uses ncs_template_interface-common-pre-grouping;
        uses ncs_template_interface-common-grouping;
        list cem {
          // NCS patched for predictable order
          ordered-by user;
          key "id";
          leaf id {
            type string;
          }
          container cem {
            leaf class {
              type string;
            }
          }
          container service-policy {
            leaf input {
              type string;
            }
          }
          uses ncs_template_xconnect-grouping;
        }
      }
      list BDI {
        // NCS patched for predictable order
        ordered-by user;
        key "name";
        leaf name {
          // NCS drop tailf-common:cli-diff-dependency statement
          type string;
        }
        uses ncs_template_interface-common-pre-grouping;
        uses ncs_template_interface-ethernet-pre-grouping;
        uses ncs_template_interface-ethernet-grouping;
        uses ncs_template_interface-common-grouping;
        uses ncs_template_interface-ethernet-post-grouping;
      }
      list BVI {
        // NCS patched for predictable order
        ordered-by user;
        key "name";
        leaf name {
          type string;
        }
        uses ncs_template_interface-common-pre-grouping;
        uses ncs_template_interface-common-grouping;
      }
      list Cable {
        // NCS patched for predictable order
        ordered-by user;
        key "name";
        leaf name {
          type string;
        }
        uses ncs_template_interface-common-pre-grouping;
        uses ncs_template_interface-common-grouping;
        container downstream {
          list Cable {
            // NCS patched for predictable order
            ordered-by user;
            key "name";
            leaf name {
              type string;
            }
            leaf rf-channel {
              type string;
            }
          }
          list Modular-Cable {
            // NCS patched for predictable order
            ordered-by user;
            key "name";
            leaf name {
              type string;
            }
            leaf rf-channel {
              type string;
            }
            leaf upstream {
              type string;
            }
          }
          list Integrated-Cable {
            // NCS patched for predictable order
            ordered-by user;
            key "name";
            leaf name {
              type string;
            }
            leaf rf-channel {
              type string;
            }
          }
        }
        list upstream {
          // NCS patched for predictable order
          ordered-by user;
          key "id";
          leaf id {
            type string;
          }
          leaf Upstream-Cable {
            type string;
          }
          leaf us-channel {
            type string;
          }
        }
        container cable {
          container tftp-enforce {
            presence "true";
            leaf mark-only {
              type empty;
            }
          }
          leaf ip-init {
            type string;
            // NCS drop default statement
          }
          container mtc-mode {
            presence "true";
          }
          list rcc-template {
            // NCS patched for predictable order
            ordered-by user;
            key "index";
            leaf index {
              type string;
            }
          }
          container rcp-control {
            leaf verbose {
              type empty;
            }
          }
          container shared-secret {
            uses ncs_template_password-grouping;
          }
          container dynamic-secret {
            choice dynamic-secret-choice {
              case reject {
                leaf reject {
                  type empty;
                }
              }
              case mark {
                leaf mark {
                  type empty;
                }
              }
              case lock {
                leaf lock {
                  type empty;
                }
                leaf lock-qos {
                  type string;
                }
              }
            }
            leaf nocrypt {
              type empty;
            }
          }
          container enable-trap {
            leaf cmonoff-notification {
              type empty;
            }
            leaf cmonoff-interval {
              type string;
            }
          }
          leaf packet-cache {
            type string;
            // NCS drop default statement
          }
          leaf default-phy-burst {
            type string;
          }
          container insertion-interval {
            choice interval-choice {
              leaf fixed-intrvl {
                type string;
              }
              container automatic {
                leaf min-intrvl {
                  type string;
                  // NCS drop default statement
                }
                leaf max-intrvl {
                  type string;
                  // NCS drop default statement
                }
              }
            }
          }
          container map-advance {
            choice map-advance-choice {
              leaf static {
                type string;
              }
              container dynamic {
                leaf safety {
                  type string;
                }
                leaf max-delay {
                  type string;
                }
              }
            }
          }
          leaf sync-interval {
            type string;
          }
          leaf bundle {
            type string;
          }
          container downstream {
            leaf description {
              type string;
            }
            container dsg {
              leaf timer {
                type string;
              }
              list tg {
                // NCS patched for predictable order
                ordered-by user;
                key "tgid";
                leaf tgid {
                  type string;
                }
                list channel {
                  // NCS patched for predictable order
                  ordered-by user;
                  key "channel-id";
                  leaf channel-id {
                    type string;
                  }
                }
              }
            }
          }
          container upstream {
            leaf balance-scheduling {
              type empty;
            }
            leaf max-ports {
              type string;
            }
            list bonding-group {
              // NCS patched for predictable order
              ordered-by user;
              key "id";
              leaf id {
                type string;
              }
              uses ncs_template_description-grouping;
              list upstream {
                // NCS patched for predictable order
                ordered-by user;
                key "number";
                leaf number {
                  type string;
                }
              }
              leaf attributes {
                type string;
              }
            }
            container resiliency {
              leaf on-failure {
                type string;
                // NCS drop default statement
              }
            }
            list cable-upstream-list {
              // NCS patched for predictable order
              ordered-by user;
              key "port";
              leaf port {
                type string;
              }
              leaf connector {
                type string;
              }
              leaf frequency {
                type string;
              }
              container channel-width {
                leaf first-choice-width {
                  type string;
                }
                leaf last-choice-width {
                  type string;
                }
              }
              leaf description {
                type string;
              }
              leaf docsis-mode {
                type string;
              }
              leaf minislot-size {
                type string;
              }
              container power-adjust {
                leaf continue {
                  type string;
                }
              }
              container range-backoff {
                choice range-backoff-choice {
                  case automatic {
                    leaf automatic {
                      type empty;
                    }
                  }
                  case numeric {
                    leaf start {
                      type string;
                    }
                    leaf end {
                      type string;
                    }
                  }
                }
              }
              container modulation-profile {
                leaf primary-profile-number {
                  type string;
                }
                leaf secondary-profile-number {
                  type string;
                }
                leaf tertiary-profile-number {
                  type string;
                }
              }
              leaf rate-limit {
                type string;
              }
              leaf equalization-coefficient {
                type empty;
              }
              leaf equalization-error-recovery {
                type string;
                // NCS drop default statement
              }
              container rate-adapt {
                presence "true";
              }
              leaf attribute-mask {
                type string;
              }
              leaf chan-class-id {
                type string;
              }
              leaf shutdown {
                type string;
              }
            }
          }
          container sid-cluster-group {
            leaf dynamic {
              type empty;
            }
            leaf num-of-cluster {
              type string;
            }
            leaf req-multiplier {
              type string;
            }
          }
          container sid-cluster-switching {
            leaf max-request {
              type string;
            }
            leaf max-time {
              type string;
            }
          }
          container divert-rate-limit {
            leaf rate {
              type string;
            }
            leaf limit {
              type string;
            }
          }
          container privacy {
            leaf mandatory {
              type empty;
            }
            leaf bpi-plus-policy {
              type string;
            }
            leaf accept-self-signed-certificate {
              type empty;
            }
            leaf eae-policy {
              type string;
            }
          }
        }
      }
      list Video {
        // NCS patched for predictable order
        ordered-by user;
        key "name";
        leaf name {
          type string;
        }
        uses ncs_template_interface-common-pre-grouping;
        uses ncs_template_interface-common-grouping;
      }
      list Integrated-Cable {
        // NCS patched for predictable order
        ordered-by user;
        key "name";
        leaf name {
          type string;
        }
        uses ncs_template_interface-common-pre-grouping;
        uses ncs_template_interface-common-grouping;
        container cable {
          leaf bundle {
            type string;
          }
          container rf-bandwidth-percent {
            leaf percent-value {
              type string;
            }
          }
        }
      }
      list Modular-Cable {
        // NCS patched for predictable order
        ordered-by user;
        key "name";
        leaf name {
          type string;
        }
        uses ncs_template_interface-common-pre-grouping;
        uses ncs_template_interface-common-grouping;
        container cable {
          leaf bundle {
            type string;
          }
          container rf-bandwidth-percent {
            leaf percent-value {
              type string;
            }
            container remaining {
              leaf ratio {
                type string;
              }
            }
          }
          container cm-status {
            container enable {
              leaf no-list {
                type string;
              }
            }
          }
        }
      }
      list Wideband-Cable {
        // NCS patched for predictable order
        ordered-by user;
        key "name";
        leaf name {
          type string;
        }
        uses ncs_template_interface-common-pre-grouping;
        uses ncs_template_interface-common-grouping;
        container cable {
          leaf bundle {
            type string;
          }
          container privacy {
            leaf accept-self-signed-certificate {
              type empty;
            }
          }
          leaf ds-resiliency {
            type empty;
          }
          container rf-channel {
            list rf-channel-list {
              // NCS patched for predictable order
              ordered-by user;
              key "rf-port";
              leaf rf-port {
                type string;
              }
              leaf bandwidth-percent {
                type string;
              }
              container remaining {
                leaf ratio {
                  type string;
                }
              }
            }
          }
          container rf-channels {
            list channel-list {
              // NCS patched for predictable order
              ordered-by user;
              key "bandwidth-percent";
              leaf bandwidth-percent {
                type string;
              }
              leaf-list group-list {
                // NCS patched for predictable order
                ordered-by user;
                type string;
              }
            }
            list controller {
              // NCS patched for predictable order
              ordered-by user;
              key "id";
              leaf id {
                type string;
              }
              leaf-list channel-list {
                // NCS patched for predictable order
                ordered-by user;
                type string;
              }
              leaf bandwidth-percent {
                type string;
              }
            }
          }
          container downstream {
            leaf attribute-mask {
              type string;
            }
          }
        }
      }
      list Bundle {
        // NCS patched for predictable order
        ordered-by user;
        key "name";
        leaf name {
          type string;
        }
        uses ncs_template_interface-common-pre-grouping;
        uses ncs_template_interface-common-grouping;
        container cable {
          leaf nd {
            type string;
            // NCS drop default statement
          }
          container arp {
            container filter {
              container request-send {
                presence "true";
                leaf number {
                  type string;
                }
                leaf window-size {
                  type string;
                }
              }
              container reply-accept {
                presence "true";
                leaf number {
                  type string;
                }
                leaf window-size {
                  type string;
                }
              }
            }
          }
          container conf {
            leaf arp {
              type string;
              // NCS drop default statement
            }
          }
          container ipv6 {
            container source-verify {
              container dhcp {
                presence "true";
                leaf server {
                  type string;
                }
              }
              container leasequery-filter {
                container upstream {
                  leaf threshold {
                    type string;
                  }
                  leaf interval {
                    type string;
                  }
                }
              }
              leaf leasetimer {
                type string;
              }
            }
          }
          leaf source-verify {
            type empty;
          }
          container source-verify-conf {
            container source-verify {
              container dhcp {
                presence "true";
                leaf server {
                  type string;
                }
              }
              container leasequery-filter {
                container upstream {
                  leaf threshold {
                    type string;
                  }
                  leaf interval {
                    type string;
                  }
                }
              }
              leaf leasetimer {
                type string;
              }
            }
          }
          container dhcp-parse {
            leaf option-43 {
              type empty;
            }
            leaf option-60 {
              type empty;
            }
          }
          container dhcp-giaddr {
            choice dhcp-giaddr-choice {
              container policy {
                presence "true";
              }
              leaf primary {
                type empty;
              }
            }
          }
          list helper-address {
            // NCS patched for predictable order
            ordered-by user;
            key "IP-address";
            leaf IP-address {
              type string;
            }
          }
        }
      }
      list Cellular {
        // NCS patched for predictable order
        ordered-by user;
        key "name";
        leaf name {
          type string;
        }
        uses ncs_template_interface-common-pre-grouping;
        uses ncs_template_interface-common-grouping;
        uses ncs_template_interface-pointtopoint-grouping;
      }
      list Qam-red {
        // NCS patched for predictable order
        ordered-by user;
        key "name";
        leaf name {
          type string;
        }
        uses ncs_template_interface-common-pre-grouping;
        uses ncs_template_interface-common-grouping;
        container cable {
          leaf carrier-id {
            type string;
          }
          container mode {
            container depi {
              choice depi-choice {
                container local;
                container remote {
                  presence "true";
                  leaf learn {
                    type empty;
                  }
                }
              }
            }
          }
          container downstream {
            leaf max-carriers {
              type string;
            }
            leaf lqam-group {
              type string;
            }
            leaf tsid {
              type string;
            }
          }
        }
        container depi {
          leaf depi-tunnel {
            type string;
          }
        }
      }
      list Asi {
        // NCS patched for predictable order
        ordered-by user;
        key "name";
        leaf name {
          type string;
        }
        uses ncs_template_interface-common-pre-grouping;
        uses ncs_template_interface-common-grouping;
      }
      list Vlan {
        // NCS patched for predictable order
        ordered-by user;
        // NCS drop tailf-common:cli-diff-dependency statement
        key "name";
        leaf name {
          type string;
        }
        uses ncs_template_interface-common-pre-grouping;
        uses ncs_template_interface-ethernet-pre-grouping;
        uses ncs_template_interface-ethernet-grouping;
        uses ncs_template_interface-common-grouping;
        uses ncs_template_interface-ethernet-post-grouping;
      }
      list Async {
        // NCS patched for predictable order
        ordered-by user;
        key "name";
        leaf name {
          type string;
        }
        uses ncs_template_interface-common-pre-grouping;
        uses ncs_template_interface-common-grouping;
        uses ncs_template_interface-pointtopoint-grouping;
      }
      list Group-Async {
        // NCS patched for predictable order
        ordered-by user;
        key "name";
        leaf name {
          type string;
        }
        uses ncs_template_interface-common-pre-grouping;
        uses ncs_template_interface-common-grouping;
        uses ncs_template_interface-pointtopoint-grouping;
      }
      list POS {
        // NCS patched for predictable order
        ordered-by user;
        key "name";
        leaf name {
          type string;
        }
        uses ncs_template_interface-common-pre-grouping;
        uses ncs_template_interface-common-grouping;
        uses ncs_template_interface-pointtopoint-grouping;
        container aps {
          leaf group {
            type string;
          }
          list protect {
            // NCS patched for predictable order
            ordered-by user;
            key "circuit-number ip-address";
            leaf circuit-number {
              type string;
            }
            leaf ip-address {
              type string;
            }
          }
          leaf working {
            type string;
          }
        }
        container pos {
          leaf ais-shut {
            type empty;
          }
          leaf framing {
            type string;
            // NCS drop default statement
          }
          container report {
            leaf rdool {
              type empty;
            }
            leaf lais {
              type empty;
            }
            leaf lrdi {
              type empty;
            }
            leaf pais {
              type empty;
            }
            leaf prdi {
              type empty;
            }
            leaf sd-ber {
              type empty;
            }
          }
          leaf scramble-atm {
            type empty;
          }
          container threshold {
            leaf sf-ber {
              type string;
              // NCS drop default statement
            }
          }
          container flag {
            leaf c2 {
              type string;
            }
            leaf j0 {
              type string;
            }
            leaf s1s0 {
              type string;
              // NCS drop default statement
            }
          }
          container delay {
            container triggers {
              leaf line {
                type string;
              }
              leaf path {
                type string;
              }
            }
          }
        }
      }
      list Serial {
        // NCS patched for predictable order
        ordered-by user;
        key "name";
        leaf name {
          type string;
        }
        uses ncs_template_interface-common-pre-grouping;
        uses ncs_template_interface-common-grouping;
        uses ncs_template_interface-pointtopoint-grouping;
      }
      container Serial-subinterface {
        list Serial {
          // NCS patched for predictable order
          ordered-by user;
          key "name";
          leaf name {
            // NCS drop tailf-common:cli-diff-dependency statement
            type string;
          }
          leaf type {
            type string;
          }
          uses ncs_template_interface-common-pre-grouping;
          uses ncs_template_sub-interface-common-grouping;
          uses ncs_template_interface-pointtopoint-grouping;
        }
      }
      list Virtual-Template {
        // NCS patched for predictable order
        ordered-by user;
        key "name";
        leaf name {
          type string;
        }
        leaf type {
          type string;
        }
        uses ncs_template_interface-common-pre-grouping;
        uses ncs_template_interface-ethernet-pre-grouping;
        uses ncs_template_interface-ethernet-grouping;
        uses ncs_template_interface-common-grouping;
        uses ncs_template_interface-ethernet-post-grouping;
        uses ncs_template_interface-pointtopoint-grouping;
        uses ncs_template_interface-tunnel-grouping;
      }
      list pseudowire {
        // NCS patched for predictable order
        ordered-by user;
        key "name";
        leaf name {
          type string;
        }
        leaf description {
          type string;
        }
        leaf shutdown {
          type empty;
        }
        container source {
          container template {
            leaf type {
              type string;
            }
            leaf name {
              type string;
            }
          }
        }
        leaf encapsulation {
          type string;
        }
        container signaling {
          leaf protocol {
            type string;
          }
        }
        container neighbor {
          leaf address {
            type string;
          }
          leaf vcid {
            type string;
          }
        }
        leaf mtu {
          type string;
        }
        leaf control-word {
          type string;
        }
        container label {
          // NCS drop tailf-common:cli-diff-dependency statement
          leaf local-pseudowire-label {
            type string;
          }
          leaf remote-pseudowire-label {
            type string;
          }
        }
        container pseudowire {
          // NCS drop tailf-common:cli-diff-dependency statement
          leaf type {
            type string;
          }
        }
        container service-policy {
          uses ncs_template_service-policy-grouping;
        }
      }
      list LISP {
        // NCS patched for predictable order
        ordered-by user;
        key "name";
        leaf name {
          type string;
        }
        uses ncs_template_interface-common-pre-grouping;
        uses ncs_template_interface-common-grouping;
      }
      container LISP-subinterface {
        list LISP {
          // NCS patched for predictable order
          ordered-by user;
          key "name";
          leaf name {
            // NCS drop tailf-common:cli-diff-dependency statement
            type string;
          }
          uses ncs_template_interface-common-pre-grouping;
          uses ncs_template_sub-interface-common-grouping;
        }
      }
      list vasileft {
        // NCS patched for predictable order
        ordered-by user;
        key "name";
        leaf name {
          type string;
        }
        uses ncs_template_interface-common-pre-grouping;
        uses ncs_template_interface-common-grouping;
      }
      list vasiright {
        // NCS patched for predictable order
        ordered-by user;
        key "name";
        leaf name {
          type string;
        }
        uses ncs_template_interface-common-pre-grouping;
        uses ncs_template_interface-common-grouping;
      }
      list AppNav-Compress {
        // NCS patched for predictable order
        ordered-by user;
        // NCS drop tailf-common:cli-diff-dependency statement
        key "name";
        leaf name {
          type string;
        }
        uses ncs_template_interface-common-pre-grouping;
        uses ncs_template_interface-common-grouping;
      }
      list AppNav-UnCompress {
        // NCS patched for predictable order
        ordered-by user;
        // NCS drop tailf-common:cli-diff-dependency statement
        key "name";
        leaf name {
          type string;
        }
        uses ncs_template_interface-common-pre-grouping;
        uses ncs_template_interface-common-grouping;
      }
      list ucse {
        // NCS patched for predictable order
        ordered-by user;
        key "name";
        leaf name {
          type string;
        }
        uses ncs_template_interface-common-pre-grouping;
        uses ncs_template_interface-ethernet-pre-grouping;
        uses ncs_template_interface-switch-grouping;
        uses ncs_template_interface-ethernet-switch-grouping;
        uses ncs_template_interface-common-switch-grouping;
        uses ncs_template_interface-ethernet-post-grouping;
      }
    }
    container access-list {
      list access-list {
        // NCS patched for predictable order
        ordered-by user;
        key "id";
        leaf id {
          type string;
        }
        list rule {
          // NCS patched for predictable order
          ordered-by user;
          key "rule";
          leaf rule {
            type string;
          }
          leaf seq {
            type string;
          }
        }
      }
      leaf dynamic-extended {
        type empty;
      }
    }
    container arp {
      uses ncs_template_arp-grouping;
      list vrf {
        // NCS patched for predictable order
        ordered-by user;
        key "name";
        leaf name {
          // NCS drop tailf-common:cli-diff-dependency statement
          // NCS drop tailf-common:cli-diff-dependency statement
          type string;
        }
        uses ncs_template_arp-grouping;
      }
      list access-list {
        // NCS patched for predictable order
        ordered-by user;
        key "name";
        leaf name {
          type string;
        }
        list access-list-rule {
          // NCS patched for predictable order
          ordered-by user;
          key "rule";
          leaf rule {
            type string;
          }
        }
      }
    }
    list virtual-service {
      // NCS patched for predictable order
      ordered-by user;
      // NCS drop tailf-common:cli-diff-dependency statement
      key "name";
      leaf name {
        type string;
      }
      leaf description {
        type string;
      }
      container ip {
        container shared {
          container host-interface {
            leaf GigabitEthernet {
              type string;
            }
          }
        }
      }
      leaf profile {
        type string;
      }
      container vnic {
        container gateway {
          list VirtualPortGroup {
            // NCS patched for predictable order
            ordered-by user;
            key "name";
            leaf name {
              type string;
            }
            container guest {
              container ip {
                leaf address {
                  type string;
                }
              }
            }
          }
        }
      }
      leaf activate {
        // NCS drop tailf-common:cli-diff-dependency statement
        // NCS drop tailf-common:cli-diff-dependency statement
        type empty;
      }
    }
    list route-map {
      // NCS patched for predictable order
      ordered-by user;
      // NCS drop tailf-common:cli-diff-dependency statement
      // NCS drop tailf-common:cli-diff-dependency statement
      key "name sequence";
      leaf name {
        type string;
      }
      leaf sequence {
        type string;
      }
      leaf operation {
        type string;
      }
      leaf description {
        type string;
      }
      container match {
        leaf-list as-path {
          // NCS patched for predictable order
          ordered-by user;
          type string;
        }
        container ip {
          container address {
            leaf-list access-list {
              // NCS patched for predictable order
              ordered-by user;
              type string;
            }
            leaf-list prefix-list {
              // NCS patched for predictable order
              ordered-by user;
              type string;
            }
          }
          container next-hop {
            leaf-list access-list {
              // NCS patched for predictable order
              ordered-by user;
              type string;
            }
            leaf-list prefix-list {
              // NCS patched for predictable order
              ordered-by user;
              type string;
            }
          }
          container route-source {
            leaf-list access-list {
              // NCS patched for predictable order
              ordered-by user;
              type string;
            }
            leaf-list prefix-list {
              // NCS patched for predictable order
              ordered-by user;
              type string;
            }
          }
        }
        container ipv6 {
          container address {
            leaf access-list {
              // NCS drop tailf-common:cli-diff-dependency statement
              type string;
            }
            leaf prefix-list {
              // NCS drop tailf-common:cli-diff-dependency statement
              type string;
            }
          }
          container next-hop {
            leaf access-list {
              type string;
            }
            leaf prefix-list {
              type string;
            }
          }
          container route-source {
            leaf access-list {
              type string;
            }
            leaf prefix-list {
              type string;
            }
          }
        }
        leaf-list community {
          // NCS patched for predictable order
          ordered-by user;
          type string;
        }
        leaf-list extcommunity {
          // NCS patched for predictable order
          ordered-by user;
          type string;
        }
        leaf-list tag {
          // NCS patched for predictable order
          ordered-by user;
          type string;
        }
        container clns {
          leaf-list address {
            // NCS patched for predictable order
            ordered-by user;
            type string;
          }
        }
        leaf-list interface {
          // NCS patched for predictable order
          ordered-by user;
          type string;
        }
        leaf-list source-protocol {
          // NCS patched for predictable order
          ordered-by user;
          type string;
        }
        list route-type {
          // NCS patched for predictable order
          ordered-by user;
          key "tag";
          leaf tag {
            type string;
          }
        }
        leaf-list local-preference {
          // NCS patched for predictable order
          ordered-by user;
          type string;
        }
      }
      container set {
        leaf global {
          type empty;
        }
        container as-path {
          container prepend {
            leaf as-list {
              type string;
            }
            leaf last-as {
              type string;
            }
          }
          container tag {
            presence "true";
          }
        }
        container comm-list {
          leaf name {
            type string;
          }
          leaf delete {
            type empty;
          }
        }
        container community {
          choice set-community-choice {
            leaf none {
              type empty;
            }
            leaf-list community-number {
              // NCS patched for predictable order
              ordered-by user;
              type string;
            }
          }
        }
        container extcomm-list {
          leaf name {
            type string;
          }
          leaf delete {
            type empty;
          }
        }
        container extcommunity {
          leaf-list rt {
            // NCS patched for predictable order
            ordered-by user;
            type string;
          }
        }
        container ip {
          container next-hop {
            leaf self {
              type empty;
            }
            container verify-availability-conf {
              list verify-availability {
                // NCS patched for predictable order
                ordered-by user;
                key "address";
                leaf address {
                  type string;
                }
                leaf sequence {
                  type string;
                }
                leaf track {
                  type string;
                }
              }
            }
            leaf peer-address {
              // NCS drop tailf-common:cli-diff-dependency statement
              type empty;
            }
            leaf-list address {
              // NCS patched for predictable order
              ordered-by user;
              // NCS drop tailf-common:cli-diff-dependency statement
              type string;
            }
            leaf verify-availability {
              type empty;
            }
            container dynamic {
              leaf dhcp {
                type empty;
              }
            }
            container recursive {
              choice global-or-vrf-choice {
                leaf global {
                  type empty;
                }
                leaf vrf {
                  type string;
                }
              }
              leaf address {
                type string;
              }
            }
            container encapsulate {
              leaf l3vpn {
                type string;
              }
            }
          }
          container df {
            presence "true";
            leaf bit {
              type string;
            }
          }
          leaf precedence {
            type string;
          }
          leaf qos-group {
            type string;
          }
        }
        container ipv6 {
          container next-hop {
            choice next-hop-choice {
              leaf-list address {
                // NCS patched for predictable order
                ordered-by user;
                type string;
              }
              leaf peer-address {
                type empty;
              }
            }
          }
        }
        container local-preference {
          presence "true";
          leaf value {
            type string;
          }
        }
        leaf-list metric {
          // NCS patched for predictable order
          ordered-by user;
          type string;
        }
        leaf metric-type {
          type string;
        }
        leaf weight {
          type string;
        }
        container origin {
          choice origin-choice {
            leaf origin-value {
              type string;
            }
            leaf egp {
              type string;
            }
          }
        }
        leaf vrf {
          // NCS drop tailf-common:cli-diff-dependency statement
          // NCS drop tailf-common:cli-diff-dependency statement
          type string;
        }
        leaf tag {
          type string;
        }
        leaf mpls-label {
          type empty;
        }
        leaf-list interface {
          // NCS patched for predictable order
          ordered-by user;
          type string;
        }
        container default {
          container interface {
            uses ncs_template_interface-name-grouping;
          }
        }
      }
      container continue {
        presence "true";
        leaf sequence-number {
          type string;
        }
      }
    }
    container dialer {
      list watch-list {
        // NCS patched for predictable order
        ordered-by user;
        key "id";
        leaf id {
          type string;
        }
        list ip {
          // NCS patched for predictable order
          ordered-by user;
          key "address";
          leaf address {
            type string;
          }
          leaf mask {
            type string;
          }
        }
        container delay {
          container route-check {
            leaf initial {
              type string;
            }
          }
          leaf connect {
            type string;
          }
          leaf disconnect {
            type string;
          }
        }
      }
    }
    list dialer-list {
      // NCS patched for predictable order
      ordered-by user;
      key "id";
      leaf id {
        type string;
      }
      container protocol {
        leaf ip {
          type string;
        }
      }
    }
    container authentication {
      container mac-move {
        leaf permit {
          type empty;
        }
      }
    }
    container banner {
      leaf exec {
        type string;
      }
      leaf login {
        type string;
      }
      leaf lcd {
        type string;
      }
      leaf prompt-timeout {
        type string;
      }
      leaf motd {
        type string;
      }
    }
    list pseudowire-class {
      // NCS patched for predictable order
      ordered-by user;
      key "name";
      leaf name {
        type string;
      }
      leaf encapsulation {
        type string;
      }
      leaf interworking {
        type string;
      }
      leaf control-word {
        type empty;
      }
      container sequencing {
        choice sequencing-choice {
          leaf both {
            type empty;
          }
          leaf receive {
            type empty;
          }
          container resync {
            presence "true";
          }
          leaf transmit {
            type empty;
          }
        }
      }
      container status {
        container peer {
          container topology {
            leaf dual-homed {
              type empty;
            }
          }
        }
      }
      container protocol {
        choice protocol-choice {
          leaf none {
            type empty;
          }
          leaf l2tpv3 {
            type string;
          }
        }
      }
      container ip {
        container local {
          container interface {
            uses ncs_template_interface-name-grouping;
          }
        }
      }
    }
    container control-plane-host {
      container control-plane {
        container host {
          presence "true";
          list management-interface {
            // NCS patched for predictable order
            ordered-by user;
            // NCS drop tailf-common:cli-diff-dependency statement
            key "interface";
            leaf interface {
              type string;
            }
            leaf-list allow {
              // NCS patched for predictable order
              ordered-by user;
              type string;
            }
          }
        }
      }
    }
    container control-plane {
      presence "true";
      container service-policy {
        uses ncs_template_service-policy-grouping;
      }
    }
    container cops {
      container listener {
        leaf access-list {
          type string;
        }
      }
      container ip {
        leaf dscp {
          type string;
        }
      }
    }
    list connect {
      // NCS patched for predictable order
      ordered-by user;
      key "interface1 interface2";
      leaf name {
        type string;
      }
      leaf interface1 {
        type string;
      }
      leaf number1 {
        type string;
      }
      leaf interface2 {
        type string;
      }
      leaf number2 {
        type string;
      }
      container backup {
        container peer {
          leaf peer-router-ip-addr {
            type string;
          }
          leaf vcid {
            type string;
          }
          leaf pw-class {
            type string;
          }
        }
      }
      uses ncs_template_xconnect-grouping;
    }
    list voice-port {
      // NCS patched for predictable order
      ordered-by user;
      key "name";
      leaf name {
        type string;
      }
      container timeouts {
        leaf interdigit {
          type string;
        }
      }
      leaf shutdown {
        type empty;
      }
      container busyout {
        leaf action {
          type string;
        }
        container monitor {
          container action {
            choice action-choice {
              leaf graceful {
                type empty;
              }
              leaf shutdown {
                type empty;
              }
              container alarm {
                leaf blue {
                  type empty;
                }
              }
            }
          }
          list state {
            // NCS patched for predictable order
            ordered-by user;
            key "name";
            leaf name {
              type string;
            }
            leaf in-service {
              type empty;
            }
          }
        }
      }
    }
    container dial-peer {
      list voice {
        // NCS patched for predictable order
        ordered-by user;
        key "id";
        leaf id {
          type string;
        }
        leaf peer {
          type string;
        }
        leaf answer-address {
          type string;
        }
        leaf trunkgroup {
          type string;
        }
        leaf description {
          type string;
        }
        container translation-profile {
          leaf incoming {
            type string;
          }
          leaf outgoing {
            type string;
          }
        }
        leaf huntstop {
          type empty;
        }
        leaf max-conn {
          type string;
        }
        leaf destination-pattern {
          type string;
        }
        container modem {
          container passthrough {
            choice passthrough-choice {
              leaf system {
                type string;
                // NCS drop default statement
              }
              container nse {
                leaf payload-type {
                  type string;
                }
                leaf codec {
                  type string;
                }
                leaf redundancy {
                  type empty;
                }
              }
            }
          }
        }
        container session {
          leaf protocol {
            type string;
          }
          leaf target {
            type string;
          }
        }
        container dtmf-relay {
          leaf cisco-rtp {
            type empty;
          }
          leaf h245-alphanumeric {
            type empty;
          }
          leaf h245-signal {
            type empty;
          }
          leaf rtp-nte {
            type empty;
          }
        }
        container incoming {
          leaf called-number {
            type string;
          }
        }
        leaf direct-inward-dial {
          type empty;
        }
        leaf forward-digits {
          type string;
        }
        container codec {
          leaf name {
            type string;
          }
          leaf bytes {
            type string;
          }
          leaf mode {
            type string;
          }
        }
        container fax {
          container protocol {
            choice protocol-option {
              leaf none {
                type empty;
              }
              leaf cisco {
                type empty;
              }
              leaf pass-through {
                type string;
              }
            }
          }
        }
        container ip {
          container qos {
            list dscp {
              // NCS patched for predictable order
              ordered-by user;
              key "name";
              leaf name {
                type string;
              }
              choice dscp-choice {
                leaf media {
                  type empty;
                }
                leaf signaling {
                  type empty;
                }
                leaf video {
                  type string;
                }
              }
            }
          }
        }
        leaf vad {
          type string;
          // NCS drop default statement
        }
      }
      container outbound {
        container status-check {
          leaf pots {
            type string;
            // NCS drop default statement
          }
        }
      }
      container cor {
        container custom {
          presence "true";
          list name {
            // NCS patched for predictable order
            ordered-by user;
            key "name";
            leaf name {
              type string;
            }
          }
        }
      }
    }
    leaf config-register {
      type string;
    }
    container network-clock-participate {
      container wic {
        list wic-enabled {
          // NCS patched for predictable order
          ordered-by user;
          key "slot";
          leaf slot {
            type string;
          }
        }
        list wic-disabled {
          // NCS patched for predictable order
          ordered-by user;
          key "slot";
          leaf slot {
            type string;
          }
        }
      }
      list T1 {
        // NCS patched for predictable order
        ordered-by user;
        key "name";
        leaf name {
          type string;
        }
      }
    }
    container service-routing {
      leaf capabilities-manager {
        type string;
        // NCS drop default statement
      }
    }
    container mgcp {
      container fax {
        container t38 {
          leaf ecm {
            type empty;
          }
        }
      }
      list behavior {
        // NCS patched for predictable order
        ordered-by user;
        key "category";
        leaf category {
          type string;
        }
        leaf version {
          type string;
        }
      }
      list profile {
        // NCS patched for predictable order
        ordered-by user;
        key "name";
        leaf name {
          type string;
        }
      }
    }
    container gatekeeper {
      leaf shutdown {
        type empty;
      }
    }
    container parser {
      leaf cache {
        type string;
        // NCS drop default statement
      }
    }
    container line {
      list console {
        // NCS patched for predictable order
        ordered-by user;
        key "first";
        // NCS drop max-elements statement
        leaf first {
          type string;
        }
        uses ncs_template_line-grouping;
      }
      list aux {
        // NCS patched for predictable order
        ordered-by user;
        key "first";
        // NCS drop max-elements statement
        leaf first {
          type string;
        }
        uses ncs_template_line-grouping;
      }
      container vty-single-conf {
        list vty {
          // NCS patched for predictable order
          ordered-by user;
          key "first";
          leaf first {
            type string;
          }
          uses ncs_template_line-grouping;
        }
      }
      list vty {
        // NCS patched for predictable order
        ordered-by user;
        key "first last";
        leaf first {
          type string;
        }
        leaf last {
          type string;
        }
        uses ncs_template_line-grouping;
      }
      list number-single-list {
        // NCS patched for predictable order
        ordered-by user;
        key "first";
        leaf first {
          type string;
        }
        uses ncs_template_line-grouping;
      }
      list number-list {
        // NCS patched for predictable order
        ordered-by user;
        key "first last";
        leaf first {
          type string;
        }
        leaf last {
          type string;
        }
        uses ncs_template_line-grouping;
      }
    }
    container exception {
      container data-corruption {
        container buffer {
          leaf truncate {
            type empty;
          }
        }
      }
      container crashinfo {
        leaf file {
          type string;
        }
        leaf buffersize {
          type string;
        }
      }
    }
    container pnp {
      list profile {
        // NCS patched for predictable order
        ordered-by user;
        key "name";
        leaf name {
          type string;
        }
        container transport {
          leaf protocol {
            type string;
          }
          leaf over {
            // NCS drop when statement
            type string;
          }
          choice address-choice {
            leaf host {
              type string;
            }
            leaf ipv4 {
              type string;
            }
            leaf ipv6 {
              type string;
            }
          }
          leaf port {
            type string;
          }
          leaf vrf {
            type string;
          }
          container source {
            uses ncs_template_interface-name-grouping;
          }
          leaf localcert {
            type string;
          }
          leaf remotecert {
            type string;
          }
        }
        container reconnect {
          leaf seconds {
            type string;
          }
        }
      }
      leaf startup-vlan {
        type string;
      }
      leaf tag {
        type string;
      }
    }
    container onep {
      leaf start {
        type string;
      }
      container transport {
        container tipc {
          presence "true";
        }
      }
    }
    container logging {
      list discriminator {
        // NCS patched for predictable order
        ordered-by user;
        key "discr-name";
        leaf discr-name {
          type string;
        }
        container mnemonics {
          choice mnemonics-choice {
            leaf drops {
              type string;
            }
            leaf includes {
              type string;
            }
          }
        }
        container msg-body {
          choice msg-body-choice {
            leaf drops {
              type string;
            }
            leaf includes {
              type string;
            }
          }
        }
      }
      container cmts {
        container ipc-cable {
          leaf log-level {
            type string;
          }
        }
        container sea {
          leaf syslog-level {
            type string;
          }
        }
      }
      leaf alarm {
        type string;
      }
      container message-counter {
        leaf log {
          type empty;
        }
        leaf debug {
          type empty;
        }
        leaf syslog {
          type string;
          // NCS drop default statement
        }
      }
      container buffered {
        leaf xxml {
          tailf:alt-name "xml";
          type empty;
        }
        leaf discriminator {
          // NCS drop when statement
          type string;
        }
        leaf buffer-size {
          type string;
        }
        leaf severity-level {
          type string;
        }
      }
      container persistent {
        leaf url {
          type string;
        }
        leaf size {
          type string;
        }
        leaf filesize {
          type string;
        }
      }
      container queue-limit {
        leaf queuesize {
          type string;
        }
      }

      grouping logging-common-grouping {
        leaf xxml {
          tailf:alt-name "xml";
          type empty;
        }
        leaf discriminator {
          // NCS drop when statement
          type string;
        }
        leaf filtered {
          type empty;
        }
        leaf severity-level {
          type string;
        }
      }
      container console {
        uses logging-common-grouping;
      }
      container monitor {
        uses logging-common-grouping;
      }
      container snmp-trap {
        leaf emergencies {
          type empty;
        }
        leaf critical {
          type empty;
        }
        leaf errors {
          type empty;
        }
        leaf informational {
          type empty;
        }
        leaf alerts {
          type empty;
        }
        leaf warnings {
          type empty;
        }
        leaf notifications {
          type empty;
        }
        leaf debugging {
          type empty;
        }
      }
      leaf snmp-authfail {
        type empty;
      }
      container event {
        container link-status {
          leaf boot {
            type empty;
          }
          leaf global {
            type empty;
          }
          leaf default {
            type empty;
          }
        }
        container trunk-status {
          leaf global {
            type empty;
          }
        }
      }
      container esm {
        leaf config {
          type empty;
        }
      }
      leaf facility {
        type string;
        // NCS drop default statement
      }
      container history {
        leaf size {
          type string;
        }
        leaf severity-level {
          type string;
        }
      }
      list hostname {
        // NCS patched for predictable order
        ordered-by user;
        key "host";
        leaf host {
          type string;
        }
      }
      container host {
        list ipv4 {
          // NCS patched for predictable order
          ordered-by user;
          key "host";
          leaf host {
            type string;
          }
          uses ncs_template_logging-host-grouping;
        }
        list ipv4-vrf {
          // NCS patched for predictable order
          ordered-by user;
          key "host vrf";
          leaf host {
            type string;
          }
          leaf vrf {
            // NCS drop tailf-common:cli-diff-dependency statement
            // NCS drop tailf-common:cli-diff-dependency statement
            type string;
          }
          uses ncs_template_logging-host-grouping;
        }
        list ipv6 {
          // NCS patched for predictable order
          ordered-by user;
          key "host";
          leaf host {
            type string;
          }
          uses ncs_template_logging-host-grouping;
        }
        container ipv6-vrf {
          list ipv6 {
            // NCS patched for predictable order
            ordered-by user;
            key "host vrf";
            leaf host {
              type string;
            }
            leaf vrf {
              // NCS drop tailf-common:cli-diff-dependency statement
              type string;
            }
            uses ncs_template_logging-host-grouping;
          }
        }
      }
      choice rate-limit-choice {
        leaf rate-limit {
          type string;
          // NCS drop default statement
        }
        container rate-limit-conf {
          container rate-limit {
            leaf console {
              type empty;
            }
            leaf all {
              type empty;
            }
            leaf rate {
              type string;
            }
            leaf except {
              type string;
            }
          }
        }
      }
      list source-interface {
        // NCS patched for predictable order
        ordered-by user;
        key "name";
        leaf name {
          // NCS drop tailf-common:cli-diff-dependency statement
          type string;
        }
        leaf vrf {
          // NCS drop tailf-common:cli-diff-dependency statement
          // NCS drop tailf-common:cli-diff-dependency statement
          type string;
        }
      }
      leaf trap {
        type string;
        // NCS drop default statement
      }
      container origin-id {
        choice origin-id-choice {
          leaf hostname {
            type empty;
          }
          leaf ip {
            type empty;
          }
          leaf ipv6 {
            type empty;
          }
          leaf string {
            type string;
          }
        }
      }
      container linecard {
        leaf size {
          type string;
          // NCS drop default statement
        }
        leaf level {
          type string;
        }
      }
    }
    container firewall {
      leaf multiple-vlan-interfaces {
        type empty;
      }
      list vlan-group {
        // NCS patched for predictable order
        ordered-by user;
        key "id";
        leaf id {
          type string;
        }
        leaf-list vlan {
          // NCS patched for predictable order
          ordered-by user;
          type string;
        }
      }
    }
    container cpd {
      presence "true";
      leaf cr-id {
        type string;
      }
    }
    container nls {
      presence "true";
      leaf resp-timeout {
        type string;
      }
    }
    list flow-sampler-map {
      // NCS patched for predictable order
      ordered-by user;
      key "name";
      leaf name {
        type string;
      }
      container mode {
        container random {
          leaf one-out-of {
            type string;
          }
        }
      }
    }
    container frame-relay {
      leaf switching {
        type empty;
      }
    }
    container scheduler {
      container allocate {
        leaf interrupt-time {
          type string;
        }
        leaf process-time {
          type string;
        }
      }
      leaf isr-watchdog {
        type empty;
      }
      container runtime {
        leaf netinput {
          type string;
        }
      }
    }
    container wsma {
      list agent {
        // NCS patched for predictable order
        ordered-by user;
        key "name";
        leaf name {
          type string;
        }
        list profile {
          // NCS patched for predictable order
          ordered-by user;
          key "name";
          leaf name {
            type string;
          }
        }
      }
      container profile {
        list listener {
          // NCS patched for predictable order
          ordered-by user;
          key "name";
          leaf name {
            type string;
          }
          container transport {
            choice transport-choice {
              container http {
                presence "true";
              }
              container https {
                presence "true";
              }
              container ssh {
                presence "true";
              }
            }
          }
        }
        list initiator {
          // NCS patched for predictable order
          ordered-by user;
          key "name";
          leaf name {
            type string;
          }
          container transport {
            choice transport-choice {
              container http {
                presence "true";
              }
              container https {
                presence "true";
              }
              container ssh {
                presence "true";
              }
            }
          }
        }
      }
    }
    container process {
      container cpu {
        container threshold {
          container type {
            container total {
              uses ncs_template_process-cpu-threshold-grouping;
            }
            container interrupt {
              uses ncs_template_process-cpu-threshold-grouping;
            }
            container process {
              uses ncs_template_process-cpu-threshold-grouping;
            }
          }
        }
        container statistics {
          container limit {
            leaf entry-percentage {
              type string;
            }
            leaf size {
              type string;
            }
          }
        }
      }
    }
    container ntp {
      leaf max-associations {
        type string;
      }
      leaf passive {
        type empty;
      }
      leaf logging {
        type empty;
      }
      container panic {
        leaf update {
          type empty;
        }
      }
      list authentication-key {
        // NCS patched for predictable order
        ordered-by user;
        key "number";
        leaf number {
          type string;
        }
        container md5 {
          leaf secret {
            type string;
          }
          leaf type {
            type string;
          }
        }
      }
      leaf authenticate {
        type empty;
      }
      list trusted-key {
        // NCS patched for predictable order
        ordered-by user;
        key "key-number";
        leaf key-number {
          type string;
        }
        leaf hyphen {
          tailf:alt-name "-";
          type empty;
        }
        leaf end-key-number {
          type string;
        }
      }
      leaf orphan {
        type string;
      }
      leaf mindistance {
        type string;
      }
      leaf maxdistance {
        type string;
      }
      leaf broadcastdelay {
        type string;
      }
      container source {
        uses ncs_template_interface-name-grouping;
      }
      container access-group {
        container peer {
          leaf access-list {
            type string;
          }
          leaf kod {
            type empty;
          }
        }
        container query-only {
          leaf access-list {
            type string;
          }
          leaf kod {
            type empty;
          }
        }
        container serve {
          leaf access-list {
            type string;
          }
          leaf kod {
            type empty;
          }
        }
        container serve-only {
          leaf access-list {
            type string;
          }
          leaf kod {
            type empty;
          }
        }
        container ipv6 {
          container peer {
            leaf access-list {
              type string;
            }
            leaf kod {
              type empty;
            }
          }
        }
      }
      container master {
        presence "true";
        leaf stratum {
          type string;
        }
      }
      container peer {
        uses ncs_template_ntp-peer-grouping;
        container ip {
          uses ncs_template_ntp-peer-grouping;
        }
        container ipv6 {
          uses ncs_template_ntp-peer-grouping;
        }
        list vrf {
          // NCS patched for predictable order
          ordered-by user;
          key "name";
          leaf name {
            // NCS drop tailf-common:cli-diff-dependency statement
            // NCS drop tailf-common:cli-diff-dependency statement
            type string;
          }
          uses ncs_template_ntp-peer-grouping;
        }
      }
      container server {
        uses ncs_template_ntp-peer-grouping;
        container ip {
          uses ncs_template_ntp-peer-grouping;
        }
        container ipv6 {
          uses ncs_template_ntp-peer-grouping;
        }
        list vrf {
          // NCS patched for predictable order
          ordered-by user;
          key "name";
          leaf name {
            // NCS drop tailf-common:cli-diff-dependency statement
            // NCS drop tailf-common:cli-diff-dependency statement
            type string;
          }
          uses ncs_template_ntp-peer-grouping;
        }
      }
      container allow {
        container mode {
          leaf private {
            type empty;
          }
        }
      }
      leaf update-calendar {
        type empty;
      }
    }
    container sntp {
      leaf logging {
        type empty;
      }
      list authentication-key {
        // NCS patched for predictable order
        ordered-by user;
        key "number";
        leaf number {
          type string;
        }
        leaf md5 {
          type string;
        }
        leaf encryption-type {
          type string;
        }
      }
      leaf authenticate {
        type empty;
      }
      list trusted-key {
        // NCS patched for predictable order
        ordered-by user;
        key "key-number";
        leaf key-number {
          type string;
        }
        leaf hyphen {
          tailf:alt-name "-";
          type empty;
        }
        leaf end-key-number {
          type string;
        }
      }
      container server {
        uses ncs_template_sntp-server-grouping;
        container ip {
          uses ncs_template_sntp-server-grouping;
        }
        container ipv6 {
          uses ncs_template_sntp-server-grouping;
        }
        list vrf {
          // NCS patched for predictable order
          ordered-by user;
          key "name";
          leaf name {
            // NCS drop tailf-common:cli-diff-dependency statement
            // NCS drop tailf-common:cli-diff-dependency statement
            type string;
          }
          uses ncs_template_sntp-server-grouping;
        }
      }
      container broadcast {
        leaf client {
          type empty;
        }
      }
      container multicast {
        container client {
          presence "true";
          leaf address {
            type string;
          }
        }
      }
      container source-interface {
        uses ncs_template_interface-name-grouping;
      }
    }
    container ptp {
      container clock {
        list profile {
          // NCS patched for predictable order
          ordered-by user;
          key "id";
          leaf id {
            type string;
          }
          container clock-source1 {
            leaf address {
              type string;
            }
            leaf gw {
              type string;
            }
          }
        }
        container ordinary {
          list domain {
            // NCS patched for predictable order
            ordered-by user;
            key "id";
            // NCS drop max-elements statement
            leaf id {
              type string;
            }
            leaf hybrid {
              type empty;
            }
            leaf priority1 {
              type string;
            }
            leaf priority2 {
              type string;
            }
            container time-properties {
              container gps {
                leaf timeScale {
                  type string;
                }
                leaf currentUtcOffsetValid {
                  type string;
                }
                leaf leap59 {
                  type string;
                }
                leaf leap61 {
                  type string;
                }
                leaf currentUtcOffset {
                  type string;
                }
              }
            }
            list clock-port {
              // NCS patched for predictable order
              ordered-by user;
              key "name mode";
              leaf name {
                type string;
              }
              leaf mode {
                type string;
              }
              leaf profile {
                type string;
              }
              container transport {
                leaf proto {
                  type string;
                }
                leaf unicast {
                  type empty;
                }
                leaf interface {
                  // NCS drop when statement
                  type string;
                }
                leaf negotiation {
                  type empty;
                }
              }
              container clock {
                leaf source {
                  type string;
                }
              }
            }
          }
        }
      }
    }
    container mac-address-table {
      container notification {
        leaf mac-move {
          type empty;
        }
      }
      container move {
        container update {
          leaf transmit {
            type empty;
          }
          leaf receive {
            type empty;
          }
        }
      }
      container synchronize {
        presence "true";
        leaf activity-time {
          type string;
        }
      }
      container aging-type {
        leaf routed-mac {
          type string;
          // NCS drop default statement
        }
      }
      leaf aging-time {
        type string;
      }
      container againg-time-routed-mac {
        container aging-time {
          leaf speed {
            type string;
          }
          leaf routed-mac {
            type empty;
          }
        }
      }
      container limit {
        list vlan {
          // NCS patched for predictable order
          ordered-by user;
          key "id";
          leaf id {
            type string;
          }
          leaf maximum {
            type string;
          }
          leaf action {
            type string;
          }
          leaf flood {
            type empty;
          }
        }
        list bdomain {
          // NCS patched for predictable order
          ordered-by user;
          key "id";
          leaf id {
            type string;
          }
          leaf maximum {
            type string;
          }
          leaf action {
            type string;
          }
          leaf flood {
            type empty;
          }
        }
      }
      container learning {
        container vlan {
          list no-list {
            // NCS patched for predictable order
            ordered-by user;
            key "id";
            leaf id {
              type string;
            }
            leaf module {
              type string;
            }
          }
        }
      }
    }
    container mac {
      container access-list {
        list extended {
          // NCS patched for predictable order
          ordered-by user;
          key "id";
          leaf id {
            type string;
          }
          list entry {
            // NCS patched for predictable order
            ordered-by user;
            key "rule";
            leaf rule {
              type string;
            }
          }
        }
      }
      container address-table {
        leaf aging-time {
          type string;
        }
        container notification {
          leaf change {
            type empty;
          }
          leaf mac-move {
            type empty;
          }
        }
        container move {
          container update {
            leaf transmit {
              type empty;
            }
            leaf receive {
              type empty;
            }
          }
        }
      }
    }
    container privilege {
      container exec {
        list level {
          // NCS patched for predictable order
          ordered-by user;
          key "privilege";
          leaf privilege {
            type string;
          }
          list command-list {
            // NCS patched for predictable order
            ordered-by user;
            key "command";
            leaf command {
              type string;
            }
          }
        }
      }
    }
    container spanning-tree {
      container etherchannel {
        container guard {
          leaf misconfig {
            type empty;
          }
        }
      }
      container extend {
        leaf system-id {
          type empty;
        }
      }
      container loopguard {
        leaf default {
          type empty;
        }
      }
      container mst {
        list instance-range {
          // NCS patched for predictable order
          ordered-by user;
          key "id";
          leaf id {
            type string;
          }
          leaf priority {
            type string;
          }
        }
        container configuration {
          leaf revision {
            type string;
          }
          leaf name {
            type string;
          }
          list instance {
            // NCS patched for predictable order
            ordered-by user;
            key "id";
            leaf id {
              type string;
            }
            leaf-list vlan {
              // NCS patched for predictable order
              ordered-by user;
              type string;
            }
          }
        }
        leaf forward-time {
          type string;
        }
      }
      container optimize {
        container bpdu {
          leaf transmission {
            type string;
            // NCS drop default statement
          }
        }
      }
      container portfast {
        uses ncs_template_spanning-tree-portfast-grouping;
        container edge {
          uses ncs_template_spanning-tree-portfast-grouping;
        }
      }
      container uplinkfast-conf {
        container uplinkfast {
          leaf max-update-rate {
            type string;
          }
        }
      }
      leaf uplinkfast {
        type empty;
      }
      container pathcost {
        leaf method {
          type string;
          // NCS drop default statement
        }
      }
      leaf mode {
        type string;
      }
      container vlan {
        list no-list {
          // NCS patched for predictable order
          ordered-by user;
          key "id";
          leaf id {
            type string;
          }
        }
        list vlan-list {
          // NCS patched for predictable order
          ordered-by user;
          key "id";
          leaf id {
            type string;
          }
          leaf hello-time {
            type string;
          }
          leaf priority {
            type string;
          }
          leaf forward-time {
            type string;
          }
          leaf max-age {
            type string;
          }
        }
      }
    }
    container dot1x {
      container critical {
        leaf eapol {
          type empty;
        }
        container recovery {
          leaf delay {
            type string;
          }
        }
      }
      leaf system-auth-control {
        type empty;
      }
    }
    container power {
      leaf redundancy-mode {
        type string;
      }
    }
    container power-supply {
      container dual {
        presence "true";
        leaf dc-feed {
          type empty;
        }
      }
    }
    container parameter-map {
      container type {
        container inspect-global {
          uses ncs_template_parameter-map-grouping;
        }
        list inspect {
          // NCS patched for predictable order
          ordered-by user;
          key "name";
          leaf name {
            type string;
          }
          uses ncs_template_parameter-map-grouping;
        }
        list inspect-vrf {
          // NCS patched for predictable order
          ordered-by user;
          key "name";
          leaf name {
            type string;
          }
          uses ncs_template_parameter-map-grouping;
        }
        list inspect-zone {
          // NCS patched for predictable order
          ordered-by user;
          key "name";
          leaf name {
            type string;
          }
          uses ncs_template_parameter-map-grouping;
        }
        list regex {
          // NCS patched for predictable order
          ordered-by user;
          key "name";
          leaf name {
            type string;
          }
          list pattern {
            // NCS patched for predictable order
            ordered-by user;
            key "regexp";
            leaf regexp {
              type string;
            }
          }
        }
      }
    }
    container vpdn {
      leaf authen-before-forward {
        type empty;
      }
      leaf enable {
        type empty;
      }
      leaf-list search-order {
        // NCS patched for predictable order
        ordered-by user;
        type string;
      }
    }
    list vpdn-group {
      // NCS patched for predictable order
      ordered-by user;
      key "name";
      leaf name {
        // NCS drop tailf-common:cli-diff-dependency statement
        type string;
      }
      container accept-dialin {
        leaf protocol {
          type string;
        }
        leaf virtual-template {
          type string;
        }
      }
      leaf description {
        type string;
      }
      leaf dsl-line-info-forwarding {
        type empty;
      }
      leaf force-local-chap {
        type empty;
      }
      container ip {
        leaf mtu {
          type string;
        }
        leaf pmtu {
          type empty;
        }
        leaf precedence {
          type string;
          // NCS drop default statement
        }
        leaf tos {
          type string;
          // NCS drop default statement
        }
      }
      container l2tp {
        // NCS drop tailf-common:cli-diff-dependency statement
        // NCS drop when statement
        container attribute {
          container clid {
            container mask-method {
              container remove {
                presence "true";
                leaf match {
                  type string;
                }
              }
              container right {
                leaf character {
                  type string;
                }
                leaf bytes {
                  type string;
                }
                leaf match {
                  type string;
                }
              }
            }
          }
        }
        leaf drop {
          type string;
        }
        leaf hidden {
          type empty;
        }
        leaf ignore {
          type string;
        }
        container ip {
          leaf udp {
            type string;
          }
        }
        container rx-speed {
          leaf ANCP {
            type empty;
          }
          leaf RAM-min {
            // NCS drop when statement
            type empty;
          }
          leaf rx-speed {
            type string;
          }
        }
        leaf sequencing {
          type empty;
        }
        container tunnel {
          leaf authentication {
            type empty;
          }
          container bearer {
            leaf capabilities {
              type string;
            }
          }
          container busy {
            leaf timeout {
              type string;
            }
          }
          container framing {
            leaf capabilities {
              type string;
            }
          }
          leaf hello {
            type string;
            // NCS drop default statement
          }
          container password {
            uses ncs_template_password-grouping;
          }
          leaf receive-window {
            type string;
          }
          leaf resync {
            type string;
          }
          container retransmit {
            container initial {
              leaf retries {
                type string;
              }
              container timeout {
                leaf max {
                  type string;
                }
                leaf min {
                  type string;
                }
              }
            }
            leaf retries {
              type string;
            }
            container timeout {
              leaf max {
                type string;
              }
              leaf min {
                type string;
              }
            }
          }
          container timeout {
            leaf no-session {
              type string;
            }
            leaf setup {
              type string;
            }
          }
          container zlb {
            leaf delay {
              type string;
            }
          }
        }
        container tx-speed {
          leaf ANCP {
            type empty;
          }
          leaf RAM-min {
            // NCS drop when statement
            type empty;
          }
          leaf tx-speed {
            type string;
          }
        }
      }
      container lcp {
        leaf renegotiation {
          type string;
        }
      }
      container local {
        leaf name {
          type string;
        }
      }
      container pptp {
        // NCS drop tailf-common:cli-diff-dependency statement
        // NCS drop when statement
        container flow-control {
          leaf receive-window {
            type string;
          }
          leaf static-rtt {
            type string;
          }
        }
        container relay {
          container pppoe {
            leaf bba-group {
              type string;
            }
          }
        }
        container tunnel {
          leaf echo {
            type string;
            // NCS drop default statement
          }
        }
      }
      container redirect {
        leaf identifier {
          type string;
        }
      }
      container source {
        leaf vpdn-template {
          type string;
        }
      }
      leaf source-ip {
        type string;
      }
      container terminate-from {
        leaf hostname {
          type string;
        }
      }
      container vpn {
        leaf id {
          type string;
        }
        leaf vrf {
          // NCS drop tailf-common:cli-diff-dependency statement
          // NCS drop tailf-common:cli-diff-dependency statement
          type string;
        }
      }
    }
    container bba-group {
      list pppoe {
        // NCS patched for predictable order
        ordered-by user;
        key "id";
        leaf id {
          type string;
        }
        container vendor-tag {
          container circuit-id {
            leaf service {
              type empty;
            }
          }
          container dsl-sync-rate {
            leaf service {
              type empty;
            }
          }
          container remote-id {
            leaf service {
              type empty;
            }
          }
          leaf strip {
            type empty;
          }
        }
        leaf virtual-template {
          type string;
        }
      }
    }
    container tacacs-server {
      // NCS drop tailf-common:cli-diff-dependency statement
      leaf administration {
        type empty;
      }
      list host {
        // NCS patched for predictable order
        ordered-by user;
        key "name";
        leaf name {
          type string;
        }
        leaf port {
          type string;
        }
        leaf timeout {
          type string;
        }
        container key {
          uses ncs_template_password-grouping;
        }
      }
      leaf timeout {
        type string;
        // NCS drop default statement
      }
      container directed-request {
        presence "true";
        leaf restricted {
          type empty;
        }
        leaf no-truncate {
          type empty;
        }
      }
      container key {
        uses ncs_template_password-grouping;
      }
      leaf last-resort {
        type string;
      }
    }
    container tacacs {
      // NCS drop tailf-common:cli-diff-dependency statement
      list server {
        // NCS patched for predictable order
        ordered-by user;
        key "name";
        leaf name {
          type string;
        }
        container address {
          choice address-choice {
            leaf ipv4 {
              type string;
            }
            leaf ipv6 {
              type string;
            }
          }
        }
        container key {
          uses ncs_template_password-grouping;
        }
        leaf port {
          type string;
          // NCS drop default statement
        }
        leaf timeout {
          type string;
        }
        leaf single-connection {
          type empty;
        }
        leaf send-nat-address {
          type empty;
        }
      }
    }
    container udld {
      leaf enable {
        type empty;
      }
      leaf aggressive {
        type empty;
      }
      container message {
        leaf time {
          type string;
        }
      }
    }
    container rep {
      container admin {
        list vlan {
          // NCS patched for predictable order
          ordered-by user;
          key "name";
          leaf name {
            type string;
          }
        }
      }
    }
    container xconnect {
      container logging {
        container pseudowire {
          leaf status {
            type empty;
          }
        }
        leaf redundancy {
          type empty;
        }
      }
    }
    list template {
      // NCS patched for predictable order
      ordered-by user;
      key "name";
      leaf name {
        type string;
      }
      leaf type {
        type string;
      }
      leaf encapsulation {
        type string;
      }
      leaf mtu {
        type string;
      }
      leaf control-word {
        type string;
      }
      container preferred-path {
        choice interface-or-peer {
          leaf interface {
            type string;
          }
          leaf peer {
            type string;
          }
        }
        leaf disable-fallback {
          type empty;
        }
      }
      container signaling {
        leaf protocol {
          type string;
        }
      }
      container dot1x {
        leaf pae {
          type string;
        }
      }
      container spanning-tree {
        container portfast {
          presence "true";
          choice portfast-choice {
            leaf disable {
              type empty;
            }
            leaf network {
              type empty;
            }
            case trunk-mode {
              leaf edge {
                type empty;
              }
              leaf trunk {
                type empty;
              }
            }
          }
        }
        leaf guard {
          type string;
        }
      }
      container mab {
        presence "true";
        leaf eap {
          type empty;
        }
      }
      container access-session {
        leaf port-control {
          type string;
        }
      }
      container authentication {
        leaf periodic {
          type empty;
        }
        container timer {
          leaf reauthenticate {
            type string;
            // NCS drop default statement
          }
        }
      }
      container service-policy {
        container type {
          container control {
            leaf subscriber {
              type string;
            }
          }
        }
      }
    }
    container fabric {
      container switching-mode {
        container allow {
          choice allow-choice {
            leaf bus-mode {
              type empty;
            }
            container truncated {
              presence "true";
              leaf threshold {
                type string;
              }
            }
          }
        }
        container force {
          leaf bus-mode {
            type empty;
          }
        }
      }
      container buffer-reserve {
        leaf queue {
          type empty;
        }
      }
    }
    container port-channel {
      container per-module {
        leaf load-balance {
          type empty;
        }
      }
      leaf load-balance {
        type string;
      }
      leaf load-balance-hash-algo {
        type string;
      }
    }
    container l2protocol-tunnel {
      leaf cos {
        type string;
      }
      container global {
        leaf drop-threshold {
          type string;
        }
      }
    }
    container l2vpn {
      presence "true";
    }
    container l2vpn-vfi {
      container l2vpn {
        container vfi {
          list context {
            // NCS patched for predictable order
            ordered-by user;
            key "name";
            leaf name {
              type string;
            }
            container vpn {
              leaf id {
                type string;
              }
            }
            container autodiscovery {
              container bgp {
                container signaling {
                  presence "true";
                  choice protocol-choice {
                    leaf bgp {
                      type empty;
                    }
                    leaf ldp {
                      type empty;
                    }
                  }
                  leaf template {
                    type string;
                  }
                  container ve {
                    leaf id {
                      type string;
                    }
                  }
                  leaf vpls-id {
                    type string;
                  }
                  container route-target {
                    uses ncs_template_route-target-grouping;
                  }
                }
              }
            }
            container member {
              list ip-address-list {
                // NCS patched for predictable order
                ordered-by user;
                key "ip-address";
                leaf ip-address {
                  type string;
                }
                choice encapsulation-template-choice {
                  leaf encapsulation {
                    type string;
                  }
                  leaf template {
                    type string;
                  }
                }
              }
              list ip-address-vc-id-list {
                // NCS patched for predictable order
                ordered-by user;
                key "ip-address vc-id";
                leaf ip-address {
                  type string;
                }
                leaf vc-id {
                  type string;
                }
                choice encapsulation-template-choice {
                  leaf encapsulation {
                    type string;
                  }
                  leaf template {
                    type string;
                  }
                }
              }
              list pseudowire {
                // NCS patched for predictable order
                ordered-by user;
                key "name";
                leaf name {
                  type string;
                }
                leaf ip-address {
                  type string;
                }
                leaf vc-id {
                  type string;
                }
                choice encapsulation-template-choice {
                  leaf encapsulation {
                    type string;
                  }
                  leaf template {
                    type string;
                  }
                }
              }
            }
            leaf mtu {
              type string;
            }
          }
        }
      }
    }
    container l2vpn-xconnect {
      container l2vpn {
        container xconnect {
          list context {
            // NCS patched for predictable order
            ordered-by user;
            key "name";
            leaf name {
              type string;
            }
            container remote {
              container link {
                container failure {
                  leaf notification {
                    type string;
                    // NCS drop default statement
                  }
                }
              }
            }
            leaf interworking {
              type string;
            }
            container member {
              list member-list {
                // NCS patched for predictable order
                ordered-by user;
                key "name";
                leaf name {
                  type string;
                }
                leaf service-instance {
                  // NCS drop tailf-common:cli-diff-dependency statement
                  // NCS drop tailf-common:cli-diff-dependency statement
                  // NCS drop tailf-common:cli-diff-dependency statement
                  // NCS drop tailf-common:cli-diff-dependency statement
                  // NCS drop tailf-common:cli-diff-dependency statement
                  // NCS drop tailf-common:cli-diff-dependency statement
                  // NCS drop tailf-common:cli-diff-dependency statement
                  // NCS drop tailf-common:cli-diff-dependency statement
                  type string;
                }
                leaf group {
                  type string;
                }
                leaf priority {
                  type string;
                }
              }
              list pseudowire {
                // NCS patched for predictable order
                ordered-by user;
                key "name";
                leaf name {
                  type string;
                }
              }
              list address-list {
                // NCS patched for predictable order
                ordered-by user;
                key "name";
                leaf name {
                  type string;
                }
                leaf vcid {
                  type string;
                }
                choice encap-or-termplate {
                  leaf encapsulation {
                    type string;
                  }
                  leaf template {
                    type string;
                  }
                }
                leaf group {
                  type string;
                }
                leaf priority {
                  type string;
                }
              }
            }
            container redundancy {
              leaf predictive {
                type string;
              }
              list delay {
                // NCS patched for predictable order
                ordered-by user;
                key "group";
                leaf group {
                  type string;
                }
                leaf enable-delay {
                  type string;
                }
                leaf disable-delay {
                  type string;
                }
              }
            }
          }
        }
      }
    }
    container l2vpn-evpn {
      container l2vpn {
        container evpn {
          list instance {
            // NCS patched for predictable order
            ordered-by user;
            key "id";
            leaf id {
              type string;
            }
            leaf point-to-point {
              type empty;
            }
            container vpws {
              list context {
                // NCS patched for predictable order
                ordered-by user;
                key "name";
                leaf name {
                  type string;
                }
                container service {
                  leaf target {
                    type string;
                  }
                  leaf source {
                    type string;
                  }
                }
                container member {
                  leaf interface {
                    type string;
                  }
                  leaf service-instance {
                    // NCS drop tailf-common:cli-diff-dependency statement
                    // NCS drop tailf-common:cli-diff-dependency statement
                    // NCS drop tailf-common:cli-diff-dependency statement
                    // NCS drop tailf-common:cli-diff-dependency statement
                    // NCS drop tailf-common:cli-diff-dependency statement
                    // NCS drop tailf-common:cli-diff-dependency statement
                    // NCS drop tailf-common:cli-diff-dependency statement
                    // NCS drop tailf-common:cli-diff-dependency statement
                    type string;
                  }
                }
              }
            }
          }
        }
      }
    }
    container segment-routing {
      container mpls {
        presence "true";
        leaf shutdown {
          type empty;
        }
        container global-block {
          leaf start {
            type string;
          }
          leaf end {
            type string;
          }
        }
        container connected-prefix-sid-map {
          container address-family {
            container ipv4 {
              list address-list {
                // NCS patched for predictable order
                ordered-by user;
                key "prefix";
                leaf prefix {
                  type string;
                }
                choice absolute-or-index {
                  leaf absolute {
                    type string;
                  }
                  leaf index {
                    type string;
                  }
                }
                leaf range {
                  type string;
                }
              }
            }
          }
        }
      }
    }
    container system {
      container env {
        container temperature {
          container threshold {
            leaf yellow {
              type string;
            }
          }
        }
      }
      container mtu {
        leaf size {
          type string;
        }
        leaf jumbo {
          type string;
        }
        leaf routing {
          type string;
        }
      }
      container flowcontrol {
        container bus {
          leaf auto {
            type empty;
          }
        }
      }
      leaf jumbomtu {
        type string;
      }
    }
    container stackmaker {
      leaf name {
        type string;
      }
    }
    container diagnostic {
      container bootup {
        leaf level {
          type string;
        }
      }
      container cns {
        leaf publish {
          type string;
        }
        leaf subscribe {
          type string;
        }
      }
      container monitor {
        leaf syslog {
          type empty;
        }
      }
    }
    container errdisable {
      container detect {
        container cause {
          leaf all {
            type empty;
          }
          leaf arp-inspection {
            type empty;
          }
          leaf bpduguard {
            type empty;
          }
          leaf dhcp-rate-limit {
            type empty;
          }
          leaf dtp-flap {
            type empty;
          }
          leaf gbic-invalid {
            type empty;
          }
          leaf inline-power {
            type empty;
          }
          leaf l2ptguard {
            type empty;
          }
          leaf link-flap {
            type empty;
          }
          leaf loopback {
            type empty;
          }
          leaf mlacp-minlink {
            type empty;
          }
          leaf pagp-flap {
            type empty;
          }
          leaf pppoe-ia-rate-limit {
            type empty;
          }
          leaf security-violation {
            type empty;
          }
          leaf sfp-config-mismatch {
            type empty;
          }
          leaf small-frame {
            type empty;
          }
        }
      }
      container flap-setting {
        container cause {
          container dtp-flap {
            leaf max-flaps {
              type string;
            }
            leaf time {
              type string;
            }
          }
          container link-flap {
            leaf max-flaps {
              type string;
            }
            leaf time {
              type string;
            }
          }
          container pagp-flap {
            leaf max-flaps {
              type string;
            }
            leaf time {
              type string;
            }
          }
        }
      }
      container recovery {
        container cause {
          leaf all {
            type empty;
          }
          leaf arp-inspection {
            type empty;
          }
          leaf bpduguard {
            type empty;
          }
          leaf channel-misconfig {
            type empty;
          }
          leaf dhcp-rate-limit {
            type empty;
          }
          leaf dtp-flap {
            type empty;
          }
          leaf gbic-invalid {
            type empty;
          }
          leaf inline-power {
            type empty;
          }
          leaf l2ptguard {
            type empty;
          }
          leaf link-flap {
            type empty;
          }
          leaf link-monitor-failure {
            type empty;
          }
          leaf loopback {
            type empty;
          }
          leaf mac-limit {
            type empty;
          }
          leaf mlacp-minlink {
            type empty;
          }
          container oam-remote-failure {
            presence "true";
            leaf critical-event {
              type empty;
            }
            leaf dying-gasp {
              type empty;
            }
            leaf link-fault {
              type empty;
            }
          }
          leaf pagp-flap {
            type empty;
          }
          leaf port-mode-failure {
            type empty;
          }
          leaf pppoe-ia-rate-limit {
            type empty;
          }
          leaf psp {
            type empty;
          }
          leaf psecure-violation {
            type empty;
          }
          leaf security-violation {
            type empty;
          }
          leaf sfp-config-mismatch {
            type empty;
          }
          leaf small-frame {
            type empty;
          }
          leaf storm-control {
            type empty;
          }
          leaf udld {
            type empty;
          }
          leaf unicast-flood {
            type empty;
          }
          leaf vmps {
            type empty;
          }
        }
        leaf interval {
          type string;
        }
      }
    }
    container monitor {
      list session {
        // NCS patched for predictable order
        ordered-by user;
        key "id";
        leaf id {
          type string;
        }
        list destination {
          // NCS patched for predictable order
          ordered-by user;
          key "id";
          leaf id {
            type string;
          }
        }
        list source {
          // NCS patched for predictable order
          ordered-by user;
          key "id";
          leaf id {
            type string;
          }
        }
        container filter {
          leaf-list vlan {
            // NCS patched for predictable order
            ordered-by user;
            type string;
          }
          container packet-type {
            container good {
              // NCS drop tailf-common:cli-diff-dependency statement
              leaf rx {
                type empty;
              }
            }
            container bad {
              // NCS drop tailf-common:cli-diff-dependency statement
              leaf rx {
                type empty;
              }
            }
          }
          container ip {
            leaf access-group {
              type string;
            }
          }
          container mac {
            leaf access-group {
              type string;
            }
          }
          container ipv6 {
            leaf access-group {
              type string;
            }
          }
        }
      }
      container session-local {
        list session {
          // NCS patched for predictable order
          ordered-by user;
          key "id";
          leaf id {
            type string;
          }
          leaf type {
            type string;
          }
          leaf shutdown {
            type empty;
          }
          container source {
            container interface {
              uses ncs_template_interface-name-grouping;
              leaf hyphen {
                tailf:alt-name "-";
                type empty;
              }
              leaf port {
                type string;
              }
            }
          }
          container destination {
            container interface {
              uses ncs_template_interface-name-grouping;
              leaf hyphen {
                tailf:alt-name "-";
                type empty;
              }
              leaf port {
                type string;
              }
            }
          }
        }
      }
      container session-erspan-source {
        list session {
          // NCS patched for predictable order
          ordered-by user;
          key "id";
          leaf id {
            type string;
          }
          leaf type {
            type string;
          }
          leaf shutdown {
            type empty;
          }
          container source {
            container interface {
              uses ncs_template_interface-name-grouping;
              leaf hyphen {
                tailf:alt-name "-";
                type empty;
              }
              leaf port {
                type string;
              }
            }
          }
          container destination {
            leaf erspan-id {
              type string;
            }
            leaf mtu {
              type string;
            }
            container ip {
              leaf address {
                type string;
              }
            }
            container origin {
              container ip {
                leaf address {
                  type string;
                }
              }
            }
          }
        }
      }
      container session-erspan-destination {
        list session {
          // NCS patched for predictable order
          ordered-by user;
          key "id";
          leaf id {
            type string;
          }
          leaf type {
            type string;
          }
          leaf shutdown {
            type empty;
          }
          container source {
            leaf erspan-id {
              type string;
            }
            container ip {
              leaf address {
                type string;
              }
              leaf force {
                type empty;
              }
            }
          }
        }
      }
      container session-conf {
        container session {
          leaf servicemodule {
            type string;
            // NCS drop default statement
          }
        }
      }
      container event-trace {
        list event-trace-list {
          // NCS patched for predictable order
          ordered-by user;
          key "name";
          leaf name {
            type string;
          }
        }
      }
    }
    container network-clock {
      leaf revertive {
        type empty;
      }
      container synchronization {
        leaf automatic {
          type empty;
        }
        container mode {
          leaf QL-enabled {
            type empty;
          }
        }
      }
      list input-source {
        // NCS patched for predictable order
        ordered-by user;
        key "priority";
        leaf priority {
          type string;
        }
        container interface {
          uses ncs_template_interface-name-grouping;
        }
        container ptp {
          leaf domain {
            type string;
          }
        }
      }
      container output-source {
        list system {
          // NCS patched for predictable order
          ordered-by user;
          key "priority";
          leaf priority {
            type string;
          }
          list External {
            // NCS patched for predictable order
            ordered-by user;
            key "name";
            leaf name {
              type string;
            }
            leaf e1 {
              type string;
            }
            leaf ohms {
              type string;
            }
            leaf linecode {
              type string;
            }
          }
        }
      }
      container wait-to-restore {
        leaf seconds {
          type string;
        }
        leaf global {
          type empty;
        }
      }
    }
    container esmc {
      leaf process {
        type empty;
      }
    }
    container netconf-yang {
      container cisco-ia {
        container snmp-trap-control {
          leaf trap-list {
            type string;
          }
        }
      }
      container cisco-odm {
        leaf actions {
          type string;
        }
      }
    }
    list tftp-server {
      // NCS patched for predictable order
      ordered-by user;
      key "name";
      leaf name {
        type string;
      }
      leaf alias {
        type string;
      }
      leaf access-list {
        type string;
      }
    }
    container radius-server {
      container load-balance {
        container method {
          container least-outstanding {
            presence "true";
          }
        }
      }
      container attribute {
        list attribute-list {
          // NCS patched for predictable order
          ordered-by user;
          key "id";
          leaf id {
            type string;
          }
          leaf on-for-login-auth {
            type empty;
          }
          leaf support-multiple {
            type empty;
          }
          leaf mandatory {
            type empty;
          }
          leaf include-in-access-req {
            type empty;
          }
          container access-request {
            leaf include {
              type empty;
            }
          }
        }
      }
      container dead-criteria {
        leaf time {
          type string;
        }
        leaf tries {
          type string;
        }
      }
      leaf deadtime {
        type string;
      }
      list host {
        // NCS patched for predictable order
        ordered-by user;
        key "id";
        leaf id {
          type string;
        }
        uses ncs_template_radius-server-grouping;
      }
      leaf retransmit {
        type string;
        // NCS drop default statement
      }
      leaf timeout {
        type string;
        // NCS drop default statement
      }
      container vsa {
        container send {
          leaf accounting {
            type empty;
          }
          leaf authentication {
            type empty;
          }
        }
      }
      container key {
        uses ncs_template_password-grouping;
      }
    }
    container radius {
      list filter {
        // NCS patched for predictable order
        ordered-by user;
        key "id";
        leaf id {
          type string;
        }
        leaf match {
          type string;
        }
      }
      list server {
        // NCS patched for predictable order
        ordered-by user;
        key "id";
        leaf id {
          type string;
        }
        container address {
          container ipv4 {
            leaf host {
              type string;
            }
            leaf auth-port {
              type string;
            }
            leaf acct-port {
              type string;
            }
          }
        }
        container backoff {
          container exponential {
            presence "true";
            leaf max-delay {
              type string;
            }
            leaf backoff-retry {
              type string;
            }
          }
        }
        container key {
          leaf type {
            type string;
          }
          leaf secret {
            type string;
          }
        }
      }
    }
    container zone {
      list security {
        // NCS patched for predictable order
        ordered-by user;
        key "id";
        leaf id {
          type string;
        }
        leaf description {
          type string;
        }
        leaf protection {
          // NCS drop tailf-common:cli-diff-dependency statement
          type string;
        }
      }
    }
    container zone-pair {
      list security {
        // NCS patched for predictable order
        ordered-by user;
        key "id";
        leaf id {
          type string;
        }
        leaf source {
          type string;
        }
        leaf destination {
          type string;
        }
        leaf description {
          type string;
        }
        container service-policy {
          container type {
            leaf inspect {
              type string;
            }
          }
        }
      }
    }
    list alarm-contact {
      // NCS patched for predictable order
      ordered-by user;
      key "name";
      leaf name {
        type string;
      }
      leaf description {
        type string;
      }
      leaf severity {
        type string;
      }
      leaf trigger {
        type string;
      }
    }
    container mpls {
      container atm {
        leaf disable-headend-vc {
          type empty;
        }
      }
      leaf cos-map {
        type string;
      }
      leaf ip {
        type string;
        // NCS drop default statement
      }
      container mpls-ip-conf {
        container ip {
          leaf default-route {
            type empty;
          }
          choice propagate-ttl-choice {
            container propagate-ttl-conf {
              leaf propagate-ttl {
                type string;
                // NCS drop default statement
              }
            }
            container propagate-ttl {
              leaf forwarded {
                type string;
                // NCS drop default statement
              }
            }
          }
          container ttl-expiration {
            leaf pop {
              type string;
            }
          }
        }
      }
      container label {
        container atm {
          leaf disable-headend-vc {
            type empty;
          }
        }
        leaf protocol {
          type string;
        }
        container range {
          leaf min {
            type string;
          }
          leaf max {
            type string;
          }
          leaf static {
            type empty;
          }
          leaf static-min {
            type string;
          }
          leaf static-max {
            type string;
          }
        }
      }
      container ldp {
        leaf advertise-labels {
          type string;
          // NCS drop default statement
        }
        leaf nsr {
          type empty;
        }
        container advertise-labels-conf {
          container advertise-labels {
            container for {
              leaf from {
                type string;
              }
              leaf to {
                type string;
              }
            }
            container interface {
              uses ncs_template_interface-name-grouping;
            }
            leaf oldstyle {
              type empty;
            }
          }
        }
        container password {
          container required {
            presence "true";
          }
          container fallback {
            choice fallback-choice {
              leaf key-chain {
                type string;
              }
              case password-case {
                uses ncs_template_password-grouping;
              }
            }
          }
        }
        container atm {
          leaf control-mode {
            type string;
          }
          leaf vc-merge {
            type string;
            // NCS drop default statement
          }
        }
        container backoff {
          leaf initial {
            type string;
          }
          leaf max {
            type string;
          }
        }
        container discovery {
          container hello {
            leaf holdtime {
              type string;
            }
            leaf interval {
              type string;
            }
          }
          container targeted-hello {
            container accept {
              presence "Accept targeted hellos";
              leaf from {
                type string;
              }
            }
            leaf holdtime {
              type string;
            }
            leaf interval {
              type string;
            }
          }
        }
        container explicit-null {
          presence "true";
          leaf for {
            type string;
          }
          leaf to {
            type string;
          }
        }
        leaf loop-detection {
          type empty;
        }
        container graceful-restart {
          presence "Configure Graceful Restart timers";
          container timers {
            leaf forwarding-holding {
              type string;
            }
            leaf max-recovery {
              type string;
            }
            leaf neighbor-liveness {
              type string;
            }
          }
        }
        leaf holdtime {
          type string;
        }
        container logging {
          leaf neighbor-changes {
            type empty;
          }
        }
        leaf maxhops {
          type string;
        }
        list neighbor {
          // NCS patched for predictable order
          ordered-by user;
          key "address";
          leaf address {
            type string;
          }
          leaf implicit-withdraw {
            type empty;
          }
          container labels {
            leaf accept {
              type string;
            }
          }
          container password {
            uses ncs_template_password-grouping;
          }
          container targeted {
            presence "Establish targeted session";
            leaf protocol {
              type string;
            }
          }
        }
        container request-labels {
          leaf for {
            type string;
          }
        }
        container router-id {
          leaf interface {
            // NCS drop tailf-common:cli-diff-dependency statement
            type string;
          }
          leaf force {
            type empty;
          }
        }
        container session {
          container protection {
            presence "true";
            leaf duration {
              type string;
            }
          }
        }
        container label {
          container allocate {
            container global {
              presence "true";
              choice global-choice {
                leaf host-routes {
                  type empty;
                }
                leaf prefix-list {
                  type string;
                }
              }
            }
          }
        }
        container igp {
          container sync {
            leaf holddown {
              type string;
            }
          }
        }
      }
      container prefix-map {
        leaf nr {
          type string;
        }
        leaf access-list {
          type string;
        }
        leaf cos-map {
          type string;
        }
      }
      container traffic-eng {
        container auto-bw {
          container timers {
            presence "Enable auto-bw Timers Collection and Application";
            leaf frequency {
              type string;
            }
          }
        }
        container link-management {
          container timers {
            leaf bandwidth-hold {
              type string;
            }
            leaf periodic-flooding {
              type string;
            }
          }
        }
        container logging {
          container lsp {
            container path-errors {
              presence "Log LSP Path Error traps";
              leaf access-list {
                type string;
              }
            }
            container preemption {
              presence "Log LSP Preemption traps";
              leaf access-list {
                type string;
              }
            }
            container reservation-errors {
              presence "Log LSP Reservation Error traps";
              leaf access-list {
                type string;
              }
            }
            container setups {
              presence "Log LSP Establishment Traps";
              leaf access-list {
                type string;
              }
            }
            container teardowns {
              presence "Log LSP Teardown Traps";
              leaf access-list {
                type string;
              }
            }
          }
          container tunnel {
            container lsp-selection {
              presence "Log Tunnel LSP Selection traps";
              leaf access-list {
                type string;
              }
            }
            container path {
              container change {
                presence "Log Tunnel Path change traps";
                leaf access-list {
                  type string;
                }
              }
            }
          }
        }
        container auto-tunnel {
          leaf backup {
            type empty;
          }
          container backup-conf {
            container backup {
              leaf nhop-only {
                type empty;
              }
              container tunnel-num {
                leaf min {
                  type string;
                }
                leaf max {
                  type string;
                }
              }
            }
          }
          container primary {
            container config {
              container mpls {
                leaf ip {
                  type empty;
                }
              }
            }
            container tunnel-num {
              leaf min {
                type string;
              }
              leaf max {
                type string;
              }
            }
          }
        }
        container path-selection {
          leaf metric {
            type string;
            // NCS drop default statement
          }
          container overload {
            leaf allow {
              type string;
            }
          }
        }
        container reoptimize {
          container events {
            leaf link-up {
              type empty;
            }
          }
          container timers {
            container delay {
              leaf cleanup {
                type string;
              }
              leaf installation {
                type string;
              }
            }
            leaf frequency {
              type string;
            }
          }
        }
        container signalling {
          container advertise {
            container implicit-null {
              presence "Use MPLS encoding for Implicit-Null Label in signalling messages";
              leaf nr {
                type string;
              }
            }
          }
          container forwarding {
            leaf sync {
              type empty;
            }
          }
          container restart {
            container neighbors {
              presence "Identify signalling restart capable neighbors";
              leaf nr {
                type string;
              }
            }
          }
        }
        container topology {
          container holddown {
            leaf sigerr {
              type string;
            }
          }
        }
        leaf tunnels {
          type empty;
        }
      }
      leaf propagate-cos {
        type empty;
      }
      container discovery {
        container vpn {
          leaf interval {
            type string;
          }
          leaf next-hop {
            type empty;
          }
        }
      }
    }
    container clns {
      leaf routing {
        type empty;
      }
      list filter-set {
        // NCS patched for predictable order
        ordered-by user;
        key "name";
        leaf name {
          type string;
        }
        leaf operation {
          type string;
        }
        leaf template {
          type string;
        }
      }
    }
    container l3-over-l2 {
      container flush {
        leaf buffers {
          type empty;
        }
      }
    }
    container l3vpn {
      container encapsulation {
        list ip {
          // NCS patched for predictable order
          ordered-by user;
          key "name";
          leaf name {
            type string;
          }
          container transport {
            container ipv4 {
              presence "true";
              container source {
                uses ncs_template_interface-name-grouping;
              }
            }
          }
        }
      }
    }
    container router {
      container mobile {
        // NCS drop tailf-common:cli-diff-dependency statement
        presence "true";
      }
      list bgp {
        // NCS patched for predictable order
        ordered-by user;
        // NCS drop tailf-common:cli-diff-dependency statement
        // NCS drop tailf-common:cli-diff-dependency statement
        // NCS drop tailf-common:cli-diff-dependency statement
        // NCS drop max-elements statement
        key "as-no";
        leaf as-no {
          // NCS drop tailf-common:cli-diff-dependency statement
          type string;
        }
        container template {
          list peer-policy {
            // NCS patched for predictable order
            ordered-by user;
            key "name";
            leaf name {
              type string;
            }
            leaf peer-group {
              tailf:hidden "all";
              type empty;
            }
            leaf remote-as {
              tailf:hidden "all";
              type empty;
            }
            leaf activate {
              tailf:hidden "all";
              type empty;
            }
            container inherit {
              // NCS drop tailf-common:cli-diff-dependency statement
              // NCS drop tailf-common:cli-diff-dependency statement
              // NCS drop tailf-common:cli-diff-dependency statement
              leaf peer-policy {
                type string;
              }
              leaf sequence {
                type string;
              }
              leaf peer-session {
                tailf:hidden "all";
                type empty;
              }
            }
            uses ncs_template_router-bgp-peer-policy-grouping;
          }
          list peer-session {
            // NCS patched for predictable order
            ordered-by user;
            key "name";
            leaf name {
              type string;
            }
            leaf remote-as {
              type string;
            }
            leaf peer-group {
              tailf:hidden "all";
              type empty;
            }
            leaf activate {
              tailf:hidden "all";
              type empty;
            }
            uses ncs_template_description-grouping;
            container inherit {
              // NCS drop tailf-common:cli-diff-dependency statement
              // NCS drop tailf-common:cli-diff-dependency statement
              // NCS drop tailf-common:cli-diff-dependency statement
              leaf peer-session {
                type string;
              }
            }
            uses ncs_template_router-bgp-peer-session-grouping;
          }
        }
        uses ncs_template_router-bgp-bgp-grouping;
        uses ncs_template_router-bgp-af-grouping {
          refine "neighbor/password/text";
          refine "neighbor-tag/neighbor/password/text";
        }
        container address-family {
          list ipv4 {
            // NCS patched for predictable order
            ordered-by user;
            key "af";
            leaf af {
              type string;
            }
            uses ncs_template_router-bgp-af-grouping {
              refine "neighbor" {
                // NCS drop tailf-common:cli-diff-dependency statement
              }
            }
          }
          list ipv6 {
            // NCS patched for predictable order
            ordered-by user;
            // NCS drop tailf-common:cli-diff-dependency statement
            key "af";
            leaf af {
              type string;
            }
            uses ncs_template_router-bgp-af-grouping {
              refine "neighbor" {
                // NCS drop tailf-common:cli-diff-dependency statement
              }
            }
          }
          container with-vrf {
            list ipv4 {
              // NCS patched for predictable order
              ordered-by user;
              key "af";
              leaf af {
                type string;
              }
              list vrf {
                // NCS patched for predictable order
                ordered-by user;
                key "name";
                leaf name {
                  // NCS drop tailf-common:cli-diff-dependency statement
                  // NCS drop tailf-common:cli-diff-dependency statement
                  type string;
                }
                uses ncs_template_router-bgp-bgp-grouping;
                uses ncs_template_router-bgp-af-grouping {
                  refine "neighbor" {
                    // NCS drop tailf-common:cli-diff-dependency statement
                    // NCS drop tailf-common:cli-diff-dependency statement
                  }
                  refine "neighbor/password/text";
                }
              }
            }
          }
          container ipv6-with-vrf {
            list ipv6 {
              // NCS patched for predictable order
              ordered-by user;
              // NCS drop tailf-common:cli-diff-dependency statement
              key "af";
              leaf af {
                type string;
              }
              list vrf {
                // NCS patched for predictable order
                ordered-by user;
                key "name";
                leaf name {
                  // NCS drop tailf-common:cli-diff-dependency statement
                  // NCS drop tailf-common:cli-diff-dependency statement
                  type string;
                }
                uses ncs_template_router-bgp-bgp-grouping;
                uses ncs_template_router-bgp-af-grouping {
                  refine "neighbor" {
                    // NCS drop tailf-common:cli-diff-dependency statement
                  }
                  refine "neighbor/password/text";
                }
              }
            }
          }
          list vpnv4 {
            // NCS patched for predictable order
            ordered-by user;
            key "af";
            leaf af {
              type string;
            }
            uses ncs_template_router-bgp-af-grouping {
              refine "neighbor" {
                // NCS drop tailf-common:cli-diff-dependency statement
              }
            }
          }
          list vpnv6 {
            // NCS patched for predictable order
            ordered-by user;
            key "af";
            leaf af {
              // NCS drop tailf-common:cli-diff-dependency statement
              type string;
            }
            uses ncs_template_router-bgp-af-grouping {
              refine "neighbor" {
                // NCS drop tailf-common:cli-diff-dependency statement
              }
            }
          }
          list l2vpn {
            // NCS patched for predictable order
            ordered-by user;
            key "af";
            leaf af {
              type string;
            }
            uses ncs_template_router-bgp-af-grouping {
              refine "neighbor" {
                // NCS drop tailf-common:cli-diff-dependency statement
              }
            }
          }
          list nsap {
            // NCS patched for predictable order
            ordered-by user;
            key "af";
            leaf af {
              type string;
            }
            uses ncs_template_router-bgp-af-grouping {
              refine "neighbor" {
                // NCS drop tailf-common:cli-diff-dependency statement
              }
            }
          }
          list rtfilter {
            // NCS patched for predictable order
            ordered-by user;
            key "af";
            leaf af {
              type string;
            }
            uses ncs_template_router-bgp-af-grouping {
              refine "neighbor" {
                // NCS drop tailf-common:cli-diff-dependency statement
              }
            }
          }
        }
      }
      container eigrp-virtual-instance {
        list eigrp {
          // NCS patched for predictable order
          ordered-by user;
          // NCS drop tailf-common:cli-diff-dependency statement
          key "name";
          leaf name {
            type string;
          }
          container address-family {
            container ipv4-vrf {
              container ipv4 {
                container unicast {
                  list vrf {
                    // NCS patched for predictable order
                    ordered-by user;
                    key "name";
                    leaf name {
                      // NCS drop tailf-common:cli-diff-dependency statement
                      // NCS drop tailf-common:cli-diff-dependency statement
                      type string;
                    }
                    leaf autonomous-system {
                      type string;
                    }
                    uses ncs_template_router-eigrp-af-virtual-instance-grouping;
                  }
                }
              }
            }
            container ipv4 {
              presence "true";
              leaf af {
                type string;
              }
              leaf autonomous-system {
                type string;
              }
              uses ncs_template_router-eigrp-af-virtual-instance-grouping;
            }
            container ipv6-vrf {
              container ipv6 {
                container unicast {
                  list vrf {
                    // NCS patched for predictable order
                    ordered-by user;
                    key "name";
                    leaf name {
                      // NCS drop tailf-common:cli-diff-dependency statement
                      // NCS drop tailf-common:cli-diff-dependency statement
                      type string;
                    }
                    leaf autonomous-system {
                      type string;
                    }
                    uses ncs_template_router-eigrp-af-virtual-instance-grouping;
                  }
                }
              }
            }
            container ipv6 {
              presence "true";
              leaf af {
                type string;
              }
              leaf autonomous-system {
                type string;
              }
              uses ncs_template_router-eigrp-af-virtual-instance-grouping;
            }
          }
        }
      }
      list eigrp {
        // NCS patched for predictable order
        ordered-by user;
        // NCS drop tailf-common:cli-diff-dependency statement
        key "as-no";
        leaf as-no {
          type string;
        }
        container address-family {
          container ipv4 {
            list vrf {
              // NCS patched for predictable order
              ordered-by user;
              key "name";
              leaf name {
                // NCS drop tailf-common:cli-diff-dependency statement
                // NCS drop tailf-common:cli-diff-dependency statement
                type string;
              }
              leaf autonomous-system {
                type string;
              }
              uses ncs_template_router-eigrp-grouping;
              uses ncs_template_router-eigrp-base-grouping;
            }
          }
        }
        uses ncs_template_router-eigrp-grouping;
        uses ncs_template_router-eigrp-base-grouping;
      }
      list ospfv3 {
        // NCS patched for predictable order
        ordered-by user;
        // NCS drop tailf-common:cli-diff-dependency statement
        key "id";
        leaf id {
          type string;
        }
        uses ncs_template_router-ospfv3-grouping;
        uses ncs_template_router-ospf-common-grouping;
        leaf shutdown {
          type empty;
        }
        container address-family {
          container ipv4 {
            container unicast {
              uses ncs_template_router-ospfv3-grouping;
              uses ncs_template_router-ospf-common-grouping;
              uses ncs_template_router-ospf-common-af-grouping;
              uses ncs_template_router-ospfv3-af-grouping;
            }
          }
          container ipv6 {
            container unicast {
              uses ncs_template_router-ospfv3-grouping;
              uses ncs_template_router-ospf-common-grouping;
              uses ncs_template_router-ospf-common-af-grouping;
              uses ncs_template_router-ospfv3-af-grouping;
            }
          }
          container ipv4-vrf {
            container ipv4 {
              container unicast {
                list vrf {
                  // NCS patched for predictable order
                  ordered-by user;
                  key "name";
                  leaf name {
                    // NCS drop tailf-common:cli-diff-dependency statement
                    // NCS drop tailf-common:cli-diff-dependency statement
                    type string;
                  }
                  uses ncs_template_router-ospfv3-grouping;
                  uses ncs_template_router-ospf-common-grouping;
                  uses ncs_template_router-ospf-common-af-grouping;
                  uses ncs_template_router-ospfv3-af-grouping;
                }
              }
            }
          }
          container ipv6-vrf {
            container ipv6 {
              container unicast {
                list vrf {
                  // NCS patched for predictable order
                  ordered-by user;
                  key "name";
                  leaf name {
                    // NCS drop tailf-common:cli-diff-dependency statement
                    // NCS drop tailf-common:cli-diff-dependency statement
                    type string;
                  }
                  uses ncs_template_router-ospfv3-grouping;
                  uses ncs_template_router-ospf-common-grouping;
                  uses ncs_template_router-ospf-common-af-grouping;
                  uses ncs_template_router-ospfv3-af-grouping;
                }
              }
            }
          }
        }
      }
      list ospf {
        // NCS patched for predictable order
        ordered-by user;
        // NCS drop tailf-common:cli-diff-dependency statement
        key "id";
        leaf id {
          type string;
        }
        leaf vrf {
          // NCS drop tailf-common:cli-diff-dependency statement
          // NCS drop tailf-common:cli-diff-dependency statement
          type string;
        }
        uses ncs_template_router-ospf-common-grouping {
          refine "area";
        }
        uses ncs_template_router-ospf-common-af-grouping;
        uses ncs_template_router-ospf-grouping;
      }
      container isis {
        // NCS drop tailf-common:cli-diff-dependency statement
        presence "true";
        uses ncs_template_router-isis-grouping;
      }
      container isis-container {
        list isis {
          // NCS patched for predictable order
          ordered-by user;
          // NCS drop tailf-common:cli-diff-dependency statement
          key "area-tag";
          leaf area-tag {
            type string;
          }
          uses ncs_template_router-isis-grouping;
        }
      }
      container rip {
        uses ncs_template_router-rip-grouping {
          refine "version" {
            // NCS drop tailf-common:cli-diff-dependency statement
          }
        }
        container address-family {
          container ipv4 {
            container unicast {
              // NCS drop tailf-common:cli-diff-dependency statement
              uses ncs_template_router-rip-grouping;
            }
            list vrf {
              // NCS patched for predictable order
              ordered-by user;
              // NCS drop tailf-common:cli-diff-dependency statement
              key "name";
              leaf name {
                // NCS drop tailf-common:cli-diff-dependency statement
                // NCS drop tailf-common:cli-diff-dependency statement
                type string;
              }
              uses ncs_template_router-rip-af-grouping;
            }
          }
        }
      }
      container lisp {
        // NCS drop tailf-common:cli-diff-dependency statement
        presence "true";
        uses ncs_template_router-lisp-grouping {
          refine "eid-table/vrf/name" {
            // NCS drop tailf-common:cli-diff-dependency statement
            // NCS drop tailf-common:cli-diff-dependency statement
          }
          refine "site/authentication-key/secret";
          refine "ipv4/etr/map-server/key/secret";
        }
      }
      container router-lisp {
        list lisp {
          // NCS patched for predictable order
          ordered-by user;
          key "id";
          leaf id {
            type string;
          }
          uses ncs_template_router-lisp-grouping {
            refine "eid-table/vrf/name" {
              // NCS drop tailf-common:cli-diff-dependency statement
              // NCS drop tailf-common:cli-diff-dependency statement
            }
          }
        }
      }
      container odr {
        presence "true";
      }
    }
    container vstack-conf {
      container vstack {
        leaf director {
          type string;
        }
        leaf basic {
          type empty;
        }
      }
    }
    container vstack-no {
      leaf vstack {
        type string;
        // NCS drop default statement
      }
    }
    container snmp {
      container ifmib {
        container ifindex {
          leaf persist {
            type empty;
          }
        }
        container ifalias {
          leaf long {
            type empty;
          }
        }
        container trap {
          leaf throttle {
            type empty;
          }
        }
      }
      container mib {
        container bulkstat {
          list object-list {
            // NCS patched for predictable order
            ordered-by user;
            key "name";
            leaf name {
              type string;
            }
          }
        }
        container persist {
          leaf v3mibs {
            type empty;
          }
          leaf dsmib {
            type empty;
          }
          leaf cbqos {
            type empty;
          }
          leaf circuit {
            type empty;
          }
        }
      }
    }
    list menu {
      // NCS patched for predictable order
      ordered-by user;
      key "name";
      leaf name {
        type string;
      }
      leaf title {
        type string;
      }
      list command {
        // NCS patched for predictable order
        ordered-by user;
        key "item";
        leaf item {
          type string;
        }
        leaf command {
          type string;
        }
      }
      leaf clear-screen {
        type empty;
      }
      leaf status-line {
        type empty;
      }
      leaf line-mode {
        type empty;
      }
      leaf single-space {
        type empty;
      }
    }
    container snmp-server {
      list user {
        // NCS patched for predictable order
        ordered-by user;
        key "name";
        leaf name {
          // NCS drop tailf-common:cli-diff-dependency statement
          type string;
        }
        leaf group {
          type string;
        }
        choice security-model {
          leaf v1 {
            type empty;
          }
          leaf v2c {
            type empty;
          }
          case v3 {
            leaf v3 {
              type empty;
            }
            leaf encrypted {
              type string;
              // NCS drop default statement
            }
            leaf auth {
              type string;
            }
            leaf auth-password {
              // NCS drop when statement
              type string;
            }
            leaf priv {
              type string;
            }
            leaf bits {
              // NCS drop when statement
              type string;
            }
            leaf priv-password {
              // NCS drop when statement
              type string;
            }
          }
        }
        container access {
          choice access-choice {
            leaf access-list-std {
              type string;
            }
            leaf access-list-named {
              type string;
            }
            leaf ipv6 {
              type string;
            }
          }
        }
      }
      leaf chassis-id {
        type string;
      }
      list community {
        // NCS patched for predictable order
        ordered-by user;
        key "name";
        leaf name {
          type string;
        }
        leaf view {
          type string;
        }
        choice access-choice {
          leaf RO {
            type empty;
          }
          leaf RW {
            type empty;
          }
        }
        leaf ipv6 {
          type string;
        }
        leaf access-list-name {
          type string;
        }
      }
      leaf contact {
        type string;
      }
      list context {
        // NCS patched for predictable order
        ordered-by user;
        key "name";
        leaf name {
          type string;
        }
      }
      container drop {
        leaf vrf-traffic {
          type empty;
        }
      }
      container enable {
        choice enable-choice {
          leaf informs {
            type empty;
          }
          list traps {
            // NCS patched for predictable order
            ordered-by user;
            key "name";
            leaf name {
              type string;
            }
          }
        }
      }
      container engineID {
        leaf local {
          type string;
        }
        list remote {
          // NCS patched for predictable order
          ordered-by user;
          key "address";
          leaf address {
            type string;
          }
          leaf udp-port {
            type string;
          }
          leaf vrf {
            // NCS drop tailf-common:cli-diff-dependency statement
            // NCS drop tailf-common:cli-diff-dependency statement
            type string;
          }
          leaf engineid-string {
            type string;
          }
        }
      }
      list group {
        // NCS patched for predictable order
        ordered-by user;
        key "id";
        leaf id {
          type string;
        }
        choice security-model {
          leaf v1 {
            type empty;
          }
          leaf v2c {
            type empty;
          }
          container v3 {
            leaf security-level {
              type string;
            }
            leaf context {
              type string;
            }
            leaf match {
              type string;
            }
            leaf read {
              type string;
            }
            leaf write {
              type string;
            }
            leaf notify {
              type string;
            }
            leaf access {
              type empty;
            }
            leaf ipv6 {
              // NCS drop when statement
              type string;
            }
            leaf acl {
              // NCS drop when statement
              type string;
            }
          }
        }
      }
      list host {
        // NCS patched for predictable order
        ordered-by user;
        key "ip-address";
        leaf ip-address {
          type string;
        }
        uses ncs_template_snmp-server-host-grouping;
      }
      container host-vrf {
        list host {
          // NCS patched for predictable order
          ordered-by user;
          key "ip-address vrf";
          leaf ip-address {
            type string;
          }
          leaf vrf {
            // NCS drop tailf-common:cli-diff-dependency statement
            // NCS drop tailf-common:cli-diff-dependency statement
            type string;
          }
          uses ncs_template_snmp-server-host-grouping;
        }
      }
      container ip {
        leaf dscp {
          type string;
        }
        leaf precedence {
          type string;
        }
      }
      container ifindex {
        leaf persist {
          type empty;
        }
      }
      leaf location {
        type string;
      }
      container manager {
        presence "true";
        leaf session-timeout {
          type string;
        }
      }
      leaf packetsize {
        type string;
      }
      leaf queue-length {
        type string;
      }
      container queue-limit {
        leaf notification-host {
          type string;
        }
      }
      leaf tftp-server-list {
        type string;
      }
      leaf system-shutdown {
        type empty;
      }
      container file-transfer {
        list access-group {
          // NCS patched for predictable order
          ordered-by user;
          key "name";
          leaf name {
            type string;
          }
          leaf-list protocol {
            // NCS patched for predictable order
            ordered-by user;
            type string;
          }
        }
      }
      container source-interface {
        container informs {
          uses ncs_template_interface-name-grouping;
        }
        container traps {
          uses ncs_template_interface-name-grouping;
        }
      }
      container trap {
        leaf timeout {
          type string;
          // NCS drop default statement
        }
        container authentication {
          leaf unknown-context {
            type string;
            // NCS drop default statement
          }
        }
      }
      leaf sparse-tables {
        type string;
        // NCS drop default statement
      }
      container trap-source {
        uses ncs_template_interface-name-grouping;
      }
      leaf trap-timeout {
        type string;
      }
      list view {
        // NCS patched for predictable order
        ordered-by user;
        key "name mib";
        leaf name {
          type string;
        }
        leaf mib {
          type string;
        }
        leaf inc-exl {
          type string;
        }
      }
    }
    container rtr {
      container responder {
        presence "true";
      }
    }
    container ipc {
      container zone {
        container default {
          presence "true";
        }
      }
    }
    container cts {
      container logging {
        leaf verbose {
          type empty;
        }
      }
    }
    container license {
      container accept {
        container end {
          container user {
            leaf agreement {
              type empty;
            }
          }
        }
      }
      list feature {
        // NCS patched for predictable order
        ordered-by user;
        key "line";
        leaf line {
          type string;
        }
      }
      list boot {
        // NCS patched for predictable order
        ordered-by user;
        key "line";
        leaf line {
          type string;
        }
      }
      container smart {
        leaf enable {
          type empty;
        }
      }
    }
    container setup {
      leaf express {
        type string;
        // NCS drop default statement
      }
    }
    container trunk {
      list group {
        // NCS patched for predictable order
        ordered-by user;
        key "name";
        leaf name {
          type string;
        }
        container hunt-scheme {
          choice hunt-scheme-choice {
            container round-robin {
              presence "true";
            }
            leaf random {
              type empty;
            }
            leaf sequential {
              type empty;
            }
          }
        }
      }
    }
    container gw-accounting {
      choice gw-accounting-choice {
        container syslog {
          presence "true";
          leaf stats {
            type empty;
          }
        }
        leaf aaa {
          type empty;
        }
        leaf file {
          type empty;
        }
        container h323 {
          presence "true";
          leaf vsa {
            type empty;
          }
        }
        leaf voip {
          type empty;
        }
      }
    }
    list voice-card {
      // NCS patched for predictable order
      ordered-by user;
      key "slot";
      leaf slot {
        type string;
      }
      leaf dspfarm {
        type empty;
      }
      leaf watchdog {
        type string;
        // NCS drop default statement
      }
    }
    container voice {
      container service {
        container voip {
          container sip {
            presence "true";
            container bind {
              container control {
                container source-interface {
                  uses ncs_template_interface-name-grouping;
                }
              }
              container media {
                container source-interface {
                  uses ncs_template_interface-name-grouping;
                }
              }
            }
          }
        }
      }
      container iec {
        leaf syslog {
          type empty;
        }
      }
      list translation-rule {
        // NCS patched for predictable order
        ordered-by user;
        key "tag";
        leaf tag {
          type string;
        }
        list rule {
          // NCS patched for predictable order
          ordered-by user;
          key "tag";
          leaf tag {
            type string;
          }
          leaf reject {
            type empty;
          }
          leaf pattern {
            type string;
          }
        }
      }
      list translation-profile {
        // NCS patched for predictable order
        ordered-by user;
        key "name";
        leaf name {
          type string;
        }
        container translate {
          list called {
            // NCS patched for predictable order
            ordered-by user;
            key "tag";
            leaf tag {
              type string;
            }
          }
        }
      }
    }
    container event {
      container manager {
        list environment {
          // NCS patched for predictable order
          ordered-by user;
          key "name";
          leaf name {
            type string;
          }
          leaf value {
            type string;
          }
        }
        container session {
          container cli {
            leaf username {
              type string;
            }
          }
        }
        container directory {
          container user {
            leaf policy {
              type string;
            }
          }
        }
        list applet {
          // NCS patched for predictable order
          ordered-by user;
          key "name";
          leaf name {
            type string;
          }
          leaf description {
            type string;
          }
          leaf authorization {
            type string;
          }
          leaf class {
            type string;
          }
          leaf trap {
            type empty;
          }
          container event {
            uses ncs_template_event-manager-applet-event-grouping;
            list tag {
              // NCS patched for predictable order
              ordered-by user;
              key "name";
              leaf name {
                type string;
              }
              uses ncs_template_event-manager-applet-event-grouping;
            }
          }
          list action {
            // NCS patched for predictable order
            ordered-by user;
            key "name";
            leaf name {
              type string;
            }
            choice action-choice {
              container cli {
                leaf command {
                  type string;
                }
                leaf pattern {
                  type string;
                }
              }
              leaf regexp {
                type string;
              }
              leaf wait {
                type string;
              }
              container syslog {
                leaf priority {
                  type string;
                }
                leaf msg {
                  type string;
                }
                leaf facility {
                  type string;
                }
                leaf filter {
                  type string;
                }
              }
              container snmp-trap {
                leaf intdata1 {
                  type string;
                }
                leaf intdata2 {
                  type string;
                }
                leaf strdata {
                  type string;
                }
              }
              leaf cmd {
                type string;
              }
            }
          }
          container trigger {
            presence "true";
            container correlate {
              leaf event {
                type string;
              }
              leaf operand2 {
                type string;
              }
              container event2 {
                leaf event {
                  type string;
                }
              }
            }
          }
        }
        list policy {
          // NCS patched for predictable order
          ordered-by user;
          key "name";
          leaf name {
            type string;
          }
          leaf type {
            type string;
          }
        }
      }
    }
    leaf disable-eadi {
      type empty;
    }
    container memory-size {
      leaf iomem {
        type string;
      }
    }
    container memory {
      container free {
        container low-watermark {
          leaf processor {
            type string;
          }
        }
      }
    }
    container transceiver {
      container type {
        container all {
          container monitoring {
            presence "true";
            leaf interval {
              type string;
            }
          }
        }
      }
    }
    list alias {
      // NCS patched for predictable order
      ordered-by user;
      key "mode name";
      leaf mode {
        type string;
      }
      leaf name {
        type string;
      }
      leaf line {
        type string;
      }
    }
    container spd {
      leaf enable {
        type string;
        // NCS drop default statement
      }
      leaf headroom {
        type string;
      }
    }
    container cached-show {
      container version {
        leaf version {
          type string;
        }
        leaf model {
          type string;
        }
        container license {
          leaf level {
            type string;
          }
          leaf type {
            type string;
          }
        }
      }
      container license {
        container udi {
          leaf pid {
            type string;
          }
          leaf sn {
            type string;
          }
        }
      }
      list inventory {
        // NCS patched for predictable order
        ordered-by user;
        key "name";
        leaf name {
          type string;
        }
        leaf sn {
          type string;
        }
      }
    }
    leaf xxyyzztop {
      type string;
      // NCS drop default statement
    }
    leaf xxyyzzfail {
      type empty;
    }
  }
}
