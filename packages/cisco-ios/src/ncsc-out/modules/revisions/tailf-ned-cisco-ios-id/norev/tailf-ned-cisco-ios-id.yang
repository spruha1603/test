module tailf-ned-cisco-ios-id {
  // Generated by yanger -t ncs
  tailf:ncs-device-type "cli-ned";

  namespace "urn:ios-id";
  prefix ios-id;

  import tailf-ncs-ned {
    prefix ned;
  }
  import tailf-ncs {
    prefix ncs;
  }
  import tailf-common {
    prefix tailf;
  }

  identity cisco-ios {
    base ned:cli-ned-id;
  }
}
